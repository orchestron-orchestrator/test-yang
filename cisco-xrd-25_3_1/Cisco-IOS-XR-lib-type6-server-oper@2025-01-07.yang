module Cisco-IOS-XR-lib-type6-server-oper {

  /*** NAMESPACE / PREFIX DEFINITION ***/

  namespace "http://cisco.com/ns/yang"+
    "/Cisco-IOS-XR-lib-type6-server-oper";


  prefix "lib-type6-server-oper";

  /*** LINKAGE (IMPORTS / INCLUDES) ***/

  import cisco-semver { prefix "semver"; }

  include Cisco-IOS-XR-lib-type6-server-oper-sub1 {
    revision-date 2025-01-07;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR lib-type6-server package operational data.

     This module contains definitions
     for the following management objects:
       type6: Type6 server operational data

     Copyright (c) 2013-2025 by Cisco Systems, Inc.
     All rights reserved.";

  revision "2025-01-07" {
    description
      "Added masterkey hash
       2023-01-20
         Added Timestamp feature";
    semver:module-version "1.2.0";
  }

  revision "2019-09-20" {
    description
      "Added support for new show CLI.";
    semver:module-version "1.1.0";
  }

  revision "2019-04-05" {
    description
      "Establish semantic version baseline.";
    semver:module-version "1.0.0";
  }

  revision "2018-09-28" {
    description
      "Fixed incorrect plural rendering.";
  }

  revision "2015-11-09" {
    description
      "IOS XR 6.0 revision.";
  }

  container type6 {
    config false;
    description "Type6 server operational data";

    container masterkey {
      description "type6 masterkey operation status";

      container update {
        description "type6 masterkey operation status";

        container status {
          description "type6 masterkey operation status";
          uses TYPE6-MK-OPER-BAG;
        }
      }
    }

    container server {
      description "type6 server information";
      uses TYPE6-SERVER-INFO;
    }

    container client {
      description "type6 client information";
      uses TYPE6-CLIENT-INFO;
    }
  }
}
