module Cisco-IOS-XR-sysdb-oper {

  /*** NAMESPACE / PREFIX DEFINITION ***/

  namespace "http://cisco.com/ns/yang/Cisco-IOS-XR-sysdb-oper";


  prefix "sysdb-oper";

  /*** LINKAGE (IMPORTS / INCLUDES) ***/

  import Cisco-IOS-XR-types { prefix "xr"; }

  import cisco-semver { prefix "semver"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR sysdb package operational data.

     This module contains definitions
     for the following management objects:
       sysdb-connections: Sysdb health on client connections
       sysdb: Sysdb operational data

     Copyright (c) 2013-2019 by Cisco Systems, Inc.
     All rights reserved.";

  revision "2019-04-05" {
    description
      "Establish semantic version baseline.";
    semver:module-version "1.0.1";
  }

  revision "2015-11-09" {
    description
      "IOS XR 6.0 revision.";
  }

  container sysdb-connections {
    config false;
    description "Sysdb health on client connections";

    container nodes {
      description "Node operational data";

      list node {
        key "node-name";
        description "Per-node Sysdb health on connection";
        leaf connections {
          type string;
          description "Per-node Sysdb Client Connections";
        }
        leaf node-name {
          type xr:Node-id;
          description "Node name";
        }
      }
    }
  }

  container sysdb {
    config false;
    description "Sysdb operational data";
    leaf configuration-space {
      type string;
      description "Sysdb health for configuration space";
    }
    leaf memory {
      type string;
      description "Sysdb health on memory consumption";
    }
    leaf ipc-space {
      type string;
      description "Sysdb health for operational space";
    }
    leaf cpu {
      type string;
      description "Sysdb health on cpu consumption";
    }
  }
}
