module Cisco-IOS-XR-es-acl-cfg {

  /*** NAMESPACE / PREFIX DEFINITION ***/

  namespace "http://cisco.com/ns/yang/Cisco-IOS-XR-es-acl-cfg";


  prefix "es-acl-cfg";

  /*** LINKAGE (IMPORTS / INCLUDES) ***/

  import Cisco-IOS-XR-types { prefix "xr"; }

  import cisco-semver { prefix "semver"; }

  import Cisco-IOS-XR-common-acl-datatypes { prefix "dt1"; }

  include Cisco-IOS-XR-es-ace-cfg {
    revision-date 2024-07-23;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR es-acl package configuration.

     This model is deprecated and is replaced by
     Cisco-IOS-XR-um-ethernet-services-access-list-cfg.yang which will provide the
     compatible functionalities.

     This module contains definitions
     for the following management objects:
       es-acl: Layer 2 ACL configuration data

     Copyright (c) 2013-2024 by Cisco Systems, Inc.
     All rights reserved.";

  revision "2024-07-23" {
    description
      "Increasing acl name length to 128 chars
       2022-08-16
         Deprecated the native model, replaced by UM model.";
    semver:module-version "1.2.0";
  }

  revision "2019-04-05" {
    description
      "Establish semantic version baseline.";
    semver:module-version "1.1.1";
  }

  revision "2018-02-26" {
    description
      "6.5.1 revision. Fixed datatypes for below leaves: - vlan1, vlan2 - inner-vlan1, inner-vlan2 - cos, inner-cos - dei, inner-dei - log-option.";
  }

  revision "2018-02-21" {
    description
      "Changed ether-type-number to type Hex-integer-16.";
  }

  revision "2018-01-03" {
    description
      "6.4.1 revision. Fixed a few typos in the description.";
  }

  revision "2015-11-09" {
    description
      "IOS XR 6.0 revision.";
  }

  typedef Es-acl-name {
    type xr:Cisco-ios-xr-string {
      length "1..128";
    }
    description "Es acl name";
  }

  container es-acl {
    status "deprecated";
    description
      "This model is deprecated and is replaced by
      Cisco-IOS-XR-um-ethernet-services-access-list-cfg
      .yang which will provide the compatible
      functionalities.  Layer 2 ACL configuration data";

    container accesses {
      description "Table of access lists";

      list access {
        key "name";
        description "An ACL";

        container access-list-entries {
          description
            "ACL entry table; contains list of access list
            entries";

          list access-list-entry {
            key "sequence-number";
            description
              "An ACL entry; either a description (remark)
              or anAccess List Entry to match against";
            leaf sequence-number {
              type dt1:Acl-sequence-number-range;
              description "Sequence number of access list entry";
            }
            uses ES-ACL-CONFIG-ACE;
          }
        }
        leaf name {
          type Es-acl-name;
          description "Name of the access list";
        }
      }
    }
  }
}
