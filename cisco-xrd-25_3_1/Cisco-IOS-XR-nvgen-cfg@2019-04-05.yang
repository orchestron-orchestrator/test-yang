module Cisco-IOS-XR-nvgen-cfg {

  /*** NAMESPACE / PREFIX DEFINITION ***/

  namespace "http://cisco.com/ns/yang/Cisco-IOS-XR-nvgen-cfg";


  prefix "nvgen-cfg";

  /*** LINKAGE (IMPORTS / INCLUDES) ***/

  import cisco-semver { prefix "semver"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR nvgen package configuration.

     This module contains definitions
     for the following management objects:
       nvgen-cfg: nvgen config commands

     Copyright (c) 2013-2019 by Cisco Systems, Inc.
     All rights reserved.";

  revision "2019-04-05" {
    description
      "Establish semantic version baseline.";
    semver:module-version "1.0.0";
  }

  revision "2015-11-09" {
    description
      "IOS XR 6.0 revision.";
  }

  container nvgen-cfg {
    description "nvgen config commands";

    container sanitize-flags {
      description "nvgen default sanitize flags";
      leaf passwords {
        type empty;
        description "nvgen will default sanitize passwords";
      }
      leaf comments {
        type empty;
        description "nvgen will default sanitize comments";
      }
      leaf ip-addrs {
        type empty;
        description
          "nvgen will default sanitize ip addresses and
          masks";
      }
      leaf strings {
        type empty;
        description
          "nvgen will default sanitize strings which are
          not passwords/comments/usernames";
      }
      leaf usernames {
        type empty;
        description "nvgen will default sanitize usernames";
      }
    }
    leaf enter {
      type empty;
      description "nvgen submode enter tuple";
    }
  }
}
