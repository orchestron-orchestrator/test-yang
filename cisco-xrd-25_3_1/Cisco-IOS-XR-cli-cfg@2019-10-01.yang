module Cisco-IOS-XR-cli-cfg {
  namespace "http://cisco.com/ns/yang/Cisco-IOS-XR-cli-cfg";
  prefix cli-cfg;

  import cisco-semver {
    prefix semver;
  }

  organization
    "Cisco Systems, Inc.";
  contact
    "Cisco Systems, Inc.
     Customer Service
      
     Postal: 170 West Tasman Drive
     San Jose, CA 95134
      
     Tel: +1 800 553-NETS
      
     E-mail: cs-yang@cisco.com";
  description
    "This module contains a collection of YANG definitions
     for Cisco IOS-XR CLI package configuration.
      
     Copyright (c) 2019 by Cisco Systems, Inc.
     All rights reserved.";

  revision 2019-10-01 {
    description
      "Made changes to be RFC6087 compliant";
    semver:module-version "2.0.0";
  }

  revision "2019-04-05" {
    description
      "Establish semantic version baseline.";
    semver:module-version "1.0.0";
  }

  revision "2019-03-18" {
    description
      "Initial draft";
  }

  leaf cli {
    type string;
    description
      "A set of CLI config commands. Content matching is not supported for this node.";
  }
}
