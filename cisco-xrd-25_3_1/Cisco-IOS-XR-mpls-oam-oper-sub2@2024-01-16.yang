submodule Cisco-IOS-XR-mpls-oam-oper-sub2 {

  belongs-to Cisco-IOS-XR-mpls-oam-oper {
    prefix Cisco-IOS-XR-mpls-oam-oper;
  }

  /*** LINKAGE (IMPORTS / INCLUDES) ***/

  import ietf-inet-types { prefix "inet"; }

  import ietf-yang-types { prefix "yang"; }

  import Cisco-IOS-XR-types { prefix "xr"; }

  import cisco-semver { prefix "semver"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR mpls-oam package operational data.

     Copyright (c) 2013-2024 by Cisco Systems, Inc.
     All rights reserved.";

  revision "2024-01-16" {
    description
      "Added request database";
    semver:module-version "1.1.0";
  }

  revision "2019-04-05" {
    description
      "Establish semantic version baseline.";
    semver:module-version "1.0.1";
  }

  revision "2015-11-09" {
    description
      "IOS XR 6.0 revision.";
  }

  typedef Lspv-bag-tt-request-state {
    type enumeration {
      enum state-idle {
        description "Tree trace state idle";
      }
      enum node-discover {
        description "Tree trace node discover";
      }
      enum node-discover-wait {
        description "Tree trace node discover wait";
      }
      enum node-discover-wait-interval {
        description "Tree trace node discover wait interval";
      }
      enum selector-discover {
        description "Tree trace node selector discover";
      }
      enum selector-discover-wait {
        description "Tree trace node selector discover wait";
      }
      enum selector-discover-wait-interval {
        description
          "Tree trace node selector discover wait interval";
      }
    }
    description "LSPV tree trace request state";
  }
  typedef Lspv-bag-fec {
    type enumeration {
      enum unspecified-fec {
        value 0;
        description "FEC type unspecified";
      }
      enum ld-pv4fec {
        value 1;
        description "LDP FEC specified";
      }
      enum ld-pv6fec {
        value 2;
        description "LDPv6 FEC specified";
      }
      enum rsv-pv4fec {
        value 3;
        description "RSVPv4 FEC specified";
      }
      enum rsv-pv6fec {
        value 4;
        description "RSVPv6 FEC specified";
      }
      enum na1-fec {
        value 5;
        description "Not Assigned";
      }
      enum vpnv4fec {
        value 6;
        description "VPNv4 FEC specified";
      }
      enum vpnv6fec {
        value 7;
        description "VPNv6 FEC specified";
      }
      enum l2vpn-fec {
        value 8;
        description "L2VPN FEC specified";
      }
      enum fec128-deprecated {
        value 9;
        description "FEC128 Deprecated specified";
      }
      enum fec128 {
        value 10;
        description "FEC128 specified";
      }
      enum fec129 {
        value 11;
        description "FEC129 specified";
      }
      enum bgp-labelv4fec {
        value 12;
        description "BGP Label v4 FEC specified";
      }
      enum bgp-labelv6fec {
        value 13;
        description "BGP Label v6 FEC specified";
      }
      enum genericv4fec {
        value 14;
        description "Generic v4 FEC specified";
      }
      enum genericv6fec {
        value 15;
        description "Generic v6 FEC specified";
      }
      enum nil-fec {
        value 16;
        description "Nil FEC specified";
      }
      enum rsv-pv4p2mp-fec {
        value 17;
        description "RSVPv4 P2MP FEC specified";
      }
      enum rsv-pv6p2mp-fec {
        value 18;
        description "RSVPv6 P2MP FEC specified";
      }
      enum mldp-p2mp-fec {
        value 19;
        description "Multicast P2MP LDP FEC specified";
      }
      enum mldp-mp2mp-fec {
        value 20;
        description "Multicast MP2MP LDP FEC specified";
      }
      enum na2-fec {
        value 21;
        description "Not Assigned";
      }
      enum static-fec {
        value 22;
        description "Static LSP specified";
      }
      enum static-pseudowire-fec {
        value 23;
        description "Static Pseudowire specified";
      }
    }
    description "LSPV FEC types";
  }
  typedef Hash-key {
    type enumeration {
      enum no-multipath {
        description "No multipath";
      }
      enum label {
        description "Label";
      }
      enum ipv4 {
        description "IPv4 type";
      }
      enum label-range {
        description "Label range";
      }
      enum ipv4-range {
        description "IPv4 range";
      }
      enum no-more-labels {
        description "No more labels";
      }
      enum ip-all {
        description "IP all";
      }
      enum no-match {
        description "No match";
      }
      enum ipv4-bit-mask {
        description "IPv4 bitmask";
      }
      enum label-bit-mask {
        description "Label bitmask";
      }
    }
    description "LSPV hash key types";
  }
  typedef Lspv-bag-reply-mode {
    type enumeration {
      enum do-not-reply {
        value 1;
        description "Do not reply mode";
      }
      enum ipv4udp {
        value 2;
        description "IPv4 UDP";
      }
      enum ipv4udp-ra {
        value 3;
        description "IPv4 UDP with RA";
      }
      enum mpls-ra {
        value 4;
        description "MPLS with RA";
      }
    }
    description "LSPV reply mode";
  }
  typedef Lspv-bag-interface-state {
    type enumeration {
      enum not-ready {
        description "Not ready";
      }
      enum admin-down {
        description "Admin down";
      }
      enum down {
        description "Down";
      }
      enum up {
        description "UP";
      }
      enum shutdown {
        description "Shutdown";
      }
      enum error-disable {
        description "Error disable";
      }
      enum down-immediate {
        description "Immediate down";
      }
      enum admin-immediate {
        description "Immediate admin";
      }
      enum graceful-down {
        description "Graceful down";
      }
      enum begin-shutdown {
        description "Begin shutdown";
      }
      enum end-shutdown {
        description "End shutdown";
      }
      enum begin-error-disable {
        description "Begin error disable";
      }
      enum end-error-disable {
        description "End error disable";
      }
      enum begin-graceful-down {
        description "Begin graceful down";
      }
      enum reset {
        description "Reset";
      }
      enum operational {
        description "Operational";
      }
      enum not-operational {
        description "Not operational";
      }
      enum not-known {
        description "Unknown";
      }
    }
    description "LSPV interface state";
  }
  typedef Lspv-bag-request-state {
    type enumeration {
      enum idle {
        description "Request state idle";
      }
      enum wait-property {
        description "Request state property";
      }
      enum wait-reply {
        description "Request state wait reply";
      }
      enum wait-finish {
        description "Request state wait finish";
      }
    }
    description "LSPV request state";
  }
  typedef Lspv-bag-target {
    type enumeration {
      enum target-unknown {
        description "Target unknown";
      }
      enum target-ipv4 {
        description "Target IPv4";
      }
      enum target-te {
        description "Target TE";
      }
      enum target-pseudowire {
        description "Target pseudowire";
      }
      enum target-ipv4-broadcast {
        description "IPv4 broadcast Deprecated";
      }
      enum targetm-ldp {
        description "Target mLDP";
      }
      enum target-ipv6 {
        description "Target IPv6";
      }
      enum target-nil-fec {
        description "Target Nil FEC";
      }
    }
    description "LSPV target type";
  }
  typedef Lspv-bag-cmd {
    type enumeration {
      enum ping {
        value 1;
        description "Ping command";
      }
      enum trace {
        value 2;
        description "Trace command";
      }
      enum path-discovery {
        value 3;
        description "Path discovery";
      }
    }
    description "LSPV command type";
  }

  grouping LSPV-TT-REQUEST-BRIEF-INFO {
    description "LSPV tree trace request brief information";

    container client-command {
      description "Client command";
      uses LSPV-COMMAND-INFO-BRIEF;
    }
    leaf state {
      type Lspv-bag-tt-request-state;
      description "TT FSM state";
    }
    leaf selector-discovery-retries {
      type uint16;
      description "Selector discovery retry count";
    }
    leaf selector-discovery-back-trace-retries {
      type uint16;
      description "Selector discovery backtrace retry count";
    }
  }

  grouping LSPV-TT-STATS-INFO {
    description "LSPV tree trace statistics information";
    leaf echo-request-attempts {
      type uint32;
      description "Number of echo request attempts";
    }
    leaf echo-request-failures {
      type uint32;
      description "Number of echo request failures";
    }
    leaf received-echo-replies {
      type uint32;
      description "Number of echo reply received";
    }
    leaf timedout-echo-replies {
      type uint32;
      description "Number of echo reply timedout";
    }
    leaf found-paths {
      type uint32;
      description "Number of path found";
    }
    leaf broken-paths {
      type uint32;
      description "Number of path broken";
    }
    leaf unexplored-paths {
      type uint32;
      description "Number of path unexplored";
    }
  }

  grouping LSPV-MULTIPATH-INFO {
    description "LSPV multipath information";
    leaf hash-key-type {
      type Hash-key;
      description "Hash key type";
    }
    leaf depth-limit {
      type uint8;
      description "Depth limit";
    }
    leaf selector-bit-cursor {
      type uint32;
      description "Selector bit cursor";
    }
    leaf selector-bitmap-size {
      type uint16;
      description "Selector bitmap size";
    }
    leaf selector-start-address {
      type inet:ipv4-address;
      description "Selector start address";
    }
  }

  grouping LSPV-DS-OUTINFO-INFO {
    description "LSPV downstream outgoing information";
    leaf is-downstream-outgoing-valid {
      type boolean;
      description "Is downstream outgoing information valid";
    }
    leaf downstream-interface-address {
      type inet:ipv4-address;
      description "Downstream interface address";
    }
    leaf downstream-interface-mtu {
      type inet:ipv4-address;
      description "Downstream interface MTU";
    }
    leaf downstream-labels {
      type uint8;
      description "Number of downstream labels";
    }
    leaf-list downstream-label-stack {
      type uint32;
      description "Downstream label stack";
    }
  }

  grouping LSPV-TT-NODE-INFO {
    description "LSPV tree trace node information";

    container downstream-mapping-in-use {
      description "Downstream mapping in use";
      uses LSPV-DSMAP-INFO;
    }
    leaf node-address {
      type inet:ipv4-address;
      description "Node address";
    }
    leaf downstream-mapping {
      type uint16;
      description "Number of downstream mapping";
    }
    leaf is-downstream-mapping-valid {
      type boolean;
      description "Is downstream mapping valid";
    }
  }

  grouping LSPV-DS-ILS-INFO {
    description
      "LSPV downstream interface and label stack
      information";
    leaf is-valid {
      type boolean;
      description
        "Is the interface and label stack information
        valid";
    }
    leaf downstream-router-id {
      type inet:ipv4-address;
      description "Downstream router ID";
    }
    leaf downstream-interface-name {
      type xr:Interface-name;
      description "Downstream interface name";
    }
  }

  grouping LSPV-RESULT-INFO {
    description "LSPV result information";

    container downstream-mapping-sent {
      description "Downstream mapping sent";
      uses LSPV-DSMAP-INFO;
    }

    container downstream-interface-label-stack {
      description "Downstream interface and label stack";
      uses LSPV-DS-ILS-INFO;
    }

    container downstream-detailed-mapping-sent {
      description "Downstream detailed mapping sent";
      uses LSPV-DDMAP-INFO;
    }
    leaf reply-source-address {
      type inet:ipv4-address;
      description "Source address of echo reply";
    }
    leaf time-sent {
      type uint32;
      description "Network time echo request was sent";
    }
    leaf time-received {
      type uint32;
      description "Network time target received echo request";
    }
    leaf delta-time {
      type uint32;
      description "Delta network time";
    }
    leaf rx-tlv-version {
      type uint32;
      description "Peer TLV version";
    }
    leaf is-traceroute {
      type boolean;
      description "Is traceroute info returned";
    }
    leaf received-downstream-mappings {
      type uint32;
      description "Number of downstream mappings received";
    }
    leaf output-interface-address {
      type inet:ipv4-address;
      description "Output interface address";
    }
    leaf ttl {
      type uint8;
      description "Time to live";
    }
  }

  grouping LSPV-TT-REQUEST-INFO {
    description "LSPV tree trace request information";

    container client-command {
      description "Client command";
      uses LSPV-COMMAND-INFO;
    }

    container lspv-command {
      description "LSPV command";
      uses LSPV-COMMAND-INFO;
    }

    container lspv-result {
      description "LSPV result";
      uses LSPV-RESULT-INFO;
    }

    container active-downsteam-outgoing {
      description "Active downstream outgoing information";
      uses LSPV-DS-OUTINFO-INFO;
    }

    container multipath {
      description "Multipath information";
      uses LSPV-MULTIPATH-INFO;
    }

    container statistics {
      description "Statistics";
      uses LSPV-TT-STATS-INFO;
    }
    leaf state {
      type Lspv-bag-tt-request-state;
      description "TT FSM state";
    }
    leaf selector-discovery-retries {
      type uint16;
      description "Selector discovery retry count";
    }
    leaf selector-discovery-back-trace-retries {
      type uint16;
      description "Selector discovery backtrace retry count";
    }
    leaf node-address {
      type inet:ipv4-address;
      description "Node address";
    }
    leaf node-discovery-retries {
      type uint16;
      description "Node discovery retry count";
    }
    leaf selector-discovery-back-trace-max-retries {
      type uint16;
      description
        "Maximum selector discovery backtrace retry count";
    }
    leaf process-name {
      type string;
      description "Client process name";
    }
    leaf node-id {
      type xr:Node-id;
      description "Location where client resides";
    }
    leaf is-timer-running {
      type boolean;
      description "Is timer running";
    }
    leaf timer-remaining {
      type uint32;
      units "second";
      description "Timer remaining seconds";
    }

    list node-database {
      description "Node database";
      uses LSPV-TT-NODE-INFO;
    }
  }

  grouping LSPV-DDMAP-INFO {
    description "LSPV downstream detailed mapping information";
    leaf downstream-router-id {
      type inet:ipv4-address;
      description "Downstream router ID";
    }
    leaf downstream-interface-mtu {
      type uint16;
      description "Downstream interface MTU";
    }
    leaf interface-address {
      type inet:ipv4-address;
      description "Interface IP address";
    }
    leaf ingress-link-id {
      type uint32;
      description "Ingress link ID";
    }
    leaf egress-link-id {
      type uint32;
      description "Egress link ID";
    }
    leaf downstream-return-code {
      type uint8;
      description
        "Downstream Return Code. See section 3.2 of http
        ://tools.ietf
        .org/html
        /draft-ietf-mpls-lsp-ping-enhanced-dsmap";
    }
    leaf downstream-return-sub-code {
      type uint8;
      description
        "Downstream Return Sub Code. See section 3.2 of
        http://tools.ietf
        .org/html
        /draft-ietf-mpls-lsp-ping-enhanced-dsmap";
    }
    leaf downstream-labels {
      type uint32;
      description "Number of downstream labels";
    }
    leaf-list downstream-label-stack {
      type uint32;
      description "Downstream label stack";
    }
  }

  grouping LSPV-DSMAP-INFO {
    description "LSPV downstream mapping information";
    leaf downstream-router-id {
      type inet:ipv4-address;
      description "Downstream router ID";
    }
    leaf downstream-interface-mtu {
      type uint16;
      description "Downstream interface MTU";
    }
    leaf ingress-link-id {
      type uint32;
      description "Ingress link ID";
    }
    leaf egress-link-id {
      type uint32;
      description "Egress link ID";
    }
    leaf interface-address {
      type inet:ipv4-address;
      description "Interface IP address";
    }
    leaf hash-key-type {
      type Hash-key;
      description "Hash key type";
    }
    leaf depth-limit {
      type uint8;
      description "Depth limit";
    }
    leaf multipath-length {
      type uint16;
      description "Multipath length";
    }
    leaf downstream-labels {
      type uint32;
      description "Number of downstream labels";
    }
    leaf-list downstream-label-stack {
      type uint32;
      description "Downstream label stack";
    }
  }

  grouping LSPV-COMMAND-INFO {
    description "LSPV command information";

    container command-brief {
      description "Command Brief";
      uses LSPV-COMMAND-INFO-BRIEF;
    }

    container tx-downstream-mapping {
      description "Sent downstream mapping";
      uses LSPV-DSMAP-INFO;
    }

    container tx-downstream-detailed-mapping {
      description "Sent downstream detailed mapping";
      uses LSPV-DDMAP-INFO;
    }
    leaf tunnel-interface-name {
      type xr:Interface-name;
      description "Tunnel Interface name";
    }
    leaf source-address {
      type inet:ipv4-address;
      description "Source address";
    }
    leaf destination-address {
      type inet:ipv4-address;
      description "Destination address";
    }
    leaf tlv-version {
      type uint32;
      description "TLV version";
    }
    leaf reply-mode {
      type Lspv-bag-reply-mode;
      description "Echo reply mode";
    }
    leaf size {
      type uint32;
      description "Size of echo request packet";
    }
    leaf ttl {
      type uint16;
      description "Time to live for echo req packet";
    }
    leaf ttl-max {
      type uint8;
      description "Maximum TTL for echo request packet";
    }
    leaf exp-bits {
      type yang:hex-string;
      description "EXP bits for echo request ip header";
    }
    leaf reply-dscp-bits {
      type yang:hex-string;
      description "DSCP bits for echo reply ip header";
    }
    leaf timeout {
      type uint32;
      description "Maximum time to wait (second) for echo reply";
    }
    leaf send-interval {
      type uint32;
      description "Network time between sending echo request";
    }
    leaf maximum-retries {
      type uint8;
      description "Maximum treetrace retry count";
    }
    leaf pattern {
      type uint16;
      description "Data pattern for pad TLV";
    }
    leaf payload-length {
      type uint32;
      description "Length of payload";
    }
    leaf is-padding-required {
      type boolean;
      description "Is padding required";
    }
    leaf is-reply-tos-requested {
      type boolean;
      description "Request sending of reply tos tlv";
    }
    leaf is-downstream-mapping-requested {
      type boolean;
      description
        "Force sending downstream mapping in echo request";
    }
    leaf is-tfs-validation-requested {
      type boolean;
      description "Is transit router FEC validation requested";
    }
    leaf is-ils-requested {
      type boolean;
      description "Is ILS object requested";
    }
    leaf is-vendor-tlv-disabled {
      type boolean;
      description "Disable send of Cisco tlv";
    }
    leaf is-label-shimming-mode {
      type boolean;
      description "Label shimming mode";
    }
    leaf shim-label {
      type uint32;
      description "Label to be shimmed";
    }
    leaf hash-key {
      type uint8;
      description "Multipath hash key type";
    }
    leaf bitmap-size {
      type uint16;
      description "Multipath bitmap size";
    }
    leaf max-selector {
      type uint32;
      description "Maximum number of selectors allowed";
    }
    leaf is-tx-downstream-mapping-valid {
      type boolean;
      description "Is transmitted downstream mapping valid";
    }
    leaf output-interface-name {
      type xr:Interface-name;
      description "Output Interface name";
    }
    leaf is-downstream-detailed-mapping-requested {
      type boolean;
      description
        "Force sending downstream detailed mapping in
        echo request";
    }
    leaf fe-ctype {
      type Lspv-bag-fec;
      description "FEC type to be used";
    }
  }

  grouping LSPV-REQUEST-INFO {
    description "LSPV request information";

    container command {
      description "Command";
      uses LSPV-COMMAND-INFO;
    }

    container tx-downstream-mapping {
      description "Sent downstream mapping";
      uses LSPV-DSMAP-INFO;
    }

    container tx-downstream-detailed-mapping {
      description "Sent downstream detailed mapping";
      uses LSPV-DDMAP-INFO;
    }
    leaf state {
      type Lspv-bag-request-state;
      description "FSM state";
    }
    leaf session-handle {
      type uint32;
      description "Session handle";
    }
    leaf process-name {
      type string;
      description "Client process name";
    }
    leaf node-id {
      type xr:Node-id;
      description "Location where client resides";
    }
    leaf is-timeout-timer-running {
      type boolean;
      description "Is timeout timer running";
    }
    leaf timeout-timer-remaining {
      type uint32;
      units "second";
      description "Timeout timer remaining seconds";
    }
    leaf output-interface-name {
      type xr:Interface-name;
      description "Output interface name";
    }
    leaf output-interface-address {
      type inet:ipv4-address;
      description "Output interface address";
    }
    leaf next-hop-address {
      type inet:ipv4-address;
      description "Nexthop address";
    }
  }

  grouping LSPV-COLLAB-COUNTER {
    description "LSPV collaborator counters";
    leaf ups {
      type uint32;
      description "Collaborator up counter";
    }
    leaf downs {
      type uint32;
      description "Collaborator down counter";
    }
  }

  grouping LSPV-COLLAB-STATISTICS {
    description "LSPV collaborator statistics";

    container collaborator-i-parm {
      description "Collaborator IPARM counts";
      uses LSPV-COLLAB-COUNTER;
    }

    container collaborator-im {
      description "Collaborator IM counts";
      uses LSPV-COLLAB-COUNTER;
    }

    container collaborator-net-io {
      description "Collaborator NetIO counts";
      uses LSPV-COLLAB-COUNTER;
    }

    container collaborator-rib {
      description "Collaborator RIB counts";
      uses LSPV-COLLAB-COUNTER;
    }
  }

  grouping LSPV-MSG-STATISTICS {
    description "LSPV verification process message statistics";
    leaf register-messages {
      type uint32;
      description "Message register count";
    }
    leaf unregister-messages {
      type uint32;
      description "Message unregister count";
    }
    leaf echo-submit-messages {
      type uint32;
      description "Message echo submit count";
    }
    leaf echo-cancel-messages {
      type uint32;
      description "Message echo cancel count";
    }
    leaf get-result-messages {
      type uint32;
      description "Message get results count";
    }
    leaf get-config-messages {
      type uint32;
      description "Message get configiuration count";
    }
    leaf get-response-messages {
      type uint32;
      description "Message get response count";
    }
    leaf property-response-messages {
      type uint32;
      description "Message property response count";
    }
    leaf property-request-messages {
      type uint32;
      description "Message property request count";
    }
    leaf property-block-messages {
      type uint32;
      description "Message property block count";
    }
    leaf thread-request-messages {
      type uint32;
      description "Message thread request count";
    }
  }

  grouping LSPV-GLOBAL-TYPE {
    description "LSPV global information";

    container message-statistics {
      description "Message statistics";
      uses LSPV-MSG-STATISTICS;
    }

    container collaborator-statistics {
      description "Collaborator statistics";
      uses LSPV-COLLAB-STATISTICS;
    }
    leaf total-clients {
      type uint32;
      description "Number of clients";
    }
  }

  grouping LSPV-BAG-STATS-TX {
    description "LSPV transmission statistics";

    container transmit-good {
      description "Transmit good packets";
      uses LSPV-PKT-COUNTER;
    }

    container transmit-drop {
      description "Transmit drop packets";
      uses LSPV-PKT-COUNTER;
    }

    container transmit-bfd-good {
      description "Transmit good BFD request packets";
      uses LSPV-PKT-COUNTER;
    }

    container bfd-no-reply {
      description
        "No Reply action for echo reqeust of BFD
        bootstrap";
      uses LSPV-PKT-COUNTER;
    }
  }

  grouping LSPV-PKT-COUNTER {
    description "LSPV verification packet count";
    leaf packets {
      type uint64;
      description "Packet counter";
    }
    leaf bytes {
      type uint64;
      units "byte";
      description "Byte counter";
    }
  }

  grouping LSPV-BAG-STATS-RX {
    description "LSPV reception statistics";

    container received-good-request {
      description "Received good request";
      uses LSPV-PKT-COUNTER;
    }

    container received-good-reply {
      description "Received good reply";
      uses LSPV-PKT-COUNTER;
    }

    container received-unknown {
      description "Received unknown packets";
      uses LSPV-PKT-COUNTER;
    }

    container received-error-ip-header {
      description "IP header error";
      uses LSPV-PKT-COUNTER;
    }

    container received-error-udp-header {
      description "UDP header error";
      uses LSPV-PKT-COUNTER;
    }

    container received-error-runt {
      description "RUNT error";
      uses LSPV-PKT-COUNTER;
    }

    container received-error-queue-full {
      description "Dropped queue full";
      uses LSPV-PKT-COUNTER;
    }

    container received-error-general {
      description "General error";
      uses LSPV-PKT-COUNTER;
    }

    container received-error-no-interface {
      description "Error no Interfaces";
      uses LSPV-PKT-COUNTER;
    }

    container received-error-no-memory {
      description "Error no memory";
      uses LSPV-PKT-COUNTER;
    }

    container protect-protocol-received-good-request {
      description "Protect Protocol Received good request";
      uses LSPV-PKT-COUNTER;
    }

    container protect-protocol-received-good-reply {
      description "Protect Protocol Received good reply";
      uses LSPV-PKT-COUNTER;
    }

    container received-good-bfd-request {
      description "Received Reqeust with BFD TLV";
      uses LSPV-PKT-COUNTER;
    }

    container received-good-bfd-reply {
      description "Received Reply with BFD TLV";
      uses LSPV-PKT-COUNTER;
    }
  }

  grouping LSPV-PACKET-STATISTICS {
    description "Receive and transmit packet counts";

    container received {
      description "Packet reception counts";
      uses LSPV-BAG-STATS-RX;
    }

    container sent {
      description "Packet transmit counts";
      uses LSPV-BAG-STATS-TX;
    }

    container working-req-sent {
      description "Working Request Packet transmit counts";
      uses LSPV-BAG-STATS-TX;
    }

    container working-rep-sent {
      description "Working Reply Packet transmit counts";
      uses LSPV-BAG-STATS-TX;
    }

    container protect-req-sent {
      description "Protect Request Packet transmit counts";
      uses LSPV-BAG-STATS-TX;
    }

    container protect-rep-sent {
      description "Protect Reply Packet transmit counts";
      uses LSPV-BAG-STATS-TX;
    }
  }

  grouping LSPV-INTERFACE-INFO {
    description "LSPV interface information";

    container interface-brief {
      description "Interface brief";
      uses LSPV-INTERFACE-INFO-BRIEF;
    }

    container packet-statistics {
      description "Packet statistics";
      uses LSPV-PACKET-STATISTICS;
    }
  }

  grouping LSPV-INTERFACE-INFO-BRIEF {
    description "LSPV interface brief information";
    leaf interface-name-xr {
      type xr:Interface-name;
      description "Interface name";
    }
    leaf state {
      type Lspv-bag-interface-state;
      description "Interface state";
    }
    leaf mtu {
      type uint32;
      description "Interface MTU";
    }
    leaf prefix-length {
      type uint32;
      description "Prefix length (IPv4)";
    }
    leaf prefix-length-v6 {
      type uint32;
      description "Prefix length (IPv6)";
    }
    leaf primary-address {
      type inet:ipv4-address;
      description "Primary interface address (IPv4)";
    }
    leaf primary-address-v6 {
      type inet:ipv6-address;
      description "Primary interface address (IPv6)";
    }
  }

  grouping LSPV-COMMAND-INFO-BRIEF {
    description "LSPV command information";
    leaf command-type {
      type Lspv-bag-cmd;
      description "Command type";
    }
    leaf target-type {
      type Lspv-bag-target;
      description "Target type";
    }
    leaf target-address {
      type inet:ipv4-address;
      description "Target address";
    }
    leaf target-mask {
      type uint8;
      description "Target mask";
    }
    leaf pseudowire-id {
      type uint32;
      description "Pseudowire ID";
    }
    leaf mldp-opaque {
      type string;
      description "mLDP target name";
    }
    leaf nil-fec-num-lables {
      type uint8;
      description "Nil FEC num labels";
    }
    leaf-list nilfec-label {
      type uint32;
      max-elements "12";
      description "Nil FEC labels";
    }
  }

  grouping LSPV-REQUEST-INFO-BRIEF {
    description "LSPV request brief information";

    container command {
      description "Command";
      uses LSPV-COMMAND-INFO-BRIEF;
    }
    leaf state {
      type Lspv-bag-request-state;
      description "FSM state";
    }
  }
}
