module Cisco-IOS-XR-lldp-clear-act {

    namespace "http://cisco.com/ns/yang/Cisco-IOS-XR-lldp-clear-act";
    
    prefix "lldp-clear-act";
    
    import cisco-semver { prefix "semver"; }
    
    import Cisco-IOS-XR-types { prefix "xr"; }

    organization "Cisco Systems, Inc.";
    
    contact
    "Cisco Systems, Inc.
     Customer Service

     Postal: 170 West Tasman Drive
     San Jose, CA 95134

     Tel: +1 800 553-NETS

     E-mail: cs-yang@cisco.com";
    
    description 
    "This module contains a collection of YANG definitions
     for Cisco IOS-XR clear per-interface adjacencies for lldp module.

     Copyright (c) 2018-2019, 2021 by Cisco Systems, Inc.
     All rights reserved.";
    
    revision "2021-10-04" {
      description
        "Added task privileges.";
    semver:module-version "1.1.0";
    }

  revision "2019-11-13" {
    description
      "Establish semantic version baseline.";
    semver:module-version "1.0.0";
  }

  revision "2019-09-09" {
    description
      "IOS XR 6.5.1 revision.";
  }

    rpc clear-lldp-adj {
        description "Clear lldp per interface adjacencies";
        xr:xr-task "ethernet-services | lldp";
        input {
            leaf interface {
                description "Interface name in R/S/I/P format";
                type string;
            }
        }
    }
}
