module Cisco-IOS-XR-mpls-static-oper {

  /*** NAMESPACE / PREFIX DEFINITION ***/

  namespace "http://cisco.com/ns/yang/Cisco-IOS-XR-mpls-static-oper";


  prefix "mpls-static-oper";

  /*** LINKAGE (IMPORTS / INCLUDES) ***/

  import Cisco-IOS-XR-types { prefix "xr"; }

  import cisco-semver { prefix "semver"; }

  include Cisco-IOS-XR-mpls-static-oper-sub1 {
    revision-date 2025-05-23;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR mpls-static package operational data.

     This module contains definitions
     for the following management objects:
       mpls-static: MPLS STATIC operational data

     Copyright (c) 2013-2025 by Cisco Systems, Inc.
     All rights reserved.";

  revision "2025-05-23" {
    description
      "Added lsd-interface-operations-count to mpls-static-summary
       2025-03-01
         Added mpls-static-lsp-fwd-info
       2023-08-01
         Changed per-vrf46 to per-vrf-46.
       2023-04-24
         Added top label hash field
       2023-03-28
         Added per-vrf46 label mode.
       2023-02-28
         Added l2bypass flag.
       2022-12-22
         Added mapped interfaces entries for PLE CEM supoort.
       2022-03-29
         Adding Label and RW Op thread filters and counts.";
    semver:module-version "1.1.0";
  }

  revision "2019-04-05" {
    description
      "Establish semantic version baseline.";
    semver:module-version "1.0.1";
  }

  revision "2017-05-01" {
    description
      "Fixing backward compatibility error in module.";
  }

  revision "2015-11-09" {
    description
      "IOS XR 6.0 revision.";
  }

  grouping LOCAL-LABEL-TABLE {
    description "Common node of mpls-static, vrf";

    container local-labels {
      description "data for static local-label table";

      list local-label {
        key "local-label-id";
        description "Data for static label";
        leaf local-label-id {
          type uint32 {
            range "16..1048575";
          }
          description "Local Label";
        }
        uses MPLS-STATIC-LBL-INFO;
      }
    }
  }

  container mpls-static {
    config false;
    description "MPLS STATIC operational data";

    container vrfs {
      description "VRF table";

      list vrf {
        key "vrf-name";
        description "VRF Name";

        container lsps {
          description "data for static lsp table";

          list lsp {
            key "lsp-name";
            description "Data for static lsp";
            leaf lsp-name {
              type xr:Cisco-ios-xr-string;
              description "LSP Name";
            }
            uses MPLS-STATIC-LSP-INFO;
          }
        }
        leaf vrf-name {
          type xr:Cisco-ios-xr-string;
          description "VRF Name";
        }
        uses LOCAL-LABEL-TABLE;
      }
    }

    container summary {
      description "MPLS STATIC summary data";
      uses MPLS-STATIC-SUMMARY;
    }
    uses LOCAL-LABEL-TABLE;
  }
}
