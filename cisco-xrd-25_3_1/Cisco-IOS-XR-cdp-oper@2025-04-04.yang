module Cisco-IOS-XR-cdp-oper {

  /*** NAMESPACE / PREFIX DEFINITION ***/

  namespace "http://cisco.com/ns/yang/Cisco-IOS-XR-cdp-oper";


  prefix "cdp-oper";

  /*** LINKAGE (IMPORTS / INCLUDES) ***/

  import Cisco-IOS-XR-types { prefix "xr"; }

  import cisco-semver { prefix "semver"; }

  include Cisco-IOS-XR-cdp-oper-sub1 {
    revision-date 2025-04-04;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR cdp package operational data.

     This module contains definitions
     for the following management objects:
       cdp: CDP operational data

     Copyright (c) 2013-2025 by Cisco Systems, Inc.
     All rights reserved.";

  revision "2025-04-04" {
    description
      "interface-handle leaf removed.";
    semver:module-version "2.0.0";
  }

  revision "2019-04-05" {
    description
      "Establish semantic version baseline.";
    semver:module-version "1.0.1";
  }

  revision "2019-01-09" {
    description
      "Fixing yang usability issues.";
  }

  revision "2015-07-30" {
    description
      "Revison descritption string.";
  }

  revision "2015-01-07" {
    description
      "IOS XR 5.3.1 revision.";
  }

  container cdp {
    config false;
    description "CDP operational data";

    container nodes {
      description "Per node CDP operational data";

      list node {
        key "node-name";
        description
          "The CDP operational data for a particular node";

        container neighbors {
          description "The CDP neighbor tables on this node";

          container details {
            description "The detailed CDP neighbor table";

            list detail {
              description
                "Detailed information about a neighbor
                discovered by CDP";
              leaf interface-name {
                type xr:Interface-name;
                description "CDP neighbor interface";
              }
              leaf device-id {
                type string;
                description "The neighboring device identifier";
              }
              uses CDP-NEIGHBOR;
            }
          }

          container devices {
            description "The detailed CDP neighbor table";

            list device {
              key "device-id";
              description
                "Detailed information about a neighbor
                discovered by CDP";
              leaf device-id {
                type string;
                description "The neighboring device identifier";
              }
              uses CDP-NEIGHBOR;
            }
          }

          container summaries {
            description "The CDP neighbor summary table";

            list summary {
              description
                "Brief information about a neighbor
                discovered by CDP";
              leaf interface-name {
                type xr:Interface-name;
                description "CDP neighbor interface";
              }
              leaf device-id {
                type string;
                description "The neighboring device identifier";
              }
              uses CDP-NEIGHBOR;
            }
          }
        }

        container statistics {
          description "The CDP traffic statistics for this node";
          uses CDP-STATS;
        }

        container interfaces {
          description
            "The table of interfaces on which CDP is
            running on this node";

          list interface {
            key "interface-name";
            description
              "Operational data for an interface on which
              CDP is running";
            leaf interface-name {
              type xr:Interface-name;
              description "The interface name";
            }
            uses CDP-INTERFACE;
          }
        }
        leaf node-name {
          type xr:Node-id;
          description "The identifier for the node";
        }
      }
    }
  }
}
