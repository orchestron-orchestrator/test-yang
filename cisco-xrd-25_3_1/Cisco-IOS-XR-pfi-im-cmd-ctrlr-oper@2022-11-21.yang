module Cisco-IOS-XR-pfi-im-cmd-ctrlr-oper {

  /*** NAMESPACE / PREFIX DEFINITION ***/

  namespace "http://cisco.com/ns/yang"+
    "/Cisco-IOS-XR-pfi-im-cmd-ctrlr-oper";


  prefix "pfi-im-cmd-ctrlr-oper";

  /*** LINKAGE (IMPORTS / INCLUDES) ***/

  import cisco-semver { prefix "semver"; }

  include Cisco-IOS-XR-pfi-im-cmd-ctrlr-oper-sub1 {
    revision-date 2022-11-21;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR pfi-im-cmd-ctrlr package operational data.

     This module contains definitions
     for the following management objects:
       controllers: Controller operational data

     Copyright (c) 2013-2022 by Cisco Systems, Inc.
     All rights reserved.";

  revision "2022-11-21" {
    description
      "Updated the model for correct key type
       2022-07-25
         Updated container names to remove duplicate nested containers
       2022-05-05
         Updated key name and description";
    semver:module-version "2.0.0";
  }

  revision "2019-04-05" {
    description
      "Establish semantic version baseline.";
    semver:module-version "1.0.1";
  }

  revision "2015-11-09" {
    description
      "IOS XR 6.0 revision.";
  }

  container controllers {
    config false;
    description "Controller operational data";

    container controller-details {
      description "Descriptions for controllers";

      list controller-detail {
        key "controller-name";
        description "Description for a particular controller";
        leaf controller-name {
          type string;
          description "The name of the controller";
        }
        uses IM-CTRLR-DESC-INFO;
      }
    }
  }
}
