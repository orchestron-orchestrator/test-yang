submodule Cisco-IOS-XR-mpls-ldp-oper-sub3 {

  belongs-to Cisco-IOS-XR-mpls-ldp-oper {
    prefix Cisco-IOS-XR-mpls-ldp-oper;
  }

  /*** LINKAGE (IMPORTS / INCLUDES) ***/

  import cisco-semver { prefix "semver"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR mpls-ldp package operational data.

     Copyright (c) 2013-2023 by Cisco Systems, Inc.
     All rights reserved.";

  revision "2023-12-12" {
    description
      "Added new ldp forwarding filter for all unlabelled next hops
       2023-09-22
         Added new field for ldp parameters indicating support of nhid
       2023-02-17
         Added interface Auto Configure TE Tunnels parameters.
       2021-12-20
         Added new path for cloned tunnels
       2021-09-20
         Added keys for nbr-br-af-info";
    semver:module-version "2.0.0";
  }

  revision "2021-04-06" {
    description
      "Added BSID data in LDP forwarding";
    semver:module-version "1.1.0";
  }

  revision "2019-04-05" {
    description
      "Establish semantic version baseline.";
    semver:module-version "1.0.0";
  }

  revision "2017-09-07" {
    description
      "Fixed type translation error.";
  }

  revision "2017-05-01" {
    description
      "Fixing backward compatibility error in module.";
  }

  revision "2015-11-09" {
    description
      "IOS XR 6.0 revision.";
  }

  grouping LDP-NSR-GBL-SYNCI-INFO {
    description "MPLS LDP NSR Global Init Sync Information";
    leaf nsr-cfged {
      type boolean;
      description "TRUE if NSR configured";
    }
    leaf nsr-synced {
      type boolean;
      description "TRUE if NSR synced";
    }
    leaf init-sync-start {
      type uint32;
      description "Init Sync Start Time";
    }
    leaf init-sync-end {
      type uint32;
      description "Init Sync End Time";
    }
    leaf num-peers {
      type uint32;
      description "Number of Peers";
    }
    leaf num-cap-sent {
      type uint32;
      description "Number of Sent Capabilities objects";
    }
    leaf num-cap-rcvd {
      type uint32;
      description "Number of Rcvd Capabilities objects";
    }
    leaf num-pfx {
      type uint32;
      description "Number of binding prefixes";
    }
    leaf num-lbl {
      type uint32;
      description "Number of label bindings";
    }
    leaf num-lcl-addr-wd {
      type uint32;
      description "Num of lcl address withdraw";
    }
    leaf num-lbl-adv {
      type uint32;
      description "Num of lbl adv";
    }
    leaf ipc-msg-tx-cnt {
      type uint32;
      description "num IPC msgs sent";
    }
    leaf ipc-msg-tx-bytes {
      type uint32;
      units "byte";
      description "total IPC bytes sent";
    }
    leaf ipc-msg-rx-cnt {
      type uint32;
      description "num IPC msgs rxed";
    }
    leaf ipc-msg-rx-bytes {
      type uint32;
      description "num IPC msgs rxed";
    }
    leaf ipc-max-tx-batch-bytes {
      type uint32;
      units "byte";
      description "biggest IPC TX bytes";
    }
    leaf ipc-max-rx-batch-bytes {
      type uint32;
      units "byte";
      description "biggest IPC RX bytes";
    }
    leaf ipc-tx-fail-cnt {
      type uint32;
      description "number of ipc send failures";
    }
    leaf total-ipc-tx-fail-cnt {
      type uint32;
      description "total number of ipc send failures";
    }
    leaf ipc-restart-cnt {
      type uint32;
      description "number of times ipc has been restarted";
    }
    leaf ipc-default-mtu {
      type uint32;
      units "byte";
      description "default IPC MTU bytes";
    }
    leaf ipc-exceeded-mtu-msg-cnt {
      type uint32;
      description "ipc exceeded mtu msg cnt";
    }
    leaf ipc-msg-cnt-evt-q {
      type uint32;
      description
        "pending NSR messages in event queue to async ipc
        thread";
    }
  }

  grouping LDP-NSR-GBL-STATS-INFO {
    description "MPLS LDP NSR Global Stats Information";

    container init-sync {
      description "Init Sync";
      uses LDP-NSR-GBL-SYNCI-INFO;
    }
  }

  grouping LDP-NSR-NBR-SYNCS-INFO {
    description "MPLS LDP NSR Nbr Steady State Sync Information";
    leaf num-cap-sent {
      type uint32;
      description "Num of Sent Capabilities";
    }
    leaf num-cap-rcvd {
      type uint32;
      description "Num of Rcvd Capabilities";
    }
    leaf rem-lbl-wd {
      type uint32;
      description "Number of remote label withdraw events";
    }
    leaf rem-lbl-rq {
      type uint32;
      description "Number of remote label request events";
    }
    leaf num-stdby-adj-join {
      type uint32;
      description "Number of standby adj join";
    }
    leaf num-stdby-adj-leave {
      type uint32;
      description "Number of standby adj leave";
    }
  }

  grouping LDP-NSR-NBR-SYNCI-INFO {
    description "MPLS LDP NSR Nbr Init Sync Information";
    leaf init-sync-start {
      type uint32;
      description "Init Sync Start Time";
    }
    leaf init-sync-end {
      type uint32;
      description "Init Sync End Time";
    }
    leaf num-addr {
      type uint32;
      description "Number of peer addresses";
    }
    leaf num-duplicate-addr {
      type uint32;
      description "Number of duplicate peer addresses";
    }
    leaf num-rx-bytes {
      type uint32;
      units "byte";
      description "Number of unprocessed Rx buffer bytes";
    }
    leaf num-cap-sent {
      type uint32;
      description "Num of Sent Capabilities";
    }
    leaf num-cap-rcvd {
      type uint32;
      description "Num of Rcvd Capabilities";
    }
    leaf num-lbl {
      type uint32;
      description "Number of peer bindings";
    }
    leaf num-app-bytes {
      type uint32;
      units "byte";
      description "Number of external App data bytes";
    }
  }

  grouping LDP-NSR-STATS-NBR-INFO {
    description "MPLS LDP NSR Neighbor Stats Information";

    container init-sync-info {
      description "NSR Init Sync Info";
      uses LDP-NSR-NBR-SYNCI-INFO;
    }

    container steady-state-sync-info {
      description "NSR Steady State Sync Info";
      uses LDP-NSR-NBR-SYNCS-INFO;
    }
    leaf lsr-id-xr {
      type uint32;
      description "lsr id xr";
    }
    leaf lbl-spc-id {
      type uint16;
      description "lbl spc id";
    }
    leaf nsr-sync-state {
      type int32;
      description "nsr sync state";
    }
    leaf num-msg {
      type uint32;
      description "Number of sync messages";
    }
  }
}
