submodule Cisco-IOS-XR-mpls-io-oper-sub1 {

  belongs-to Cisco-IOS-XR-mpls-io-oper {
    prefix Cisco-IOS-XR-mpls-io-oper;
  }

  /*** LINKAGE (IMPORTS / INCLUDES) ***/

  import cisco-semver { prefix "semver"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR mpls-io package operational data.

     Copyright (c) 2013-2019 by Cisco Systems, Inc.
     All rights reserved.";

  revision "2019-04-05" {
    description
      "Establish semantic version baseline.";
    semver:module-version "1.0.1";
  }

  revision "2019-03-21" {
    description
      "IOS XR 7.0.1 revision.";
  }

  revision "2015-11-09" {
    description
      "IOS XR 6.0 revision.";
  }

  grouping MPLS-IO-SHOW-INTF-INFO {
    description "MPLS EA information for a particular Interface";
    leaf mtu {
      type uint32;
      description "MTU for fragmentation";
    }
    leaf bkp-label-stack-depth {
      type uint8;
      description "Interface Backup Label Stack Depth";
    }
    leaf srte-label-stack-depth {
      type uint8;
      description "Interface SR-TE Label Stack Depth";
    }
    leaf pri-label-stack-depth {
      type uint8;
      description "Interface Primary Label Stack Depth";
    }
  }
}
