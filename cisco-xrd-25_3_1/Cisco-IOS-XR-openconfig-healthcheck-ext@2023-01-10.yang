module Cisco-IOS-XR-openconfig-healthcheck-ext {
  namespace "http://cisco.com/ns/yang/Cisco-IOS-XR-openconfig-healthcheck-ext";
  prefix oc-sys-healthcheck-ext;

  import openconfig-system {
    prefix oc-sys;
  }
  import openconfig-extensions {
    prefix oc-ext;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module defines IOS-XR healthcheck configuration and 
     status data.
     
     Copyright (c) 2013-2023 by Cisco Systems, Inc.
     All rights reserved.";
  oc-ext:openconfig-version "0.13.0";

  revision 2023-01-10 {
    description
      "Initial version";
    reference "0.13.0";
  }

  grouping healthcheck-data-config {
    description
      "Healthcheck config data parameters.";

      leaf enable {
        type boolean;
        description "Enable or disable health check.";
      }

      leaf cadence {
        type uint32 {
          range "30..1800";
        }
        description "Healthcheck cadence value in seconds.";
      }
  }
  
  grouping healthcheck-data-state {
    description
      "Healthcheck state/oper data parameters.";
  }
  
  augment "/oc-sys:system" {
    description
      "This augment extends the oc-sys with
       healthcheck data.";

    container healthcheck {
      description
        "Enclosing container for IOS-XR healthcheck configuration and
         status data.";

      container config {
        description "Configuration data for IOS-XR healthcheck.";

        uses healthcheck-data-config;
      }

      container state {
        config false;
        description "Operational state data for IOS-XR healthcheck.";
        
        uses healthcheck-data-config;
        
        uses healthcheck-data-state;
      }
    }
  }
}
