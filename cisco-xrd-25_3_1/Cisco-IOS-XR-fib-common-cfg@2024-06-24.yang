module Cisco-IOS-XR-fib-common-cfg {

  /*** NAMESPACE / PREFIX DEFINITION ***/

  namespace "http://cisco.com/ns/yang/Cisco-IOS-XR-fib-common-cfg";


  prefix "fib-common-cfg";

  /*** LINKAGE (IMPORTS / INCLUDES) ***/

  import cisco-semver { prefix "semver"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR fib-common package configuration.

     This module contains definitions
     for the following management objects:
       fib: CEF configuration

     Copyright (c) 2013-2024 by Cisco Systems, Inc.
     All rights reserved.";

  revision "2024-06-24" {
    description
      "Added cef bcdl route-prioritization mode config
       2024-04-03
         Removed unsupported input values for cef load-balancing oor configuration
       2024-02-03
         Added cef load-balancing oor mode configuration
       2023-04-26
         Added cef SRv6 VPWS over BGP unipath configuration
       2023-01-27
         Added prefix accounting support with SRv6 configuration
       2021-09-28
         Added cef hierarchical-load-balancing configuration
       2021-09-14
         Leaf frr-follow-bgp is removed due to deprecation";
    semver:module-version "2.0.0";
  }

  revision "2021-07-09" {
    description
      "Added PI FIB Telemetry Hopeless Retry and OOR";
    semver:module-version "1.1.0";
  }

  revision "2020-07-23" {
    description
      "obsolete frr-follow-bgp-pic
      2020-07-21
           Added Support for Proactive ARP and ND";
    semver:module-version "1.1.0";
  }

  revision "2019-04-05" {
    description
      "Establish semantic version baseline.";
    semver:module-version "1.0.0";
  }

  revision "2017-05-01" {
    description
      "Fixing backward compatibility error in module.";
  }

  revision "2017-01-20" {
    description
      "IOS XR 6.2.1 revision";
  }

  revision "2015-11-09" {
    description
      "IOS XR 6.0 revision.";
  }

  typedef Fib-lb-level {
    type enumeration {
      enum recursive {
        value 1;
        description "LB level type recursive";
      }
    }
    description "Fib lb level";
  }
  typedef Fib-oor-mode {
    type enumeration {
      enum dampen-and-dlb {
        value 1;
        description "LB OOR Mode DAM_DLB";
      }
    }
    description "Fib oor mode";
  }
  typedef Fib-route-prioritization-mode {
    type enumeration {
      enum cross-afi {
        value 2;
        description "Cross Address-Family view and prioritization";
      }
    }
    description "Fib route prioritization mode";
  }
  typedef Fib-hlb-mode {
    type enumeration {
      enum ecmp {
        value 1;
        description "HLB Mode ECMP";
      }
      enum ucmp {
        value 2;
        description "HLB Mode UCMP";
      }
    }
    description "Fib hlb mode";
  }
  typedef Fib-pbts-forward-class {
    type union {
      type enumeration {
        enum any {
          value 8;
          description "Any class";
        }
      }
      type uint32 {
        range "0..8";
      }
    }
    description "Fib pbts forward class";
  }
  typedef Fib-pbts-fallback {
    type enumeration {
      enum list {
        value 1;
        description "Fallback to class number list";
      }
      enum any {
        value 2;
        description "Fallback to any class";
      }
      enum drop {
        value 3;
        description "Fallback to drop";
      }
    }
    description "Fib pbts fallback";
  }

  container fib {
    description "CEF configuration";

    container pbts-forward-class-fallbacks {
      description "PBTS class configuration";

      list pbts-forward-class-fallback {
        key "forward-class-number";
        description "Set PBTS class for fallback";
        leaf forward-class-number {
          type Fib-pbts-forward-class;
          description "PBTS forward class number";
        }
        leaf fallback-type {
          type Fib-pbts-fallback;
          mandatory true;
          description "Set PBTS fallback type";
        }
        leaf-list fallback-class-number-array {
          type uint32 {
            range "0..7";
          }
          max-elements "7";
          description "Set PBTS fallback class number array";
        }
      }
    }

    container platform {
      description "FIB platform parameters";

      container label-switched-multicast {
        description
          "Options for label-switched-multicast parameters";
        leaf frr-holdtime {
          type uint32 {
            range "3..180";
          }
          units "second";
          description
            "Set time to keep FRR slots programmed post FRR";
        }
      }
    }

    container bcdl {
      description "BCDL configuration";

      container route-prioritization {
        description "BCDLv2 Route-Prioritization configuration";
        leaf mode {
          type Fib-route-prioritization-mode;
          description
            "Specify mode for prioritizing route downloads
            and processing";
        }
      }
    }

    container load-balancing {
      description "Load Balancing OOR";

      container mode-hierarchical {
        presence "Indicates a mode-hierarchical node is configured.";
        description "Hierarchical Load Balancing mode";
        leaf hlb-mode {
          type Fib-hlb-mode;
          mandatory true;
          description "HLB Mode";
        }
        leaf hlb-num-paths {
          type uint32 {
            range "1..128";
          }
          mandatory true;
          description "HLB NumPaths";
        }
      }

      container oor-mode {
        presence "Indicates a oor-mode node is configured.";
        description "Recursive OOR mode";
        leaf lb-lvl-type {
          type Fib-lb-level;
          mandatory true;
          description "Load balance level type";
        }
        leaf oor-mode {
          type Fib-oor-mode;
          mandatory true;
          description "LBOOR Mode";
        }
        leaf rsrc-threshold-dampening {
          type uint32 {
            range "1..99";
          }
          mandatory true;
          description "Dampening Resource Threshold";
        }
        leaf max-duration-dampening {
          type uint32 {
            range "1..600";
          }
          mandatory true;
          description "Dampen Max Duration";
        }
        leaf rsrc-threshold-dlb {
          type uint32 {
            range "1..99";
          }
          mandatory true;
          description "DLB Resource threshold";
        }
      }
    }

    container hierarchical-loadbalancing {
      presence "Indicates a hierarchical-loadbalancing node is"+
        " configured.";
      description "Hierarchical Load Balancing";
      leaf hlb-mode {
        type Fib-hlb-mode;
        mandatory true;
        description "HLB Mode";
      }
      leaf hlb-num-paths {
        type uint32 {
          range "1..128";
        }
        mandatory true;
        description "HLB NumPaths";
      }
    }
    leaf auto-hash-recover {
      type boolean;
      description
        "Set option for automatcially recovering
        consistent-hashing state on interface up";
    }
    leaf prefer-aib-routes {
      type boolean;
      description
        "Set options for adjacency routes overriding RIB
        routes";
    }
    leaf proactive-arp-nd {
      type empty;
      description "Enable Proactive ARP and ND";
    }
    leaf encap-sharing-disable {
      type boolean;
      description "Set true to disable encapsulation sharing";
    }
    leaf srv6-vpws-over-bgp-unipath-xport {
      type empty;
      description
        "Enable Segment-routing SRv6 VPWS service support
        over BGP unipath transport";
    }
  }
}
