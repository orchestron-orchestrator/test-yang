submodule Cisco-IOS-XR-gil-ma-oper-sub1 {

  belongs-to Cisco-IOS-XR-gil-ma-oper {
    prefix Cisco-IOS-XR-gil-ma-oper;
  }

  /*** LINKAGE (IMPORTS / INCLUDES) ***/

  import cisco-semver { prefix "semver"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR gil-ma package operational data.

     Copyright (c) 2013-2023 by Cisco Systems, Inc.
     All rights reserved.";

  revision "2023-03-09" {
    description
      "Initial GIL MA Support";
    semver:module-version "1.0.0";
  }

  revision "2019-04-05" {
    description
      "Establish semantic version baseline.";
  }

  revision "2015-11-09" {
    description
      "IOS XR 6.0 revision.";
  }

  typedef Im-state {
    type uint32;
    description "Im state";
  }

  grouping GIL-TIMER-STATS {
    description "GIL timer statistics";
    leaf expiry-count {
      type uint32;
      description "Number of times it expired";
    }
    leaf start-count {
      type uint32;
      description "Number of times it was started";
    }
    leaf stop-count {
      type uint32;
      description "Number of times it was stopped";
    }
  }

  grouping GIL-TIMER {
    description "GIL timer";

    container stats {
      description "Statistics";
      uses GIL-TIMER-STATS;
    }
    leaf delay-ms {
      type uint32;
      units "millisecond";
      description "Timer delay in Milliseconds";
    }
    leaf remaining-ms {
      type uint32;
      units "millisecond";
      description "Amount of time remaining in Milliseconds";
    }
    leaf running {
      type boolean;
      description "Is the timer currently running";
    }
  }

  grouping GIL-MA-IDB-INTF {
    description "Member interface of the GIL";
    leaf member-interface-name {
      type string;
      description "Configured interface name";
    }
  }

  grouping GIL-MA-IDB-CONTENT {
    description "GIL IDB content";

    container retry-timer {
      description "Retry timer";
      uses GIL-TIMER;
    }
    leaf idb-im-state {
      type Im-state;
      description "IM state of the IDB";
    }

    list member-interface {
      description "Member interfaces";
      uses GIL-MA-IDB-INTF;
    }
  }

  grouping GIL-MA-IDB-KEY {
    description "GIL IDB key";
    leaf gil-name {
      type string;
      description "generic-interface-list name";
    }
  }

  grouping GIL-MA-IDB {
    description "Generic Interface List IDB";

    container key {
      description "GIL IDB key";
      uses GIL-MA-IDB-KEY;
    }

    container content {
      description "GIL IDB content";
      uses GIL-MA-IDB-CONTENT;
    }
  }

  grouping GIL-MA-PORT-CONTENT {
    description "GIL PORT content";
    leaf port-im-state {
      type Im-state;
      description "IM state of the PORT";
    }
  }

  grouping GIL-MA-PORT-KEY {
    description "GIL PORT key";
    leaf port-name {
      type string;
      description "Interface name of the PORT";
    }
  }

  grouping GIL-MA-PORT {
    description "GIL PORT";

    container key {
      description "GIL PORT key";
      uses GIL-MA-PORT-KEY;
    }

    container content {
      description "GIL PORT content";
      uses GIL-MA-PORT-CONTENT;
    }
  }

  grouping GIL-MA-PDCAP {
    description "Generic Interface List System Capabilities";
    leaf max-gil-limit {
      type uint32;
      description "Max # of GILs supported";
    }
    leaf max-interfaces-per-gil {
      type uint32;
      description "Max # of interfaces per GIL";
    }
    leaf max-bundles-per-gil {
      type uint32;
      description "Max # of bundles per GIL";
    }
    leaf capability-library-return-code {
      type uint32;
      description "Capability Library Return Code";
    }
  }
}
