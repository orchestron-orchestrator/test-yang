submodule Cisco-IOS-XR-infra-xtc-oper-sub1 {

  belongs-to Cisco-IOS-XR-infra-xtc-oper {
    prefix Cisco-IOS-XR-infra-xtc-oper;
  }

  /*** LINKAGE (IMPORTS / INCLUDES) ***/

  import ietf-inet-types { prefix "inet"; }

  import cisco-semver { prefix "semver"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR infra-xtc package operational data.

     Copyright (c) 2013-2025 by Cisco Systems, Inc.
     All rights reserved.";

  revision "2025-06-09" {
    description
      "Extended topology summary statistics to include virtual nodes and links and to specify more detailed statistics for prefixes
       2024-11-25
         Added PCE override for blocking PCEP objects
       2024-11-21
         drop-upon-invalidation leaf added under pce/pce-lsp-data/tunnel-detail-infos/tunnel-detail-info/detail-lsp-information
       2024-09-25
         Changed the GRPC protocol origin id value
       2024-09-15
         Added bandwidth leaf under candidate path segment list to store allocated bandwidth value
       2024-08-01
         Modified name of metric type value to include IANA
       2024-06-11
         Added grpc service-instance list
       2024-04-22
         Added Candidate Path and Instance in TreeSID
       2024-03-18
         Added SRv6 MSD list to peer PCEP info
       2024-03-01
         Added Cleanup Timer in TreeSID
       2023-11-30
         Added CommonTopologyTable
       2023-10-12
         Added fields for path-type of a policy and candidate path
       2023-08-08
         Extended SR-MPLS CSPF computation oper command with exclude IP constraint for both paths as well as affinities constraint for second path. Extended LSP display to show received XRO values, as well as added indication of shortest-path flag in disjoint constraints.
       2023-07-26
         Added protection type to BWoD sub-delegation.
       2023-07-04
         Add CPATH Name to cmn bag to display it using show pce lsp private command.
       2023-06-20
         Display override rule override for SID protection-type constraint.
       2023-05-04
         Display Flex-Algo information for P2MP policies.
       2023-04-27
         Add override rule override pcep advertise admin down when no path configure.
       2023-04-06
         Add a field to differentiate SRv6 path in path work group
       2023-03-30
         Changed work group operational data to use an ID based system as the key instead of a complex set of attributes.
       2023-03-21
         Added SID-algo in override rule
       2023-03-09
         Added protection type for path work group
       2023-03-06
         Updated PM CPath info and PM Stats bag
       2023-02-27
         Added fields to differentiate IPV4 or IPV6 TREESID policies
       2023-01-24
         Added fields for Flex-algo ASLA attributes on IPv4 and IPv6 links
       2023-01-18
         Updated description of flex-algo leaf to SID algorithm in cspf-sr-mpls.
       2022-11-11
         Added distribute-ls policy operational data.
       2022-10-20
         Added initiated tunnel operational information including PCE-INITIATED-TUN-BAG grouping.
       2022-09-01
         Added field to display p2mp rest initiated treeSID.
       2022-07-29
         changed default value of initial-verify-startup timer from 120 seconds to 180 seconds.
       2022-07-11
         Added leaves for blocked reoptimization and adjacency SID only
       2022-06-28
         Added weight outputs to srv6 nexthop and lsp sls.
       2022-06-02
         Removed prefix-metric entry from the topology node.
       2022-05-13
         TreeSID PCE HA, added few fields on oper commands
       2022-04-29
         Added some field in oper bag for Dynamic CS policies
       2022-04-26
         TreeSID PCE HA, oper enhancements
       2022-03-09
         Pce-sr-sid enum updated to add unknown-srv6sid element
       2022-03-03
         Modified description for override rules related leaves
       2022-03-03
         Added capability-srv6 in brief-pcep-information container
       2022-02-24
         Added PCE-BWOD-BEST-CLIENT-BAG and PCE-BWOD-SUB-DELEGATION-BAG grouping.
       2022-01-28
         Added maximum-delay in PCE-LSP-DETAIL-INFO grouping.
       2022-01-27
         Adding performance-statistics class
       2022-01-17
         Change the type of extended-value leaf from leaf-list to list.
       2022-01-14
         Added support for metric bounds for CSPF
       2022-01-10
         Added sid-algorithm and sid-algorithm-set in PCE-SIBLING-SYNCED-LSP-BAG grouping. Added sid-algorithm and sid-algorithm-set in PCE-LSP-DETAIL-INFO grouping.
       2022-01-07
         Added SID algorithm constraint to LSP.
       2021-12-14
         Moving algorithm and computation time in the path query results object
       2021-11-21
         Added prefix-metric entry in the topology node.
       2021-11-09
         Added unreliable flag and update drop count in topology summary bag.
       2021-10-21
         Adding algorithm and computation time to path query results
       2021-10-08
         Added support for override rules";
    semver:module-version "5.0.0";
  }

  revision "2021-09-28" {
    description
      "Added protection type set in candidate path constraints.
      2021-08-27
          Added binding-sid to pce sibling synced lsp.
      2021-06-21
          un-hide cspf-srv6 option in cspf srv6 path calculation.
      2021-05-26
          Added keys to topology-summary list.";
    semver:module-version "4.0.0";
  }

  revision "2021-04-22" {
    description
      "Added TE metric field for Flex-algo ASLA.
      2021-04-08
           Change protection type from integer to enum.
      2021-03-31
           Added new enumeration Api-peer-stats-info-oper. Changed type of type in API-PEER-STATS-INFO to use Api-peer-stats-info-oper. This is a non backward compatible change.
      2021-03-04
           Added MSD list per topology link. Added SRLB list per topology node.
      2021-01-29
           Updated SRv6 Endpoint function from int to enum.
      2020-09-16
           Adding operational nodes for new features path invalidation drop protected and unprotected path Operational nodes for PCE segment-routing traffic-eng policy
      2020-09-01
           Added uB6SID field in the LSP object
      2020-08-18
           Added SRv6 LSP details fields in the LSP object
      2020-07-13
           Added NodeID fields in the uN SID object in the IPv6 topology.
      2020-04-20
           Added fields in the PCE IPv6 link object.";
    semver:module-version "3.0.0";
  }

  revision "2020-03-17" {
    description
      "Add flex-algo related operational nodes. Updated description of statistics-nodes. Add SR-PAG related operational nodes. Add PCE authentication related operational nodes.
      2020-02-03
         Added TCP AuthenticationOption related operational model. Implemented show pce authentication. Added classes AuthenticationKeyTable and AuthenticationKey.
      2019-11-07
         Adding leaf preference, leaf interface-name, and leaf profile-id to support a new HTTP API bindpoint for sibling PCEs.
      2019-10-09
         Adding enum sr-flex-algo-prefix-sid, enum pce-cspf-flex-algo-definition-mistmatch, leaf flex-algo-prefix-sids, list sr-flex-algo, and container flex-algos to support Flex-algo info.";
    semver:module-version "2.0.0";
  }

  revision "2019-10-02" {
    description
      "Added REST peer statistic information.
      2019-09-27
         Implement new show pce lsp and show pce initiated tunnels commands for Optima";
    semver:module-version "1.1.0";
  }

  revision "2019-04-05" {
    description
      "Establish semantic version baseline.";
    semver:module-version "1.0.0";
  }

  revision "2017-09-07" {
    description
      "Fixed type translation error.";
  }

  revision "2017-08-24" {
    description
      "Added C flag to pcep flags.";
  }

  revision "2017-06-26" {
    description
      "Change identifiers to be more readable.";
  }

  revision "2017-05-01" {
    description
      "Fixing backward compatibility error in module.";
  }

  revision "2016-05-31" {
    description
      "Revision description string.";
  }

  revision "2015-11-09" {
    description
      "IOS XR 6.0 revision.";
  }

  typedef Nbapi-peer-state {
    type enumeration {
      enum api-peer-state-down {
        value 0;
        description "Operational status down";
      }
      enum api-peer-state-up {
        value 1;
        description "Operational status up";
      }
    }
    description "Nbapi peer state";
  }
  typedef Api-peer-stats-info-oper {
    type enumeration {
      enum api-operation-invalid {
        value 0;
        description "Invalid operation";
      }
      enum api-operation-lsp-create {
        value 1;
        description "LSP create";
      }
      enum api-operation-lsp-reclaim-delegation {
        value 2;
        description "LSP reclaim delegation";
      }
      enum api-operation-lsp-drop-delegation {
        value 3;
        description "LSP drop delegation";
      }
      enum api-operation-lsp-update {
        value 4;
        description "LSP update";
      }
      enum api-operation-lsp-delete {
        value 5;
        description "LSP delete";
      }
      enum api-operation-lsp-delete-all {
        value 6;
        description "LSP delete all";
      }
      enum api-operation-lsp-computation {
        value 7;
        description "LSP compute";
      }
      enum api-operation-lsp-subscription {
        value 8;
        description "LSP subscrube";
      }
      enum api-operation-topology-subscription {
        value 9;
        description "Topology subscribe";
      }
      enum api-operation-topology-subscriptionv2 {
        value 10;
        description "Topology subscribe version 2";
      }
      enum api-operation-peer-subscription {
        value 11;
        description "Peer subscribe";
      }
      enum api-operation-bwod-subscription {
        value 12;
        description "BWoD subscribe";
      }
      enum api-operation-p2mp-install {
        value 13;
        description "P2MP install";
      }
      enum api-operation-p2mp-delete {
        value 14;
        description "P2MP delete";
      }
      enum api-operation-p2mp-delete-all {
        value 15;
        description "P2MP delete all";
      }
      enum api-operation-p2mp-reoptimization {
        value 16;
        description "P2MP reoptimization";
      }
      enum api-operation-p2mp-get-information {
        value 17;
        description "P2MP get information";
      }
      enum api-operation-p2mp-subscription {
        value 18;
        description "P2MP subscribe";
      }
      enum api-operation-external-lsp {
        value 19;
        description "External LSP";
      }
      enum api-operation-topology-link-attribute {
        value 20;
        description "Topology link attribute update";
      }
      enum api-operationversion {
        value 21;
        description "API version";
      }
      enum api-operation-maximum {
        value 22;
        description "Maximum value";
      }
    }
    description "Api peer stats info oper";
  }
  typedef Pce-headend-swap {
    type enumeration {
      enum pcehs-none {
        description "Headends not swapped";
      }
      enum pcehs-plain {
        description "Headends swapped";
      }
      enum pcehs-rwi {
        description "Headends swapped with increment";
      }
    }
    description "PCE Headends Swap Code";
  }
  typedef Path-work-node {
    type enumeration {
      enum path-work-bag-node-type-work {
        value 0;
        description "work";
      }
      enum path-work-bag-node-type-worker-prio-1 {
        value 1;
        description "reoptimization worker";
      }
      enum path-work-bag-node-type-region {
        value 2;
        description "region";
      }
    }
    description "Path work node type";
  }
  typedef Pce-treesid-role {
    type enumeration {
      enum none {
        description "No role";
      }
      enum ingress {
        description "Ingress";
      }
      enum transit {
        description "Transit";
      }
      enum egress {
        description "Egress";
      }
      enum bud-node {
        description "Bud Node";
      }
    }
    description "Pce treesid role";
  }
  typedef Pce-treesid-prog-phase {
    type enumeration {
      enum none {
        description "No state";
      }
      enum programming {
        description "Programming non-root nodes";
      }
      enum programming-root {
        description "Programming the root node";
      }
      enum pruning {
        description "Pruning stale legs on non-root nodes";
      }
      enum pruning-root {
        description "Pruning stale legs on root node";
      }
      enum deleting {
        description "TreeSID is being deleted";
      }
    }
    description "Pce treesid prog phase";
  }
  typedef Pce-treesid-cpath-origin {
    type enumeration {
      enum unknown {
        description "Unknown";
      }
      enum config {
        description "Config initiated";
      }
      enum pcc-init {
        description "PCC Initiated";
      }
      enum rest-init {
        description "REST initiated";
      }
    }
    description "Pce treesid cpath origin";
  }
  typedef Cmn-protection {
    type enumeration {
      enum cmn-protection-type-protected-preferred {
        description "Protected Preferred";
      }
      enum cmn-protection-type-unprotected-only {
        description "Unprotected Only";
      }
      enum cmn-protection-type-protected-only {
        description "Protected Only";
      }
      enum cmn-protection-type-unprotected-preferred {
        description "Unprotected Preferred";
      }
    }
    description "Cmn protection";
  }
  typedef Sr-computation-algorithm {
    type enumeration {
      enum computation-sr-native {
        description "SR Native";
      }
      enum computation-igp {
        description "SR IGP";
      }
      enum computation-dijkstra {
        description "Dijkstra";
      }
      enum computation-k-shortest {
        description "K shortest";
      }
      enum computation-flex-algo {
        description "Flex Algo";
      }
      enum computation-suurballe {
        description "Suurballe";
      }
      enum computation-bellman-ford {
        description "Bellman Ford";
      }
      enum computation-rsvp {
        description "RSVP Computation";
      }
    }
    description "Path Computation Algorithm";
  }
  typedef Pce-cspf-rc {
    type enumeration {
      enum pce-cspf-not-set {
        description "Not set";
      }
      enum pce-cspf-src-not-found {
        description "Source not found";
      }
      enum pce-cspf-dst-not-found {
        description "Destination not found";
      }
      enum pce-cspf-second-src-not-found {
        description "Second source not found";
      }
      enum pce-cspf-second-dst-not-found {
        description "Second destination not found";
      }
      enum pce-cspf-no-mem {
        description "No memory";
      }
      enum pce-cspf-ex-path-not-resolved {
        description "Second path not resolved";
      }
      enum pce-cspf-no-path {
        description "No path";
      }
      enum pce-cspf-sp-success {
        description "Shortest path success";
      }
      enum pce-cspf-error {
        description "Error";
      }
      enum pce-cspf-fallback-srlg-node-node {
        description "Fallback from SRLG-NODE to NODE";
      }
      enum pce-cspf-fallback-srlg-node-link {
        description "Fallback from SRLG-NODE to LINK";
      }
      enum pce-cspf-fallback-srlg-node-sp {
        description "Fallback from SRLG-NODE to SP";
      }
      enum pce-cspf-fallback-node-link {
        description "Fallback from NODE to LINK";
      }
      enum pce-cspf-fallback-link-sp {
        description "Fallback from LINK to SP";
      }
      enum pce-cspf-fallback-node-sp {
        description "Fallback from NODE to SP";
      }
      enum pce-cspf-fallback-srlg-link {
        description "Fallback from SRLG to LINK";
      }
      enum pce-cspf-fallback-srlg-sp {
        description "Fallback from SRLG to SP";
      }
      enum pce-cspf-dp-success {
        description "Disjoint path success";
      }
      enum pce-cspf-flex-algo-definition-mistmatch {
        description
          "Flex-algo definition mistmatch across IGP
          domain";
      }
      enum pce-cspf-latency-bound-exceeded {
        description "Latency bound exceeded for computed path";
      }
      enum pce-cspf-flex-algo-unsupported {
        description "Flex-algo based path computation unsupported";
      }
      enum pce-cspf-sid-algorithm-argument-invalid {
        description "SID algorithm number is invalid";
      }
      enum pce-cspf-flex-algo-definition-unsupported {
        description "Flex-algo definition unsupported";
      }
      enum pce-cspf-flex-algo-definition-not-found {
        description "Flex-algo definition not found";
      }
      enum pce-cspf-msd-exceeded {
        description "MSD exceeded for computed path";
      }
      enum pce-cspf-constraints-unsupported {
        description "Combination of constraints is unsupported";
      }
      enum pce-cspf-same-source-destination {
        description "Source and destination are the same node";
      }
      enum pce-cspf-exclude-ip-limit-reached {
        description "Number of exclude IPs limit reached";
      }
    }
    description "PCE CSPF Result Code";
  }
  typedef Topo-ls-link-asla-app {
    type enumeration {
      enum none {
        value 0;
        description "None";
      }
      enum rsvp-te {
        value 1;
        description "RSVP TE";
      }
      enum sr {
        value 2;
        description "Segment Routing";
      }
      enum lfa {
        value 3;
        description "LFA";
      }
      enum fa {
        value 4;
        description "Flex algo";
      }
      enum all-apps {
        value 255;
        description "All apps";
      }
    }
    description "Topo ls link asla app";
  }
  typedef Topo-ls-link-metric {
    type enumeration {
      enum unknown {
        value 0;
        description "Unknown";
      }
      enum igp {
        value 1;
        description "IGP metric";
      }
      enum te {
        value 2;
        description "TE metric";
      }
      enum latency {
        value 3;
        description "Latency (delay) metric";
      }
    }
    description "Topo ls link metric";
  }
  typedef Topo-sid {
    type enumeration {
      enum none {
        value 0;
        description "No type";
      }
      enum adjacency {
        value 1;
        description "Adjacency SID";
      }
      enum bgp-epe {
        value 2;
        description "BGP EPE SID";
      }
      enum regular {
        value 3;
        description "Regular SID";
      }
      enum strict {
        value 4;
        description "Strict SID";
      }
      enum fa {
        value 5;
        description "Flex algo SID";
      }
    }
    description "Topo sid";
  }
  typedef Topo-ls-node-id-proto {
    type enumeration {
      enum unknown {
        value 0;
        description "Unknown";
      }
      enum ospf {
        value 1;
        description "OSPF";
      }
      enum isis {
        value 2;
        description "ISIS";
      }
      enum bgp {
        value 3;
        description "BGP";
      }
    }
    description "Topo ls node id proto";
  }
  typedef Cmn-ha-case {
    type enumeration {
      enum ha-case-migration {
        description "HA Case Migration";
      }
      enum ha-case-restart {
        description "HA Case Restart";
      }
      enum ha-case-switchover {
        description "HA Case Switchover";
      }
      enum ha-case-startup {
        description "HA Case Startup";
      }
      enum ha-case-invalid {
        description "HA Case Invalid";
      }
    }
    description "Various HA cases";
  }
  typedef Sid {
    type enumeration {
      enum sr-protected-adj-sid {
        value 1;
        description "Protected Adjacency SID";
      }
      enum sr-unprotected-adj-sid {
        value 2;
        description "Unprotected Adjacency SID";
      }
      enum sr-bgp-egress-peer-engineering-sid {
        value 3;
        description "BGP egress peer engineering SID";
      }
      enum sr-reqular-prefix-sid {
        value 4;
        description "Regular prefix SID";
      }
      enum sr-strict-prefix-sid {
        value 5;
        description "Strict prefix SID";
      }
      enum sr-flex-algo-prefix-sid {
        value 6;
        description "Flex-algo prefix SID";
      }
    }
    description "SID Types";
  }
  typedef Cmn-metric {
    type enumeration {
      enum metric-type-none {
        value 0;
        description "Metric Type None";
      }
      enum metric-type-igp {
        value 1;
        description "Metric Type IGP";
      }
      enum metric-type-te {
        value 2;
        description "Metric Type TE";
      }
      enum metric-type-hop-count {
        value 3;
        description "Metric Type hop count";
      }
      enum metric-type-msd {
        value 11;
        description "Metric Type MSD";
      }
      enum metric-type-latency {
        value 12;
        description "Metric Type latency";
      }
      enum metric-type-bandwidth {
        value 24;
        description "Metric Type bandwidth";
      }
    }
    description "PCE Metric Type";
  }
  typedef Pce-igp-info-id {
    type enumeration {
      enum isis {
        value 1;
        description "ISIS";
      }
      enum ospf {
        value 2;
        description "OSPF";
      }
      enum bgp {
        value 3;
        description "BGP";
      }
    }
    description "IGP IDs";
  }
  typedef Topo-msd-subtype {
    type enumeration {
      enum msd-type-mpls {
        value 1;
        description "Base MPLS Imposition MSD";
      }
      enum msd-type-erld {
        value 2;
        description "ERLD MSD";
      }
      enum msd-type-srh-max-sl {
        value 41;
        description "SRH Max SL";
      }
      enum msd-type-srh-max-end-pop {
        value 42;
        description "SRH Max End Pop";
      }
      enum msd-type-srh-max-h-encaps {
        value 44;
        description "SRH Max H.encaps";
      }
      enum msd-type-srh-max-end-d {
        value 45;
        description "SRH Max End D";
      }
      enum msd-type-unknown {
        value 255;
        description "Unknown";
      }
    }
    description "Topo msd subtype";
  }
  typedef Cmn-auth {
    type enumeration {
      enum none {
        description "None";
      }
      enum md5-clear {
        description "MD5 Clear";
      }
      enum md5-encrypted {
        description "MD5 Encrypted";
      }
      enum authentication-option {
        description "Authentication Option";
      }
      enum authentication-keychain {
        description "Authentication Keychain";
      }
      enum max {
        description "Max";
      }
    }
    description "Cmn auth";
  }
  typedef Pcep-state {
    type enumeration {
      enum tcp-close {
        description "TCP close";
      }
      enum tcp-listen {
        description "TCP listen";
      }
      enum tcp-connect {
        description "TCP connect";
      }
      enum pcep-closed {
        description "PCEP closed";
      }
      enum pcep-opening {
        description "PCEP opening";
      }
      enum pcep-open {
        description "PCEP open";
      }
    }
    description "PCEP State";
  }
  typedef Pce-proto {
    type enumeration {
      enum pcep {
        description "PCE protocol";
      }
      enum netconf {
        description "Netconf protocol";
      }
    }
    description "PCE peer protocol";
  }
  typedef Pce-lsp-exclude-resource {
    type enumeration {
      enum resource-interface {
        description "Interface";
      }
      enum resource-node {
        description "Node";
      }
      enum resource-srlg {
        description "SRLG";
      }
    }
    description "PCE LSP exclude resource type";
  }
  typedef Xtc-ipv6-address {
    type inet:ipv6-address;
    description "Xtc ipv6 address";
  }
  typedef Xtc-ipv4-address {
    type inet:ipv4-address;
    description "Xtc ipv4 address";
  }
  typedef Xtc-af-id {
    type enumeration {
      enum none {
        value 0;
        description "None";
      }
      enum ipv4 {
        value 1;
        description "IPv4";
      }
      enum ipv6 {
        value 2;
        description "IPv6";
      }
    }
    description "Xtc af id";
  }
  typedef Pce-rro {
    type enumeration {
      enum rro-type-ipv4-address {
        description "IPv4 Address";
      }
      enum rro-type-mpls-label {
        description "MPLS Label";
      }
      enum rro-type-sripv4-node-sid {
        description "Segment Routing IPv4 Node SID";
      }
      enum rro-type-sripv4-adjacency-sid {
        description "Segment Routing IPv4 Adjacency SID";
      }
      enum rro-type-sr-nai-null {
        description "Segment Routing with NAI null";
      }
    }
    description "PCE RRO type";
  }
  typedef Pce-sr-sid {
    type enumeration {
      enum ipv4-node-sid {
        description "IPv4 Node SID";
      }
      enum ipv4-adjacency-sid {
        description "IPv4 Adjacency SID";
      }
      enum ipv6-node-sid {
        description "IPv6 Node SID";
      }
      enum ipv6-adjacency-sid {
        description "IPv6 Adjacency SID";
      }
      enum ipv4-unnumbered-adjacency-sid {
        description "IPv4 unnumbered adjacency segment identifier";
      }
      enum ipv6-linklocal-adjacency-sid {
        description "IPv6 linklocal adjacency segment identifier";
      }
      enum unknown-sid {
        description "Unknown SID";
      }
      enum unknown-srv6sid {
        description "Unknown SRv6 SID";
      }
    }
    description "PCE SR SID type";
  }
  typedef Lsp-state {
    type enumeration {
      enum lsp-down {
        description "LSP is down";
      }
      enum lsp-up {
        description "LSP is up";
      }
    }
    description "LSP setup type";
  }
  typedef Pcep-lsp-state {
    type enumeration {
      enum lsp-down {
        description "LSP is down";
      }
      enum lsp-up {
        description "LSP is up";
      }
      enum lsp-active {
        description "LSP is active (carrying traffic)";
      }
      enum lsp-going-down {
        description "LSP is going down";
      }
      enum lsp-being-signaled {
        description "LSP is being signaled";
      }
    }
    description "PCEP operation protocol";
  }
  typedef Lsp-setup {
    type enumeration {
      enum setup-rsvp {
        description "LSP is established using RSVP-TE";
      }
      enum setup-sr {
        description "LSP is established using SR-TE";
      }
      enum setup-pcecc {
        description "LSP is established using PCECC";
      }
      enum setup-srv6 {
        description "LSP is established using SRv6-TE";
      }
      enum setup-unknown {
        description "Unknown LSP establishment method";
      }
    }
    description "LSP setup type";
  }
  typedef Mgmt-srv6-endpoint {
    type enumeration {
      enum unknown {
        value 0;
        description "Unknown Endpoint type";
      }
      enum end {
        value 1;
        description "End (no PSP/USP)";
      }
      enum end-with-psp {
        value 2;
        description "End with PSP";
      }
      enum end-with-usp {
        value 3;
        description "End with USP";
      }
      enum end-with-psp-usp {
        value 4;
        description "End with PSP/USP";
      }
      enum end-x {
        value 5;
        description "End.X (no PSP/USP)";
      }
      enum end-x-with-psp {
        value 6;
        description "End.X with PSP";
      }
      enum end-x-with-usp {
        value 7;
        description "End.X with USP";
      }
      enum end-x-with-psp-usp {
        value 8;
        description "End.X with PSP/USP";
      }
      enum end-tbl {
        value 9;
        description "End.T (no PSP/USP)";
      }
      enum end-tbl-with-psp {
        value 10;
        description "End.T with PSP";
      }
      enum end-tbl-with-usp {
        value 11;
        description "End.T with USP";
      }
      enum end-tbl-with-psp-usp {
        value 12;
        description "End.T with PSP/USP";
      }
      enum end-b6-insert {
        value 13;
        description "End.B6.Insert";
      }
      enum end-b6-encaps {
        value 14;
        description "End.B6.Encaps";
      }
      enum end-bm {
        value 15;
        description "End.BM";
      }
      enum end-dx6 {
        value 16;
        description "End.DX6";
      }
      enum end-dx4 {
        value 17;
        description "End.DX4";
      }
      enum end-dt6 {
        value 18;
        description "End.DT6";
      }
      enum end-dt4 {
        value 19;
        description "End.DT4";
      }
      enum end-dt46 {
        value 20;
        description "End.DT46";
      }
      enum end-dx2 {
        value 21;
        description "End.DX2";
      }
      enum end-dx2v {
        value 22;
        description "End.DX2V";
      }
      enum end-dt2u {
        value 23;
        description "End.DT2U";
      }
      enum end-dt2m {
        value 24;
        description "End.DT2M";
      }
      enum end-s {
        value 25;
        description "End.S";
      }
      enum end-b6-insert-red {
        value 26;
        description "End.B6.Insert.Reduced";
      }
      enum end-b6-encaps-red {
        value 27;
        description "End.B6.Encaps.Reduced";
      }
      enum end-with-usd {
        value 28;
        description "End with USD";
      }
      enum end-with-psp-usd {
        value 29;
        description "End with PSP/USD";
      }
      enum end-with-usp-usd {
        value 30;
        description "End with USP/USD";
      }
      enum end-with-psp-usp-usd {
        value 31;
        description "End with PSP/USP/USD";
      }
      enum end-x-with-usd {
        value 32;
        description "End.X with USD";
      }
      enum end-x-with-psp-usd {
        value 33;
        description "End.X with PSP/USD";
      }
      enum end-x-with-usp-usd {
        value 34;
        description "End.X with USP/USD";
      }
      enum end-x-with-psp-usp-usd {
        value 35;
        description "End.X with PSP/USP/USD";
      }
      enum end-tbl-with-usd {
        value 36;
        description "End.T with USD";
      }
      enum end-tbl-with-psp-usd {
        value 37;
        description "End.T with PSP/USD";
      }
      enum end-tbl-with-usp-usd {
        value 38;
        description "End.T with USP/USD";
      }
      enum end-tbl-with-psp-usp-usd {
        value 39;
        description "End.T with PSP/USP/USD";
      }
      enum end-op {
        value 40;
        description "End.OP";
      }
      enum end-otp {
        value 41;
        description "End.OTP";
      }
      enum un-shift-only {
        value 42;
        description "uN Shift-only";
      }
      enum un {
        value 43;
        description "uN";
      }
      enum un-psp {
        value 44;
        description "uN with PSP";
      }
      enum un-usp {
        value 45;
        description "uN with USP";
      }
      enum un-psp-usp {
        value 46;
        description "uN with PSP-USP";
      }
      enum un-usd {
        value 47;
        description "uN with USD";
      }
      enum un-psp-usd {
        value 48;
        description "uN with PSP-USD";
      }
      enum un-usp-usd {
        value 49;
        description "uN with USP-USD";
      }
      enum un-psp-usp-usd {
        value 50;
        description "uN with PSP_USP-USD";
      }
      enum ua-shift-only {
        value 51;
        description "uA Shift-only";
      }
      enum ua {
        value 52;
        description "uA";
      }
      enum ua-psp {
        value 53;
        description "uA with PSP";
      }
      enum ua-usp {
        value 54;
        description "uA with USP";
      }
      enum ua-psp-usp {
        value 55;
        description "uA with PSP-USP";
      }
      enum ua-usd {
        value 56;
        description "uA with USD";
      }
      enum ua-psp-usd {
        value 57;
        description "uA with PSP-USD";
      }
      enum ua-usp-usd {
        value 58;
        description "uA with USP-USD";
      }
      enum ua-psp-usp-usd {
        value 59;
        description "uA with PSP_USP-USD";
      }
      enum udx6 {
        value 60;
        description "uDX6";
      }
      enum udx4 {
        value 61;
        description "uDX4";
      }
      enum udt6 {
        value 62;
        description "uDT6";
      }
      enum udt4 {
        value 63;
        description "uDT4";
      }
      enum udt46 {
        value 64;
        description "uDT46";
      }
      enum udx2 {
        value 65;
        description "uDX2";
      }
      enum udx2v {
        value 66;
        description "uDX2V";
      }
      enum udt2u {
        value 67;
        description "uDT2U";
      }
      enum udt2m {
        value 68;
        description "uDT2M";
      }
      enum ub6-insert {
        value 69;
        description "uB6 Insert";
      }
      enum ub6-encaps {
        value 70;
        description "uB6 Encaps";
      }
      enum ub6-insert-red {
        value 71;
        description "uB6 Insert.Red";
      }
      enum ub6-encaps-red {
        value 72;
        description "uB6 Encaps.Red";
      }
      enum ubm {
        value 73;
        description "uBM";
      }
      enum ub6-psp-usd-insert-red {
        value 79;
        description "uB6 with PSP-USD Insert.Red";
      }
      enum ub6-psp-usd-encaps-red {
        value 80;
        description "uB6 with PSP-USD Encaps.Red";
      }
      enum utef {
        value 81;
        description "PT uTEF";
      }
      enum ub6-insert-red-shift-only {
        value 82;
        description "uB6 Insert.Red Shift-only";
      }
    }
    description "SRv6 Endpoint Behavior Type";
  }
  typedef Pce-ipv6-address {
    type inet:ipv6-address;
    description "Pce ipv6 address";
  }
  typedef Pce-ipv4-address {
    type inet:ipv4-address;
    description "Pce ipv4 address";
  }
  typedef Pce-af-id {
    type enumeration {
      enum none {
        value 0;
        description "None";
      }
      enum ipv4 {
        value 1;
        description "IPv4";
      }
      enum ipv6 {
        value 2;
        description "IPv6";
      }
    }
    description "Pce af id";
  }

  grouping PCE-COMPUTATION-ALGORITHM-STATS {
    description "Statistics per computation algorithm";
    leaf computation-algorithm {
      type Sr-computation-algorithm;
      description "The computation algorithm for these stats";
    }
    leaf invocations {
      type uint64;
      description "Number of invocations";
    }
    leaf paths-found {
      type uint64;
      description "Number of times a path was found";
    }
    leaf paths-not-found {
      type uint64;
      description "Number of times a path was not found";
    }
    leaf total-time-milliseconds {
      type uint64;
      units "millisecond";
      description
        "Total time (milliseconds) spent executing this
        algorithm";
    }
    leaf minimum-time-milliseconds {
      type uint32;
      units "millisecond";
      description
        "Minimum time (milliseconds) for any invocation
        of this algorithm";
    }
    leaf maximum-time-milliseconds {
      type uint32;
      units "millisecond";
      description
        "Maximum time (milliseconds) for any invocation
        of this algorithm";
    }
    leaf average-time-milliseconds {
      type uint32;
      units "millisecond";
      description
        "Average time (milliseconds) for all invocations
        of this algorithm";
    }
    leaf total-iterations {
      type uint64;
      description "Total number of iterations using this algorithm";
    }
    leaf minimum-iterations {
      type uint32;
      description "Minimum number of iterations to find a path";
    }
    leaf maximum-iterations {
      type uint32;
      description "Maximum number of iterations to find a path";
    }
    leaf average-iterations {
      type uint32;
      description "Average number of iterations to find a path";
    }
  }

  grouping PCE-PCEP-STATS {
    description "PCEP Statistics";
    leaf timestamp-first-pc-report {
      type uint32;
      description
        "Timestamp of the first received path computation
        report";
    }
    leaf timestamp-last-pc-report {
      type uint32;
      description
        "Timestamp of the last received path computation
        report";
    }
    leaf timestamp-first-p-update-c {
      type uint32;
      description
        "Timestamp of the first sent path computation
        update";
    }
    leaf timestamp-last-pc-update {
      type uint32;
      description
        "Timestamp of the last sent path computation
        update";
    }
    leaf pcep-peers {
      type uint32;
      description "Number of PCEP peers";
    }
    leaf received-pc-reports {
      type uint64;
      description "Number of path computation reports received";
    }
    leaf sent-pc-updates {
      type uint64;
      description "Number of path computation updates sent";
    }
  }

  grouping PCE-PERFORMANCE-STATS-BAG {
    description "PCE performance statistics bag";

    container pcep-statistics {
      description "PCEP Aggregate Statistics";
      uses PCE-PCEP-STATS;
    }
    leaf timestamp-clearing {
      type uint32;
      description
        "Timestamp when the performance stats were
        cleared";
    }
    leaf down-ls-ps {
      type uint32;
      description "Number of LSPs that are down";
    }
    leaf up-ls-ps {
      type uint32;
      description "Number of LSPs that are up";
    }
    leaf path-computation-cache-misses {
      type uint64;
      description "Number of misses in the computed paths cache";
    }
    leaf path-computation-cache-hits {
      type uint64;
      description "Number of hits in the computed paths cache";
    }
    leaf cache-garbage-collection-count {
      type uint64;
      description "Number of times the cache was garbage collected";
    }
    leaf topology-import-count {
      type uint64;
      description
        "Number of times the topology was imported for
        CSPF";
    }
    leaf spc-taken-memory {
      type uint32;
      description "Memory taken by the cache in MiB";
    }
    leaf cache-maximum-size {
      type uint32;
      description "Maximum cache size in MiB";
    }

    list computation-algorithm-stat {
      max-elements "8";
      description "Statistics for the computation algorithms";
      uses PCE-COMPUTATION-ALGORITHM-STATS;
    }
  }

  grouping API-PEER-STATS-INFO {
    description "Stats info struct";
    leaf api-peer-type {
      type Api-peer-stats-info-oper;
      description "Peer operation types";
    }
    leaf peer-state {
      type Nbapi-peer-state;
      description "Peer state";
    }
    leaf id {
      type uint32;
      description "Unique Identifier for stats";
    }
    leaf failed-flag {
      type boolean;
      description "Indicates failure";
    }
    leaf start-time {
      type uint32;
      description "Indicates start time";
    }
    leaf last-seen-time {
      type uint32;
      description "Indicates Last seen time";
    }
    leaf queue-valid-time {
      type uint32;
      description
        "Timestamp, when something was sent from queue or
        when it was empty.";
    }
    leaf send-queue-size {
      type uint64;
      units "byte";
      description "Size of data in send queue in bytes";
    }
    leaf rest-query {
      type string;
      description "query string";
    }
  }

  grouping API-PEER-STATS-BAG {
    description "API PEER STATS BAG";

    container peer-address {
      description "Indicates the peer IP";
      uses PCE-IP-ADDR-TYPE;
    }
    leaf uid {
      type uint32;
      description "Indicates the UID for the peer";
    }

    list stats {
      description "Stats info";
      uses API-PEER-STATS-INFO;
    }
  }

  grouping PCE-PATH-LIST-BAG {
    description "PCE path list";
    leaf headends-swapped {
      type Pce-headend-swap;
      description "DEPRECATED: Headends swapped";
    }
    leaf cspf-result {
      type Pce-cspf-rc;
      description "CSPF Result";
    }
    leaf iterations-done {
      type uint32;
      description "Iterations of the algorithm";
    }

    list output-path {
      description "Output PCE paths";
      uses PCE-PATH-BAG;
    }
  }

  grouping PCE-SRV6-HOP-BAG {
    description "SRv6 Hop Details";

    container srv6sid {
      description "SRv6 SID detailed";
      uses SRV6-SID-BAG;
    }
    leaf local-ipv6-address {
      type inet:ipv6-address;
      description "Local IPv6 address";
    }
    leaf remote-ipv6-address {
      type inet:ipv6-address;
      description "Remote IPv6 address";
    }
  }

  grouping PCE-ADDR-BAG {
    description "PCE Address Information";

    container srv6-hop {
      description "SRv6 Hop information";
      uses PCE-SRV6-HOP-BAG;
    }
    leaf address-family {
      type uint8;
      description "Address Family";
    }
    leaf ipv4-prefix {
      type inet:ipv4-address;
      description "IPv4 prefix";
    }
    leaf ipv6-prefix {
      type inet:ipv6-address;
      description "IPv6 prefix";
    }
  }

  grouping PCE-PATH-BAG {
    description "PCE path information";

    container source-xr {
      description "Source of path";
      uses PCE-IP-ADDR-TYPE;
    }

    container destination-xr {
      description "Destination of path";
      uses PCE-IP-ADDR-TYPE;
    }
    leaf cost {
      type uint64;
      description "Cost";
    }

    list hops {
      description "Hop addresses";
      uses PCE-ADDR-BAG;
    }
  }

  grouping PATH-WORK-CACHE-STATS {
    description "Statistics about a particular cache";
    leaf work-consumed {
      type uint64;
      description "Number of work nodes consumed";
    }
    leaf cache-hit {
      type uint64;
      description "How many times we were able to use the cache";
    }
    leaf cache-miss {
      type uint64;
      description "How many times we had to recompute the cache";
    }
    leaf cache-miss-time-usec {
      type uint64;
      units "microsecond";
      description "How many microseconds the last computation took";
    }
    leaf average-cache-miss-time-usec {
      type uint64;
      units "microsecond";
      description
        "How many microseconds the average computation
        took";
    }
    leaf error {
      type uint64;
      description "Number of errors";
    }
    leaf run-time-usec {
      type uint64;
      units "microsecond";
      description
        "How many microseconds it took to verify one
        region";
    }
  }

  grouping PATH-WORK-GROUP-STATS {
    description "Path work group stats";

    list last {
      description "Last several computations";
      uses PATH-WORK-CACHE-STATS;
    }
  }

  grouping PATH-WORK-REGION {
    description "Path work region";
    leaf work-count {
      type uint32;
      description "Number of work elements";
    }
  }

  grouping XTC-AFFINITY-COLOR {
    description "XTC AFFINITY COLOR";
    leaf color {
      type string;
      description "An affinity color";
    }
  }

  grouping XTC-AFFINITY-CONSTRAINT {
    description "XTC AFFINITY CONSTRAINT";
    leaf type {
      type uint8;
      description "Affinity type";
    }
    leaf value {
      type uint32;
      description "Affinity value";
    }

    list extended-value {
      description "Extended Affinity values";
      leaf entry {
        type uint32;
        description "Extended Affinity values";
      }
    }

    list color {
      description "Colors";
      uses XTC-AFFINITY-COLOR;
    }
  }

  grouping PATH-WORK-GROUP-KEY {
    description "Identifies path work group";

    container source-address {
      description "Source address";
      uses XTC-IP-ADDR-TYPE;
    }
    leaf maximum-segments {
      type uint16;
      description "Max number of segments to impose";
    }
    leaf metric-type {
      type uint8;
      description "Metric type being optimized";
    }
    leaf protection-type {
      type Cmn-protection;
      description "Requested path protection type";
    }
    leaf non-ocspf {
      type boolean;
      description "Constraints are something other than O-CSPF";
    }
    leaf is-srv6 {
      type boolean;
      description "Path work for SRv6";
    }

    list affinity-constraint {
      description "Affinity constraints list";
      uses XTC-AFFINITY-CONSTRAINT;
    }
  }

  grouping PATH-WORK-GROUP {
    description "Path work group";

    container key {
      description "Unique key to identify group";
      uses PATH-WORK-GROUP-KEY;
    }

    container region-1 {
      description "First region of the group";
      uses PATH-WORK-REGION;
    }

    container region-2 {
      description "Second region of the group";
      uses PATH-WORK-REGION;
    }

    container stats {
      description "Group statistics";
      uses PATH-WORK-GROUP-STATS;
    }
    leaf id-xr {
      type uint32;
      description "Work group ID";
    }
    leaf works-count {
      type uint64;
      description "Number of works in this group";
    }
    leaf worker-past-region1 {
      type boolean;
      description "Is the worker past region_1";
    }
  }

  grouping PCE-ASSO-LSP-INFO {
    description "Association LSP common information";

    container pcc-address {
      description "PCC address";
      uses PCE-IP-ADDR-TYPE;
    }
    leaf tunnel-id {
      type uint32;
      description "Tunnel ID";
    }
    leaf lspid {
      type uint32;
      description "LSP ID";
    }
    leaf tunnel-name {
      type string;
      description "Tunnel Name";
    }
    leaf pce-based {
      type boolean;
      description "PCE Based";
    }
    leaf plsp-id {
      type uint32;
      description "PLSP ID";
    }
  }

  grouping PCE-ASSO-BAG {
    description "PCE Association information";

    container association-source {
      description "Association Source";
      uses PCE-IP-ADDR-TYPE;
    }
    leaf association-type {
      type uint32;
      description "Association Type";
    }
    leaf association-id {
      type uint32;
      description "Association ID";
    }
    leaf strict {
      type boolean;
      description "Association Strict Mode";
    }
    leaf status {
      type uint32;
      description "Association Status";
    }
    leaf headends-swapped {
      type uint32;
      description "DEPRECATED: Headends Swapped";
    }

    list association-lsp {
      description "Association LSP Info";
      uses PCE-ASSO-LSP-INFO;
    }
  }

  grouping XTC-GRPC-SERVICE-INSTANCE-STATS-BAG {
    description "gRPC path computation service statistics";
    leaf connect-time {
      type uint32;
      description
        "Time at which the client most recently connected";
    }
    leaf disconnect-time {
      type uint32;
      description
        "Time at which the client most recently
        disconnected";
    }
    leaf requests-sent {
      type uint64;
      description "Count of requests sent to the server";
    }
    leaf updates-sent {
      type uint64;
      description "Count of updates sent to the server";
    }
    leaf withdraws-sent {
      type uint64;
      description "Count of withdraws sent to the server";
    }
    leaf responses-received {
      type uint64;
      description "Count of responses received from the server";
    }
    leaf errors-received {
      type uint64;
      description "Count of errors received from the server";
    }
    leaf error {
      type uint64;
      description "Count of any errors encountered internally";
    }
  }

  grouping XTC-GRPC-SERVICE-INSTANCE-BAG {
    description "gRPC path computation service";

    container statistics {
      description "Statistics";
      uses XTC-GRPC-SERVICE-INSTANCE-STATS-BAG;
    }
    leaf id {
      type uint32;
      description "Service Instance ID";
    }
    leaf instance-name {
      type string;
      description "Service Instance name";
    }
    leaf address {
      type string;
      description "Server Address";
    }
    leaf connected {
      type boolean;
      description "Whether connection with server is established";
    }
    leaf cleanup-timer-running {
      type boolean;
      description "Cleanup timer is started, in cleanup phase";
    }
  }

  grouping CMN-TRACE-BUFFER-SUMMARY-BAG {
    description "Trace buffer summary";
    leaf trace-buffer-name {
      type string;
      description "Name of trace buffer";
    }
    leaf unique-trace-count {
      type uint32;
      description "Unique trace count";
    }
    leaf wrapping-trace-count-default {
      type uint32;
      description "Default value of wrapping trace count";
    }
    leaf wrapping-trace-count-programmed {
      type uint32;
      description "Programmed value of wrapping trace count";
    }
    leaf string-buffer-size-default {
      type uint32;
      units "byte";
      description
        "Default string buffer size for wrapping traces
        in bytes";
    }
    leaf string-buffer-size-programmed {
      type uint32;
      units "byte";
      description
        "Programmed string buffer size for wrapping
        traces in bytes";
    }
  }

  grouping PCE-OV-RULE-ME-BAG {
    description "PCE override rule override attributes";

    container peer-address {
      description "IP address of peer";
      uses XTC-IP-ADDR-TYPE;
    }
    leaf symbolic-name {
      type string;
      description "Symbolic name of the LSP being matched";
    }
  }

  grouping PCE-OV-RULE-OV-PCEP-OBJ-SUB-TYPE-BAG {
    description
      "PCE override for blocking PCEP objects of
      specific sub-type";
    leaf sub-type {
      type uint8;
      description
        "Block only instances of PCEP object of specific
        sub-type";
    }
  }

  grouping PCE-OV-RULE-OV-PCEP-BLOCK-BAG {
    description "PCE override for blocking PCEP objects";
    leaf object-type {
      type uint8;
      description "Block PCEP object of specific type.";
    }
    leaf all {
      type boolean;
      description "Block PCEP object of any sub-type";
    }

    list sub-type {
      description "List of blocked PCEP object sub-type";
      uses PCE-OV-RULE-OV-PCEP-OBJ-SUB-TYPE-BAG;
    }
  }

  grouping PCE-OV-RULE-OV-BAG {
    description "PCE override rule override attributes";
    leaf metric-type {
      type Cmn-metric;
      description "Overridden metric type";
    }
    leaf bandwidth {
      type uint64;
      description "Bandwidth";
    }
    leaf sid-algorithm {
      type uint8;
      description "SID algorithm";
    }
    leaf admin-down-when-no-path {
      type boolean;
      description
        "Flag to advertise admin down in PCEP when no
        path";
    }
    leaf protection-type {
      type Cmn-protection;
      description "Path protection type";
    }

    list blocked-pcep-object {
      description "List of blocked PCEP objects";
      uses PCE-OV-RULE-OV-PCEP-BLOCK-BAG;
    }
  }

  grouping PCE-OV-RULE-MC-LSP-CR-BAG {
    description "LSP color range bag";
    leaf minimum {
      type uint32;
      description "Minimum";
    }
    leaf maximum {
      type uint32;
      description "Maximum";
    }
  }

  grouping PCE-OV-RULE-MC-LSP-BAG {
    description "PCE override profile LSP matching criteria";
    leaf all-ls-ps {
      type boolean;
      description "Flag indicating all LSPs should be matched";
    }
    leaf regular-expression {
      type string;
      description "String containing the regular expression";
    }

    list color-range {
      description "List containing color ranges";
      uses PCE-OV-RULE-MC-LSP-CR-BAG;
    }
  }

  grouping PCE-OV-RULE-MC-PEER-BAG {
    description "PCE override rule peer matching criteria";
    leaf all-peers {
      type boolean;
      description "Flag indicating all peers should be matched";
    }
    leaf ipv4-acl-name {
      type string;
      description "ACL name";
    }
  }

  grouping PCE-OV-RULE-MC-BAG {
    description "PCE override rule matching criteria";

    container peer {
      description "Matching criteria for peers";
      uses PCE-OV-RULE-MC-PEER-BAG;
    }

    container lsp {
      description "Matching criteria for LSPs";
      uses PCE-OV-RULE-MC-LSP-BAG;
    }
  }

  grouping PCE-OV-RULE-BAG {
    description "PCE override rule bag";

    container matching-criteria {
      description "Matching criteria";
      uses PCE-OV-RULE-MC-BAG;
    }

    container override-attributes {
      description "Override attributes";
      uses PCE-OV-RULE-OV-BAG;
    }
    leaf sequence-number-xr {
      type uint32;
      description "Sequence number";
    }

    list matching-entry {
      description "Matching entries/LSPs";
      uses PCE-OV-RULE-ME-BAG;
    }
  }

  grouping PATH-WORK-NODE {
    description "Path work node";
    leaf type {
      type Path-work-node;
      description "Node type";
    }
    leaf repr {
      type string;
      description "String representation";
    }
  }

  grouping PCE-NODE-FLEX-ALGO-DEFINITION {
    description "PCE Node Flex-algo definition";

    container node-id {
      description
        "Flex-algo Advertising Link-state node identifier";
      uses PCE-NODE-ID-BAG;
    }

    container flex-algo-definition {
      description "Flex-algo definition";
      uses PCE-FA-DEFINITION;
    }
  }

  grouping PCE-IGP-AREA-INFO-TYPE {
    description "PCE IGP AREA INFO TYPE";
    leaf igp-id {
      type Pce-igp-info-id;
      description "IGP ID";
    }
    leaf level {
      when "../igp-id = 'isis'" {
        description "../IGP_ID = 'ISIS'";
      }
      type uint32;
      description "ISIS level";
    }
    leaf area {
      when "../igp-id = 'ospf'" {
        description "../IGP_ID = 'OSPF'";
      }
      type uint32;
      description "OSPF area";
    }
  }

  grouping PCE-FLEX-ALGO-AREA {
    description "Flex-algo information per Area";

    container igp-area {
      description "IGP-area-specific information";
      uses PCE-IGP-AREA-INFO-TYPE;
    }
    leaf igp-id {
      type Pce-igp-info-id;
      description "IGP type";
    }
    leaf domain-identifier {
      type uint64;
      description "Domain identifier";
    }

    list definition {
      description "Per Area Flex-Algo Definition";
      uses PCE-NODE-FLEX-ALGO-DEFINITION;
    }
  }

  grouping PCE-PEER-PROTO-SUMMARY-BAG {
    description "Peer summary for specified protocol";
    leaf peer-count-up {
      type uint32;
      description "Number of peers in up state";
    }
    leaf peer-count-down {
      type uint32;
      description "Number of peers in down state";
    }
    leaf peer-count-all {
      type uint32;
      description "Number of all peers";
    }
  }

  grouping PCE-PEER-SUMMARY-BAG {
    description "Peer summary information";

    container pcep-peers {
      description "PCEP peers summary information";
      uses PCE-PEER-PROTO-SUMMARY-BAG;
    }
  }

  grouping PCE-TREESID-HOP-BAG {
    description "TreeSID hop information";
    leaf next-hop-address {
      type inet:ipv4-address;
      description "Next hop remote address";
    }
    leaf next-hop-label {
      type uint32;
      description "Next hop outgoing label";
    }
    leaf next-hop-node-sid {
      type uint32;
      description "Next hop node-sid";
    }
    leaf next-hop-node-address {
      type inet:ipv4-address;
      description "Next hop node address";
    }
    leaf next-hop-node-name {
      type string;
      description "Next hop node name";
    }
    leaf stale {
      type boolean;
      description "Stale hop; will be removed in next update";
    }
    leaf central-control-identifier {
      type uint32;
      description "Identifier for Central Control instructions";
    }
    leaf fast-reroute {
      type boolean;
      description "Fast Re-route to hop remote node";
    }
  }

  grouping PCE-TREESID-NODE-BAG {
    description "TreeSID node information";
    leaf prefix-address {
      type inet:ipv4-address;
      description "Node prefix address";
    }
    leaf name {
      type string;
      description "Node name";
    }
    leaf role {
      type Pce-treesid-role;
      description "Node role";
    }
    leaf awaiting-report {
      type boolean;
      description "Awaiting report";
    }
    leaf stale {
      type boolean;
      description "Stale node";
    }
    leaf plsp-id {
      type uint32;
      description "PLSP ID";
    }
    leaf lsp-id {
      type uint16;
      description "LSP ID";
    }
    leaf delegated-by-pcc {
      type boolean;
      description "Indicates if PCC has delegated LSP to this PCE";
    }
    leaf delegated-to-pce {
      type boolean;
      description
        "Indicates if PCC has delegated LSP to a peer PCE";
    }
    leaf is-pcc-delegation-stale {
      type boolean;
      description
        "Indicates if delegation from PCC for this LSP is
        stale";
    }
    leaf is-pce-delegation-stale {
      type boolean;
      description
        "Indicates if delegation from PCE for this LSP is
        stale";
    }
    leaf delegated-pce {
      type inet:ipv4-address;
      description "PCE to which LSP is delegated to";
    }

    list next-hop {
      description "Next hops";
      uses PCE-TREESID-HOP-BAG;
    }
  }

  grouping PCE-TREESID-INST-BAG {
    description "TreeSID instance information";
    leaf instance-id {
      type uint16;
      description "Instance ID";
    }
    leaf label {
      type uint32;
      description "SID of the TreeSID";
    }
    leaf operational-state {
      type boolean;
      description "Operational state";
    }
    leaf instance-active {
      type boolean;
      description "Instance active?";
    }
    leaf prog-phase {
      type Pce-treesid-prog-phase;
      description
        "Programming phase of the TreeSID (ie, pending
        operation)";
    }
    leaf uptime {
      type uint32;
      units "second";
      description "Uptime of the tunnel in seconds";
    }
    leaf active-time {
      type uint32;
      description "Time at which instance went active";
    }
    leaf transition-count {
      type uint32;
      description
        "Number of transitions between operational
        up/down";
    }

    list nodes {
      description "List of nodes associated with this instance";
      uses PCE-TREESID-NODE-BAG;
    }
  }

  grouping PCEP-SR-P2MP-POLICY-POL-ID-BAG {
    description "PCEP SR P2MP Policy POL-ID";
    leaf tree-id {
      type uint32;
      description "P2MP Policy Tree Identifier";
    }
  }

  grouping PCEP-SR-P2MP-AG-BAG {
    description "PCEP SR Policy Association Group";

    container srp2mpag-asso-source {
      description "Association Source";
      uses XTC-IP-ADDR-TYPE;
    }

    container p2mp-policy-id-info {
      description "P2MP POL-ID";
      uses PCEP-SR-P2MP-POLICY-POL-ID-BAG;
    }

    container p2mp-policy-name-info {
      description "P2MP POL-Name";
      uses PCEP-SRPOLICY-POL-NAME-BAG;
    }

    container p2mp-candidate-path-id-info {
      description "P2MP Candidate-path ID";
      uses PCEP-SRPOLICY-CPATH-ID-BAG;
    }

    container p2mp-candidate-path-preference {
      description "P2MP Candidate-path preference";
      uses PCEP-SRPOLICY-CPATH-PREFERENCE-BAG;
    }
    leaf srp2mpag-asso-id {
      type uint16;
      description "Association ID";
    }
    leaf p2mp-candidate-path-name {
      type string;
      description "P2MP Candidate-path name";
    }
  }

  grouping PCE-TREESID-CPATH-BAG {
    description "TreeSID Candidate Path information";

    container srp2mpag-info {
      description "SR P2MP Policy Association Group";
      uses PCEP-SR-P2MP-AG-BAG;
    }

    container attribute-info {
      description "Candidate path attributes";
      uses PCE-LSPA-INFO;
    }
    leaf candidate-path-name {
      type string;
      description "Name of the candidate path";
    }
    leaf cpath-origin {
      type Pce-treesid-cpath-origin;
      description "Candidate path origin";
    }
    leaf metric-type {
      type uint8;
      description "Metric type of the candidate path";
    }
    leaf fa-metric-type {
      type uint8;
      description "Flex-algo metric type of the candidate path";
    }
    leaf flex-algo {
      type uint8;
      description "Flex-algo of the candidate path";
    }
    leaf error {
      type string;
      description "Last instance computation error";
    }
    leaf operational-state {
      type boolean;
      description "Operational state";
    }
    leaf is-compute-pce {
      type boolean;
      description "Compute role of PCE for candidate path";
    }
    leaf administrative-state {
      type boolean;
      description "Administrative state";
    }
    leaf lfa-protected {
      type boolean;
      description "LFA Protection enabled?";
    }
    leaf from-checkpoint {
      type boolean;
      description "Created from checkpoint database?";
    }
    leaf rest-dynamic-label-alloc {
      type boolean;
      description "Label auto allocation for REST tree";
    }
    leaf uptime {
      type uint32;
      units "second";
      description "Uptime of the candidate path in seconds";
    }
    leaf transition-count {
      type uint32;
      description
        "Number of transitions between operational
        up/down";
    }

    list p2mp-instance {
      description "List of instances of this candidate path";
      uses PCE-TREESID-INST-BAG;
    }
  }

  grouping PCE-TREESID-BAG {
    description "TreeSID information";

    container cleanup-timer {
      description "Cleanup timer; started when tree is not valid";
      uses CMN-TIMER-INFO;
    }
    leaf name-xr {
      type string;
      description "Name of the TreeSID";
    }
    leaf source-address {
      type inet:ipv4-address;
      description "Address of the source node";
    }
    leaf pcc-address {
      type inet:ipv4-address;
      description "PCC Address of the source node";
    }
    leaf operational-state {
      type boolean;
      description "Operational state";
    }
    leaf uptime {
      type uint32;
      units "second";
      description "Uptime of the tunnel in seconds";
    }
    leaf transition-count {
      type uint32;
      description
        "Number of transitions between operational
        up/down";
    }
    leaf tree-id-xr {
      type uint32;
      description "TreeSID Tree-ID";
    }
    leaf-list destination-address {
      type inet:ipv4-address;
      description "List of destination addresses";
    }

    list event {
      description "Events";
      uses PCE-EVENT-INFO;
    }

    list cand-path {
      description "List of candidate path of this TreeSID";
      uses PCE-TREESID-CPATH-BAG;
    }
  }

  grouping PCE-SIBLING-CONN-BAG {
    description "PCE sibling connection information";

    container address {
      description "Address of sibling";
      uses XTC-IP-ADDR-TYPE;
    }
    leaf connected {
      type boolean;
      description "Flag indicating the connection status";
    }
    leaf packet-read-size {
      type uint32;
      description "Input buffer data size";
    }
    leaf packet-write {
      type uint32;
      description "Packets in output buffer";
    }
  }

  grouping PCE-SYNCED-LSP-DISJOINTNESS-BAG {
    description "PCE disjointness bag";

    container association-information {
      description "Association information";
      uses PCE-ASSO-INFO;
    }
    leaf fallback {
      type boolean;
      description "Fallback flag";
    }
  }

  grouping PCE-SIBLING-SYNCED-LSP-BAG {
    description "PCE sibling synced LSP data";

    container actual-pcc-address {
      description
        "Actual address of PCC peer where the PCInitiate
        was sent";
      uses XTC-IP-ADDR-TYPE;
    }

    container requested-pcc-address {
      description
        "Requested address of PCC peer used by the
        creator of LSP";
      uses XTC-IP-ADDR-TYPE;
    }

    container affinity {
      description "Affinity";
      uses PCE-AFFINITY-BAG;
    }

    container disjointness {
      description "Disjointness";
      uses PCE-SYNCED-LSP-DISJOINTNESS-BAG;
    }
    leaf lsp-name-xr {
      type string;
      description "Name of the LSP";
    }
    leaf remote-ls-pdata {
      type boolean;
      description
        "Flag to indicate whether this is remote lsp data
        or a local copy";
    }
    leaf protected {
      type boolean;
      description "Flag to indicate if protected path is required";
    }
    leaf allow-xtc-reoptimization {
      type boolean;
      description "Flag to indicate if reoptimization is allowed";
    }
    leaf binding-sid {
      type uint32;
      description "Binding sid";
    }
    leaf sid-algorithm-set {
      type boolean;
      description "Flag to indicate if SID algorithm is set";
    }
    leaf sid-algorithm {
      type uint8;
      description
        "SID algorithm value. Applicable if
        SIDAlgorithmSet is set";
    }
  }

  grouping PCE-AFFINITY-BAG {
    description "PCE affinity bag";
    leaf exclude-any {
      type uint32;
      description "Exclude any";
    }
    leaf include-any {
      type uint32;
      description "Include any";
    }
    leaf include-all {
      type uint32;
      description "Include all";
    }
  }

  grouping PCE-BWOD-SUB-DELEGATION-BAG {
    description "PCE NB-API BWoD sub-delegation bag";

    container pcc-address-xr {
      description "IP address of the PCC";
      uses XTC-IP-ADDR-TYPE;
    }

    container source-address {
      description "Source address of the tunnel";
      uses XTC-IP-ADDR-TYPE;
    }

    container destination-address {
      description "Destination address of the tunnel";
      uses XTC-IP-ADDR-TYPE;
    }

    container affinity {
      description "Affinity";
      uses PCE-AFFINITY-BAG;
    }
    leaf reference-id {
      type uint64;
      description "Reference ID of the sub-delegation";
    }
    leaf symbolic-name {
      type string;
      description "Symbolic name of the tunnel";
    }
    leaf plsp-id {
      type uint32;
      description "PLSP-ID of the tunnel";
    }
    leaf setup-type {
      type Lsp-setup;
      description "Path setup type";
    }
    leaf metric-type {
      type Cmn-metric;
      description "Metric-type of requested path";
    }
    leaf requested-bandwidth {
      type uint64;
      units "kbit/s";
      description "Requested bandwidth in kbps";
    }
    leaf computed-metric {
      type uint32;
      description "Computed metric (cost) from NB-API BWoD client";
    }
    leaf sid-algorithm-set {
      type boolean;
      description "Flag to indicate if sid algorithm is set";
    }
    leaf sid-algorithm {
      type uint8;
      description
        "Value of sid algorithm. Only applicable if
        SIDAlgorithmSet is TRUE";
    }
    leaf maximum-delay {
      type uint32;
      description "Maximum delay constraint";
    }
    leaf cp-preference {
      type uint32;
      description "Candidate path preference";
    }
    leaf block-recomputation {
      type boolean;
      description
        "TRUE if path recomputation is blocked in case of
        topology change";
    }
    leaf adjacency-sids-only {
      type boolean;
      description
        "TRUE if only adjacency SIDs may be used in the
        path-computation";
    }
    leaf protection-type {
      type Cmn-protection;
      description "Protection Type";
    }
  }

  grouping PCE-BWOD-BEST-CLIENT-BAG {
    description
      "Best BWoD client with sub-delegations currently
      active.";

    container address {
      description "Client IP address";
      uses XTC-IP-ADDR-TYPE;
    }
    leaf is-client-connected {
      type boolean;
      description
        "Flag indicating whether there is a best BWoD
        client";
    }
    leaf priority {
      type int32;
      description "Priority of BWoD client";
    }
  }

  grouping PCE-BGP-LS-POLICY-ENTRY-BAG {
    description "PCE BGP-LS policy entry bag";

    container tunnel-information {
      description "Tunnel information as translated from BGP-LS";
      uses PCE-TUN-DETAIL-BAG;
    }
    leaf bgp-router-id {
      type inet:ipv4-address;
      description "BGP router ID advertising this policy entry";
    }
  }

  grouping PCE-BGP-LS-POLICY-BAG {
    description "PCE BGP-LS policy bag";

    container ipv4-router-address {
      description
        "IPv4 router (headend) address advertising the SR
        candidate path";
      uses XTC-IP-ADDR-TYPE;
    }

    container ipv6-router-address {
      description
        "IPv6 router (headend) address advertising the SR
        candidate path";
      uses XTC-IP-ADDR-TYPE;
    }

    container endpoint-address-xr {
      description "SR policy endpoint address";
      uses XTC-IP-ADDR-TYPE;
    }

    container originator-address-xr {
      description "SR policy candidate path originator address";
      uses XTC-IP-ADDR-TYPE;
    }
    leaf color-xr {
      type uint32;
      description "SR policy color";
    }
    leaf protocol-origin-xr {
      type uint8;
      description "SR policy candidate path protocol origin";
    }
    leaf originator-asn-xr {
      type uint32;
      description "SR policy candidate path originator ASN";
    }
    leaf discriminator-xr {
      type uint32;
      description "SR policy candidate path discriminator";
    }

    list entry {
      description "SR policy entries";
      uses PCE-BGP-LS-POLICY-ENTRY-BAG;
    }
  }

  grouping PCE-POLICY-CPATH-BAG {
    description "PCE policy candidate-path";
    leaf name {
      type string;
      description "Name of the candidate-path";
    }
    leaf plsp-id {
      type uint32;
      description "PLSP-ID pf tje candidate-path";
    }
    leaf active-flag {
      type boolean;
      description
        "Flag to mention if the candidate-path is
        currently active";
    }
  }

  grouping PCE-POLICY-BAG {
    description "PCE policy";

    container pcc-address-xr {
      description "Path computation client address";
      uses XTC-IP-ADDR-TYPE;
    }

    container end-point {
      description "End-point of the policy";
      uses XTC-IP-ADDR-TYPE;
    }
    leaf interface-name {
      type string;
      description "Name of the interface";
    }
    leaf color {
      type uint32;
      description "Color of the policy";
    }

    list candidate-path {
      description "Array of candidate-paths";
      uses PCE-POLICY-CPATH-BAG;
    }
  }

  grouping PCE-SR-MPLS-PATH-BAG {
    description "PCE SR path information";

    container source {
      description "Source of path";
      uses PCE-IP-ADDR-TYPE;
    }

    container destination {
      description "Destination of path";
      uses PCE-IP-ADDR-TYPE;
    }
    leaf cost {
      type uint64;
      description "Cost";
    }

    list hops {
      description "SR hops";
      uses PCE-SR-HOP-TYPE;
    }
  }

  grouping PCE-SR-MPLS-PATH-LIST-BAG {
    description "PCE SR MPLS path list";
    leaf cspf-result {
      type Pce-cspf-rc;
      description "Result of the computation";
    }
    leaf iterations-done {
      type uint32;
      description
        "Iterations performed of the Suurballe-Tarjan
        algorithm";
    }
    leaf computation-duration-millisecond {
      type uint32;
      units "millisecond";
      description
        "How many milliseconds it took to compute this
        path";
    }
    leaf computation-algorithm {
      type Sr-computation-algorithm;
      description "What algorithm was used to compute this path";
    }

    list output-path {
      description "Output SR MPLS paths";
      uses PCE-SR-MPLS-PATH-BAG;
    }
  }

  grouping PCE-PEER-AUTH-OPTION-BAG {
    description "PCE Peer Authentication Option information";

    container peer-address {
      description "Peer address";
      uses PCE-IP-ADDR-TYPE;
    }

    container authentication-option {
      description "Authentication Option information";
      uses PCE-AUTH-OPTION-BAG;
    }
  }

  grouping TOPO-LS-LINK-ASLA-BAG {
    description "Topology LS link ASLA";
    leaf application-type {
      type Topo-ls-link-asla-app;
      description "ASLA application type";
    }
    leaf te-metric {
      type uint32;
      description "ASLA TE metric value";
    }
    leaf minimum-latency {
      type uint32;
      description "ASLA Minimum latency value";
    }
    leaf-list admin-group {
      type uint32;
      description "Admin groups (affinities)";
    }
  }

  grouping TOPO-LS-ADJ-SID-BAG {
    description "Topology LS adjacency SID";
    leaf label {
      type uint32;
      description "MPLS label";
    }
    leaf type {
      type Topo-sid;
      description "Type of the adjacency SID";
    }
    leaf protected {
      type boolean;
      description "Whether the adjacency SID is eligible for FRR";
    }
  }

  grouping TOPO-LS-LINK-METRIC-BAG {
    description "Topology LS link metric";
    leaf type {
      type Topo-ls-link-metric;
      description "Type of the metric";
    }
    leaf value {
      type uint32;
      description "Metric value";
    }
  }

  grouping TOPO-LS-LINK-ID-BAG {
    description "Topology LS link identifiers";

    container local-address {
      description
        "Local address of the link (node in case of
        unnumbered)";
      uses XTC-IP-ADDR-TYPE;
    }

    container remote-address {
      description
        "Remote address of the link (node in case of
        unnumbered)";
      uses XTC-IP-ADDR-TYPE;
    }
    leaf local-id {
      type uint32;
      description "Local ID of the link";
    }
    leaf remote-id {
      type uint32;
      description "Remote ID of the link";
    }
  }

  grouping TOPO-LS-LINK-BAG {
    description "Topology LS link";

    container link-identifier {
      description "The link identifier";
      uses TOPO-LS-LINK-ID-BAG;
    }

    container remote-node-attributes {
      description "The remote LS node attributes and identifiers";
      uses TOPO-LS-NODE-ATTRIBUTES-BAG;
    }
    leaf maximum-link-bandwidth {
      type uint64;
      units "byte/s";
      description "Maximum link bandwidth in bytes per second";
    }
    leaf maximum-reservable-bandwidth {
      type uint64;
      units "byte/s";
      description
        "Maximum reservable bandwidth in bytes per second";
    }
    leaf-list srl-gs {
      type uint32;
      description "SRLGs associated with this LS link";
    }
    leaf-list admin-group {
      type uint32;
      description "Admin groups (affinities)";
    }
    leaf-list unreserved-bandwidth {
      type uint64;
      units "byte/s";
      description "Unreserved bandwidth in bytes per second";
    }

    list metric {
      description "Advertised metrics for this LS link";
      uses TOPO-LS-LINK-METRIC-BAG;
    }

    list adjacency-sid {
      description "Adjacency SIDs associated with this LS link";
      uses TOPO-LS-ADJ-SID-BAG;
    }

    list asl-as {
      description "ASLAs advertised for this link";
      uses TOPO-LS-LINK-ASLA-BAG;
    }

    list srv6-adjacency-sid {
      description "Advertised SRv6 adjacency SIDs";
      uses TOPO-LS-SRV6-SID-BAG;
    }

    list ms-ds {
      description "Advertised MSDs";
      uses TOPO-MSD-BAG;
    }
  }

  grouping TOPO-FLEX-ALGO-DEF-BAG {
    description "Topology flex algorithm definition";
    leaf flex-algorithm {
      type uint8;
      description "The flex algorithm";
    }
    leaf metric-type {
      type uint8;
      description "DEPRECATED: PCEP Metric type value";
    }
    leaf priority {
      type uint8;
      description "Priority of this flex algorithm definition";
    }
    leaf igp-iana-metric-type {
      type uint8;
      description "IGP IANA Metric type value";
    }
    leaf-list affinity-exclude-any {
      type uint32;
      description
        "Exclude any affinity advertised for this flex
        algorithm";
    }
    leaf-list affinity-include-any {
      type uint32;
      description
        "Include any affinity advertised for this flex
        algorithm";
    }
    leaf-list affinity-include-all {
      type uint32;
      description
        "Include all affinity advertised for this flex
        algorithm";
    }
  }

  grouping TOPO-SRLB-BAG {
    description "Topology SRLB bag";
    leaf start {
      type uint32;
      description "SRLB start";
    }
    leaf size {
      type uint32;
      description "SRLB size";
    }
  }

  grouping TOPO-SRGB-BAG {
    description "Topology SRGB bag";
    leaf start {
      type uint32;
      description "SRGB start";
    }
    leaf size {
      type uint32;
      description "SRGB size";
    }
  }

  grouping TOPO-LS-SRV6-LOCATOR-BAG {
    description "Topology LS SRv6 locator";
    leaf algorithm {
      type uint8;
      description "SRv6 locator algorithm";
    }
    leaf metric {
      type uint32;
      description "SRv6 locator metric";
    }
  }

  grouping TOPO-LS-PFX-SID-BAG {
    description "Topology LS prefix SID";
    leaf index {
      type uint32;
      description "SID index";
    }
    leaf type {
      type Topo-sid;
      description "Type of the SID";
    }
    leaf algorithm {
      type uint8;
      description "Algorithm of the prefix SID";
    }
    leaf flag-x {
      type boolean;
      description "Whether the X flag is enabled - DEPRECATED";
    }
    leaf flag-r {
      type boolean;
      description
        "Whether the R flag is enabled. Set if R flag for
        Prefix SID or for Prefix is set.";
    }
    leaf flag-n {
      type boolean;
      description
        "Whether the N flag is enabled. Set if N flag for
        Prefix SID or for Prefix is set";
    }
    leaf flag-p {
      type boolean;
      description "Whether the P flag is enabled";
    }
    leaf flag-e {
      type boolean;
      description "Whether the E flag is enabled";
    }
    leaf flag-v {
      type boolean;
      description "Whether the V flag is enabled";
    }
    leaf flag-l {
      type boolean;
      description "Whether the L flag is enabled";
    }
    leaf flag-m {
      type boolean;
      description "Whether the M flag is enabled";
    }
  }

  grouping TOPO-LS-PFX-ID-BAG {
    description "Topology LS prefix identifiers";

    container prefix {
      description "The IP prefix";
      uses XTC-IP-ADDR-TYPE;
    }
    leaf prefix-length {
      type uint8;
      description "Length of the prefix";
    }
  }

  grouping TOPO-LS-PFX-BAG {
    description "Topology LS prefix";

    container prefix-identifier {
      description "The prefix identifier";
      uses TOPO-LS-PFX-ID-BAG;
    }

    container srv6-locator {
      description "Associated SRv6 locator";
      uses TOPO-LS-SRV6-LOCATOR-BAG;
    }
    leaf metric {
      type uint32;
      description "The metric associated with this prefix";
    }
    leaf flag-x {
      type boolean;
      description "Whether the X flag is enabled";
    }
    leaf flag-r {
      type boolean;
      description "Whether the R flag is enabled";
    }
    leaf flag-n {
      type boolean;
      description "Whether the N flag is enabled";
    }

    list prefix-sid {
      description "Prefix SIDs associated with this prefix";
      uses TOPO-LS-PFX-SID-BAG;
    }
  }

  grouping TOPO-LS-NODE-ID-BGP-BAG {
    description "BGP specific LS node identifiers";
    leaf router-id {
      type inet:ipv4-address;
      description "BGP router ID";
    }
  }

  grouping TOPO-LS-NODE-ID-ISIS-BAG {
    description "ISIS specific LS node identifiers";
    leaf system-id {
      type string;
      description "ISIS system ID";
    }
    leaf level {
      type uint8;
      description "ISIS level (L1/L2)";
    }
  }

  grouping TOPO-LS-NODE-ID-OSPF-BAG {
    description "OSPF specific LS node identifiers";
    leaf router-id {
      type inet:ipv4-address;
      description "OSPF router ID";
    }
    leaf area-identifier {
      type uint32;
      description "OSPF area identifier";
    }
  }

  grouping TOPO-LS-NODE-ID-TYPE {
    description "TOPO LS NODE ID TYPE";

    container ospf {
      when "../protocol = 'ospf'" {
        description "../Protocol = 'OSPF'";
      }
      description "OSPF identifiers";
      uses TOPO-LS-NODE-ID-OSPF-BAG;
    }

    container isis {
      when "../protocol = 'isis'" {
        description "../Protocol = 'ISIS'";
      }
      description "ISIS identifiers";
      uses TOPO-LS-NODE-ID-ISIS-BAG;
    }

    container bgp {
      when "../protocol = 'bgp'" {
        description "../Protocol = 'BGP'";
      }
      description "BGP identifiers";
      uses TOPO-LS-NODE-ID-BGP-BAG;
    }
    leaf protocol {
      type Topo-ls-node-id-proto;
      description "Protocol";
    }
  }

  grouping TOPO-LS-NODE-ID-BAG {
    description "Identifier of an LS node";

    container identifier {
      description "Protocol specific identifier";
      uses TOPO-LS-NODE-ID-TYPE;
    }
    leaf link-state-identifier {
      type uint32;
      description "BGP-LS identifier (TLV 513) of the LS node";
    }
    leaf autonomous-system-number {
      type uint32;
      description "Autonomous system number of the LS-node";
    }
  }

  grouping TOPO-LS-NODE-ATTRIBUTES-BAG {
    description "Common LS node attributes";

    container node-identifier {
      description "LS node identifiers";
      uses TOPO-LS-NODE-ID-BAG;
    }
    leaf host-name {
      type string;
      description "Hostname of the LS node";
    }
    leaf domain-id {
      type uint64;
      description "Domain ID where this node is advertised from";
    }
    leaf te-router-id {
      type inet:ipv4-address;
      description "TE router ID (if any)";
    }
    leaf ipv6-router-id {
      type inet:ipv6-address;
      description "IPv6 router ID (if any)";
    }
    leaf overload {
      type boolean;
      description
        "Whether the overload bit is set for this LS node";
    }
    leaf isis-area-identifier {
      type string;
      description "ISIS area identifier";
    }
  }

  grouping TOPO-SRV6-SID-STRUCT-BAG {
    description "Topology SRv6 SID structure information";
    leaf locator-block-length {
      type uint8;
      description "SRv6 SID Locator Block length in bits";
    }
    leaf locator-node-length {
      type uint8;
      description "SRv6 SID Locator Node length in bits";
    }
    leaf function-length {
      type uint8;
      description "SRv6 SID Function length in bits";
    }
    leaf arguments-length {
      type uint8;
      description "SRv6 SID Arguments length in bits";
    }
  }

  grouping TOPO-SRV6-SID-FUNC-BAG {
    description "Topology SRv6 SID function";

    container endpoint-function {
      description "Endpoint function";
      uses MGMT-SRV6-ENDPOINT-BEHAVIOR;
    }
    leaf algorithm {
      type uint8;
      description "SRv6 SID algorithm";
    }
  }

  grouping TOPO-LS-SRV6-SID-BAG {
    description "Topology LS SRv6 SID";

    container function {
      description "Function of the SRv6 SID";
      uses TOPO-SRV6-SID-FUNC-BAG;
    }

    container sid-structure {
      description "SRv6 SID structure";
      uses TOPO-SRV6-SID-STRUCT-BAG;
    }
    leaf sid-identifier {
      type inet:ipv6-address;
      description "SRv6 SID identifier";
    }
  }

  grouping TOPO-LS-NODE-BAG {
    description "Topology LS node as received from BGP-LS";

    container attributes {
      description "The LS node attributes and identifiers";
      uses TOPO-LS-NODE-ATTRIBUTES-BAG;
    }
    leaf-list sr-algorithm {
      type uint8;
      description
        "Which SR algorithms are supported by this LS
        node";
    }

    list srv6sid {
      description "Advertised SRv6 SIDs";
      uses TOPO-LS-SRV6-SID-BAG;
    }

    list prefixe {
      description "Prefixes advertised by this LS node";
      uses TOPO-LS-PFX-BAG;
    }

    list srg-bs {
      description "SRGBs advertised by this LS node";
      uses TOPO-SRGB-BAG;
    }

    list srl-bs {
      description "SRLBs advertised by this LS node";
      uses TOPO-SRLB-BAG;
    }

    list flex-algorithm-definition {
      description
        "Flex algorithm definitions advertised by this LS
        node";
      uses TOPO-FLEX-ALGO-DEF-BAG;
    }

    list links {
      description "LS links associated with this LS node";
      uses TOPO-LS-LINK-BAG;
    }

    list ms-ds {
      description "Advertised MSDs";
      uses TOPO-MSD-BAG;
    }
  }

  grouping TOPO-NODE-BAG {
    description "Physical topology node";
    leaf uid {
      type uint32;
      description "Unique identifier of the node";
    }
    leaf router-id {
      type inet:ipv4-address;
      description "Router ID of the node";
    }
    leaf ipv6-router-id-xr {
      type inet:ipv6-address;
      description "IPv6 router ID of the node";
    }
    leaf-list domain-id {
      type uint64;
      description "Domain IDs this node belongs to";
    }

    list ls-node {
      description "LS nodes that belong under this physical node";
      uses TOPO-LS-NODE-BAG;
    }
  }

  grouping PCE-PFX-ENTRY {
    description "PCE prefix etnry";

    container ip {
      description "Prefix IP address";
      uses PCE-IP-ADDR-TYPE;
    }
  }

  grouping PCE-PFX-BAG {
    description "PCE Prefix Information";

    container node-protocol-identifier {
      description "Node protocol identifier";
      uses PCE-NODE-PID-BAG;
    }
    leaf node-identifier-xr {
      type uint32;
      description "Node identifier";
    }

    list address {
      description "Prefix address";
      uses PCE-PFX-ENTRY;
    }
  }

  grouping CMN-TIMER-INFO {
    description "Timer information";
    leaf running {
      type boolean;
      description "Whether the timer is running";
    }
    leaf remaining-seconds {
      type int64;
      units "second";
      description "Number of remaining seconds";
    }
    leaf remaining-nano-seconds {
      type int64;
      units "nanosecond";
      description "Number of remaining nanoseconds";
    }
  }

  grouping XTC-TOPO-READY-BAG {
    description "XTC Topology Readiness Information";

    container timer {
      description "Topology readiness timer";
      uses CMN-TIMER-INFO;
    }
    leaf ready {
      type boolean;
      description "Topology readiness";
    }
    leaf pcep-allowed {
      type boolean;
      description "Whether PCEP is allowed";
    }
    leaf ha-case {
      type Cmn-ha-case;
      description "Last HA case";
    }
    leaf timer-value {
      type uint32;
      description "Topology ready timer value selected at start";
    }
  }

  grouping PCE-TOPO-STATS-BAG {
    description "Statistics on topology update";
    leaf num-nodes-added {
      type uint32;
      description "Number of nodes added";
    }
    leaf num-nodes-deleted {
      type uint32;
      description "Number of nodes deleted";
    }
    leaf num-links-added {
      type uint32;
      description "Number of links added";
    }
    leaf num-links-deleted {
      type uint32;
      description "Number of links deleted";
    }
    leaf num-prefixes-added {
      type uint32;
      description "Number of prefixes added";
    }
    leaf num-prefixes-deleted {
      type uint32;
      description "Number of prefixes deleted";
    }
  }

  grouping PCE-NODE-SUMMARY-BAG {
    description "PCE Node Summary Information";

    container stats-topology-update {
      description "Statistics on topology update";
      uses PCE-TOPO-STATS-BAG;
    }

    container topology-ready-summary {
      description "Topology ready summary";
      uses XTC-TOPO-READY-BAG;
    }
    leaf total-nodes {
      type uint32;
      description
        "Aggregate total of all types of nodes in
        topology";
    }
    leaf nodes {
      type uint32;
      description "Number of topology nodes";
    }
    leaf virtual-nodes {
      type uint32;
      description "Number of virtual nodes";
    }
    leaf lookup-nodes {
      type uint32;
      description "Number of lookup nodes";
    }
    leaf prefixes {
      type uint32;
      description
        "Aggregate total of all types of prefixes in
        topology";
    }
    leaf local-prefixes {
      type uint32;
      description "Number of local prefixes";
    }
    leaf non-anycast-prefixes {
      type uint32;
      description "Number of non-anycast prefixes";
    }
    leaf anycast-prefixes {
      type uint32;
      description "Number of anycast prefixes";
    }
    leaf remote-prefixes {
      type uint32;
      description "Number of remote prefixes";
    }
    leaf prefix-sids {
      type uint32;
      description "Number of total prefix SIDs";
    }
    leaf regular-prefix-sids {
      type uint32;
      description "Number of reguar prefix SIDs";
    }
    leaf strict-prefix-sids {
      type uint32;
      description "Number of strict prefix SIDs";
    }
    leaf flex-algo-prefix-sids {
      type uint32;
      description "Number of flex-algo prefix SIDs";
    }
    leaf total-links {
      type uint32;
      description
        "Aggregate total of all types of links in
        topology";
    }
    leaf links {
      type uint32;
      description "Number of topology links";
    }
    leaf virtual-links {
      type uint32;
      description "Number of virtual links";
    }
    leaf epe-links {
      type uint32;
      description "Number of EPE links";
    }
    leaf adjacency-sids {
      type uint32;
      description "Number of total adjacency SIDs";
    }
    leaf epesids {
      type uint32;
      description "Number of total EPE SIDs";
    }
    leaf protected-adjacency-sids {
      type uint32;
      description "Number of protected adjacency SIDs";
    }
    leaf un-protected-adjacency-sids {
      type uint32;
      description "Number of unprotected adjacency SIDs";
    }
    leaf topology-consistent {
      type boolean;
      description "True if topology is consistent";
    }
    leaf topology-unreliable {
      type boolean;
      description "True if topology is unreliable";
    }
    leaf update-dropped {
      type uint32;
      description "Number of total update dropped";
    }
  }

  grouping SRV6-NODE-SID-BAG {
    description "SRv6 Node SID bag";

    container srv6sid {
      description "SRv6 node SID";
      uses SRV6-SID-BAG;
    }

    container node-id {
      description "Link-state node identifier";
      uses PCE-NODE-ID-BAG;
    }
    leaf domain-identifier {
      type uint64;
      description "Domain identifier";
    }
  }

  grouping PCE-IPV6-LINK-BAG {
    description "PCE IPv6 Link Information";

    container local-igp-information {
      description "Local node IGP information";
      uses PCE-IGP-INFO-BAG;
    }

    container remote-node-protocol-identifier {
      description "Remote node protocol identifier";
      uses PCE-NODE-PID-BAG;
    }

    container performance-metrics {
      description "Performance metrics";
      uses PCE-LINK-PM-METRICS;
    }
    leaf is-unnumbered {
      type boolean;
      description "True if this is an IPv6 Unnumbered link";
    }
    leaf local-interface-index {
      type uint32;
      description "Non-zero if IsUnnumbered is True";
    }
    leaf remote-interface-index {
      type uint32;
      description "Non-zero if IsUnnumbered is True";
    }
    leaf local-ipv6-address {
      type inet:ipv6-address;
      description "Local IPv6 address";
    }
    leaf remote-ipv6-address {
      type inet:ipv6-address;
      description "Remote IPv6 address";
    }
    leaf igp-metric {
      type uint32;
      description "IGP Metric";
    }
    leaf te-metric {
      type uint32;
      description "TE Metric";
    }
    leaf maximum-link-bandwidth {
      type uint64;
      description "Max link bandwidth";
    }
    leaf max-reservable-bandwidth {
      type uint64;
      description "Max Reservable bandwidth";
    }
    leaf administrative-groups {
      type uint32;
      description "Link admin-groups";
    }
    leaf flex-algo-asla-te-metric {
      type uint32;
      description "Flex-algo specific Link TE metric";
    }
    leaf flex-algo-asla-minimum-latency {
      type uint32;
      description "Flex-algo specific Link Minimum latency metric";
    }
    leaf-list srlgs {
      type uint32;
      description "SRLG Values";
    }
    leaf-list flex-algo-asla-administrative-group {
      type uint32;
      description "Flex-algo specific Link Extended admin-groups";
    }

    list adjacency-sid {
      description "Adjacency SIDs";
      uses PCE-SID-BAG;
    }

    list srv6-adjacency-sid {
      description "SRv6 Adjacecny micro-SIDs";
      uses SRV6-SID-BAG;
    }

    list msd {
      description "Advertised MSDs";
      uses TOPO-MSD-BAG;
    }
  }

  grouping PCE-LINK-PM-METRICS {
    description "Link performance metric information";
    leaf unidirectional-minimum-delay-microseconds {
      type uint32;
      units "microsecond";
      description "Min delay in microseconds";
    }
  }

  grouping PCE-IPV4-LINK-BAG {
    description "PCE IPv4 Link Information";

    container local-igp-information {
      description "Local node IGP information";
      uses PCE-IGP-INFO-BAG;
    }

    container remote-node-protocol-identifier {
      description "Remote node protocol identifier";
      uses PCE-NODE-PID-BAG;
    }

    container performance-metrics {
      description "Performance metrics";
      uses PCE-LINK-PM-METRICS;
    }
    leaf is-unnumbered {
      type boolean;
      description "True if this is an IPv4 Unnumbered link";
    }
    leaf local-interface-index {
      type uint32;
      description "Non-zero if IsUnnumbered is True";
    }
    leaf remote-interface-index {
      type uint32;
      description "Non-zero if IsUnnumbered is True";
    }
    leaf local-ipv4-address {
      type inet:ipv4-address;
      description "Local IPv4 address";
    }
    leaf remote-ipv4-address {
      type inet:ipv4-address;
      description "Remote IPv4 address";
    }
    leaf igp-metric {
      type uint32;
      description "IGP Metric";
    }
    leaf te-metric {
      type uint32;
      description "TE Metric";
    }
    leaf maximum-link-bandwidth {
      type uint64;
      description "Max link bandwidth";
    }
    leaf max-reservable-bandwidth {
      type uint64;
      description "Max Reservable bandwidth";
    }
    leaf administrative-groups {
      type uint32;
      description "Link admin-groups";
    }
    leaf flex-algo-asla-te-metric {
      type uint32;
      description "Flex-algo specific Link TE metric";
    }
    leaf flex-algo-asla-minimum-latency {
      type uint32;
      description "Flex-algo specific Link Minimum latency metric";
    }
    leaf-list flex-algo-asla-administrative-group {
      type uint32;
      description "Flex-algo specific Link Extended admin-groups";
    }
    leaf-list srlgs {
      type uint32;
      description "SRLG Values";
    }

    list adjacency-sid {
      description "Adjacency SIDs";
      uses PCE-SID-BAG;
    }

    list msd {
      description "Advertised MSDs";
      uses TOPO-MSD-BAG;
    }
  }

  grouping PCE-SID-BAG {
    description "PCE SID bags";

    container sid-prefix {
      description "Prefix";
      uses PCE-IP-ADDR-TYPE;
    }
    leaf sid-type {
      type Sid;
      description "SID Type";
    }
    leaf mpls-label {
      type uint32;
      description "MPLS Label";
    }
    leaf algorithm {
      type uint32;
      description "Prefix SID Algorithm";
    }
    leaf xflag {
      type boolean;
      description "X Flag";
    }
    leaf rflag {
      type boolean;
      description "R Flag";
    }
    leaf nflag {
      type boolean;
      description "N Flag";
    }
    leaf pflag {
      type boolean;
      description "P Flag";
    }
    leaf eflag {
      type boolean;
      description "E Flag";
    }
    leaf vflag {
      type boolean;
      description "V Flag";
    }
    leaf lflag {
      type boolean;
      description "L Flag";
    }
    leaf mflag {
      type boolean;
      description "M Flag";
    }
  }

  grouping PCE-PREFIX-BAG {
    description "PCE Prefix bag";

    container pfx-sid {
      description "Prefix SID";
      uses PCE-SID-BAG;
    }

    container node-id {
      description "Link-state node identifier";
      uses PCE-NODE-ID-BAG;
    }
    leaf domain-identifier {
      type uint64;
      description "Domain identifier";
    }
  }

  grouping PCE-SRLB-INFO-BAG {
    description "PCE SRLB information bag";

    container node-id {
      description "Link-state node identifier";
      uses PCE-NODE-ID-BAG;
    }
    leaf start {
      type uint32;
      description "SRLB start";
    }
    leaf size {
      type uint32;
      description "SRLB size";
    }
    leaf domain-identifier {
      type uint64;
      description "Domain identifier";
    }
  }

  grouping PCE-FA-DEFINITION {
    description "Flex-algo definition";
    leaf number {
      type uint8;
      description "Flex-Algo number";
    }
    leaf local-priority {
      type uint8;
      description "Local Priority";
    }
    leaf metric-type {
      type Cmn-metric;
      description "DEPRECATED: Metric Type ";
    }
    leaf igp-iana-metric-type {
      type uint8;
      description "IGP IANA Metric type value";
    }
    leaf-list aff {
      type uint32;
      description "Affinity exclude any";
    }
    leaf-list affinity-include-any {
      type uint32;
      description "Affinity include any";
    }
    leaf-list affinity-include-all {
      type uint32;
      description "Affinity include all";
    }
  }

  grouping PCE-SR-ALGO-BAG {
    description "PCE SR Algo Information";

    container node-id {
      description "Link-state node identifier";
      uses PCE-NODE-ID-BAG;
    }
    leaf domain-identifier {
      type uint64;
      description "Domain identifier";
    }
    leaf-list algo-participation {
      type uint8;
      description "Algos participated by this node";
    }

    list flex-algo-advertised-definition {
      description "Flex-algo definition advertised";
      uses PCE-FA-DEFINITION;
    }
  }

  grouping PCE-SRGB-INFO-BAG {
    description "PCE SRGB information bag";

    container node-id {
      description "Link-state node identifier";
      uses PCE-NODE-ID-BAG;
    }
    leaf start {
      type uint32;
      description "SRGB start";
    }
    leaf size {
      type uint32;
      description "SRGB size";
    }
    leaf domain-identifier {
      type uint64;
      description "Domain identifier";
    }
  }

  grouping PCE-IGP-INFO-BGP {
    description "PCE BGP Information";
    leaf router-id {
      type Pce-ipv4-address;
      description "BGP router ID";
    }
    leaf confed-asn {
      type uint32;
      description "Confederation ASN";
    }
  }

  grouping PCE-IGP-INFO-OSPF {
    description "PCE OSPF Information";
    leaf router-id {
      type Pce-ipv4-address;
      description "OSPF router ID";
    }
    leaf area {
      type uint32;
      description "OSPF area";
    }
  }

  grouping PCE-IGP-INFO-ISIS {
    description "PCE ISIS Information";
    leaf system-id {
      type string;
      description "ISIS system ID";
    }
    leaf level {
      type uint32;
      description "ISIS level";
    }
    leaf area {
      type string;
      description "ISIS area";
    }
  }

  grouping PCE-IGP-INFO-TYPE {
    description "PCE IGP INFO TYPE";

    container isis {
      when "../igp-id = 'isis'" {
        description "../IGP_ID = 'ISIS'";
      }
      description "ISIS information";
      uses PCE-IGP-INFO-ISIS;
    }

    container ospf {
      when "../igp-id = 'ospf'" {
        description "../IGP_ID = 'OSPF'";
      }
      description "OSPF information";
      uses PCE-IGP-INFO-OSPF;
    }

    container bgp {
      when "../igp-id = 'bgp'" {
        description "../IGP_ID = 'BGP'";
      }
      description "BGP information";
      uses PCE-IGP-INFO-BGP;
    }
    leaf igp-id {
      type Pce-igp-info-id;
      description "IGP ID";
    }
  }

  grouping PCE-NODE-ID-BAG {
    description "PCE Node ID information";

    container igp {
      description "IGP-specific information";
      uses PCE-IGP-INFO-TYPE;
    }
    leaf autonomous-system-number {
      type uint32;
      description "Autonomous System Number";
    }
    leaf ls-identifier {
      type uint32;
      description "Link-State identifier";
    }
  }

  grouping PCE-IGP-INFO-BAG {
    description "PCE IGP information bag";

    container node-id {
      description "Link-state node identifier";
      uses PCE-NODE-ID-BAG;
    }
    leaf domain-identifier {
      type uint64;
      description "Domain identifier";
    }
  }

  grouping PCE-NODE-PID-BAG {
    description "PCE Node Protocol Identifier Information";
    leaf node-name {
      type string;
      description "Node Name";
    }
    leaf ipv4-bgp-router-id-set {
      type boolean;
      description "True if IPv4 BGP router ID is set";
    }
    leaf ipv4-bgp-router-id {
      type inet:ipv4-address;
      description "IPv4 TE router ID";
    }
    leaf ipv4te-router-id-set {
      type boolean;
      description "True if IPv4 TE router ID is set";
    }
    leaf ipv4te-router-id {
      type inet:ipv4-address;
      description "IPv4 BGP router ID";
    }
    leaf ipv6-router-id-set {
      type boolean;
      description "True if the IPv6 router ID is set";
    }
    leaf ipv6-router-id {
      type inet:ipv6-address;
      description "IPv6 Router ID";
    }

    list igp-information {
      description "IGP information";
      uses PCE-IGP-INFO-BAG;
    }

    list srgb-information {
      description "SRGB information";
      uses PCE-SRGB-INFO-BAG;
    }

    list sr-algo {
      description "SR Algo information";
      uses PCE-SR-ALGO-BAG;
    }

    list srlb-information {
      description "SRLB information";
      uses PCE-SRLB-INFO-BAG;
    }
  }

  grouping PCE-XTC-NODE-BAG {
    description "PCE XTC Node Information";

    container node-protocol-identifier {
      description "Node protocol identifier";
      uses PCE-NODE-PID-BAG;
    }
    leaf node-identifier-xr {
      type uint32;
      description "Node identifier";
    }
    leaf overload {
      type boolean;
      description "Node Overload Bit";
    }

    list prefixe {
      description "Prefixes";
      uses PCE-PREFIX-BAG;
    }

    list ipv4-link {
      description "IPv4 Link information";
      uses PCE-IPV4-LINK-BAG;
    }

    list ipv6-link {
      description "IPv6 Link information";
      uses PCE-IPV6-LINK-BAG;
    }

    list srv6-node-sid {
      description "SRv6 Node micro-SIDs";
      uses SRV6-NODE-SID-BAG;
    }
  }

  grouping PCE-VIRTUAL-LINK-BAG {
    description "PCE Virtual Link Info";
    leaf local-pce-id {
      type uint32;
      description "Virtual link local PCE ID";
    }
    leaf remote-pce-id {
      type uint32;
      description "Virtual link remote PCE ID";
    }
    leaf local-ipv4-address {
      type inet:ipv4-address;
      description "Virtual link local IPv4 address";
    }
    leaf remote-ipv4-address {
      type inet:ipv4-address;
      description "Virtual link remote IPv4 address";
    }
    leaf metric {
      type uint32;
      description "Virtual link metric";
    }
    leaf label {
      type uint32;
      description "Virtual link SID Label";
    }
  }

  grouping PCE-REMOTE-PFX-BAG {
    description "PCE Remote Prefix Information";

    container ip {
      description "Remote prefix IP address";
      uses PCE-IP-ADDR-TYPE;
    }
    leaf virtual-node-pce-id {
      type uint32;
      description "Virtual Node PCE ID";
    }

    list virtual-link {
      description "virtual links";
      uses PCE-VIRTUAL-LINK-BAG;
    }
  }

  grouping PCE-PEER-BAG {
    description "Peer information";

    container peer-address-xr {
      description "Peer address";
      uses PCE-IP-ADDR-TYPE;
    }

    container brief-pcep-information {
      description "PCE protocol information";
      uses PCE-PCEP-BAG;
    }
    leaf peer-protocol {
      type Pce-proto;
      description "Protocol between PCE and peer";
    }
  }

  grouping TOPO-MSD-BAG {
    description "Topology MSD";
    leaf subtype {
      type Topo-msd-subtype;
      description "Subtype of the MSD as defined by IANA";
    }
    leaf value {
      type uint8;
      description "MSD value";
    }
  }

  grouping PCE-AUTH-OPTION-BAG {
    description "PCE Authentication Option information";
    leaf authentication-key-type {
      type Cmn-auth;
      description "Authentication Key Type";
    }
    leaf password {
      type string;
      description "Authentication Password";
    }
    leaf authentication-option-include-options-enable {
      type boolean;
      description "Include Option Enable";
    }
    leaf authentication-option-accept-mismatch-enable {
      type boolean;
      description "Accept Mismatch Enable";
    }
  }

  grouping PCE-PCEP-ERROR-BAG {
    description "PCEP Error information";
    leaf pc-error-type {
      type uint8;
      description "PCEP Error type";
    }
    leaf pc-error-value {
      type uint8;
      description "PCEP Error Value";
    }
  }

  grouping PCE-PCEP-BAG {
    description "PCEP information";
    leaf pcep-state {
      type Pcep-state;
      description "PCEP State";
    }
    leaf stateful {
      type boolean;
      description "Stateful";
    }
    leaf capability-update {
      type boolean;
      description "Update capability";
    }
    leaf capability-instantiate {
      type boolean;
      description "Instantiation capability";
    }
    leaf capability-segment-routing {
      type boolean;
      description "Segment Routing capability";
    }
    leaf capability-triggered-sync {
      type boolean;
      description "Triggered Synchronization capability";
    }
    leaf capability-db-version {
      type boolean;
      description "DB version capability";
    }
    leaf capability-delta-sync {
      type boolean;
      description "Delta Synchronization capability";
    }
    leaf capability-srv6 {
      type boolean;
      description "SRv6 capability";
    }
    leaf capability-srp2mp {
      type boolean;
      description "SR P2MP capability";
    }
  }

  grouping PCE-PCEP-DETAIL-BAG {
    description "Detailed PCE protocol information";

    container brief-pcep-information {
      description "Brief PCE protocol information";
      uses PCE-PCEP-BAG;
    }

    container last-error-rx {
      description "Last PCError received";
      uses PCE-PCEP-ERROR-BAG;
    }

    container last-error-tx {
      description "Last PCError sent";
      uses PCE-PCEP-ERROR-BAG;
    }

    container pce-authentication {
      description "PCE Peer Authentication";
      uses PCE-AUTH-OPTION-BAG;
    }
    leaf error {
      type string;
      description "Error (for display only)";
    }
    leaf speaker-id {
      type string;
      description "Speaker Entity ID";
    }
    leaf pcep-up-time {
      type uint32;
      description "PCEP Up Time";
    }
    leaf keepalives {
      type uint32;
      description "Keepalive count";
    }
    leaf md5-enabled {
      type boolean;
      description "MD5 Authentication Enabled";
    }
    leaf authentication-option-keychain-enabled {
      type boolean;
      description "AO Keychain based Authentication Enabled";
    }
    leaf negotiated-local-keepalive {
      type uint32;
      description "Negotiated KA";
    }
    leaf negotiated-remote-keepalive {
      type uint32;
      description "Negotiated KA";
    }
    leaf negotiated-dead-time {
      type uint32;
      description "Negotiated DT";
    }
    leaf pce-request-rx {
      type uint32;
      description "PCEReq Rx";
    }
    leaf pce-request-tx {
      type uint32;
      description "PCEReq Tx";
    }
    leaf pce-reply-rx {
      type uint32;
      description "PCERep Rx";
    }
    leaf pce-reply-tx {
      type uint32;
      description "PCERep Tx";
    }
    leaf pce-error-rx {
      type uint32;
      description "PCEErr Rx";
    }
    leaf pce-error-tx {
      type uint32;
      description "PCEErr Tx";
    }
    leaf pce-open-tx {
      type uint32;
      description "PCEOpen Tx";
    }
    leaf pce-open-rx {
      type uint32;
      description "PCEOpen Rx";
    }
    leaf pce-report-rx {
      type uint32;
      description "PCERpt Rx";
    }
    leaf pce-report-tx {
      type uint32;
      description "PCERpt Tx";
    }
    leaf pce-update-rx {
      type uint32;
      description "PCEUpd Rx";
    }
    leaf pce-update-tx {
      type uint32;
      description "PCEUpd Tx";
    }
    leaf pce-initiate-rx {
      type uint32;
      description "PCEInit Rx";
    }
    leaf pce-initiate-tx {
      type uint32;
      description "PCEInit Tx";
    }
    leaf pce-keepalive-tx {
      type uint64;
      description "PCE Keepalive Tx";
    }
    leaf pce-keepalive-rx {
      type uint64;
      description "PCE Keepalive Rx";
    }
    leaf local-session-id {
      type uint8;
      description "Local PCEP session ID";
    }
    leaf remote-session-id {
      type uint8;
      description "Remote PCEP session ID";
    }
    leaf minimum-keepalive-interval {
      type uint8;
      description "Minimum keepalive interval for the peer";
    }
    leaf maximum-dead-interval {
      type uint8;
      description "Maximum dead interval for the peer";
    }
    leaf max-sid-depth {
      type uint8;
      description
        "Maximum number of labels the peer can impose for
        SR-MPLS policies";
    }
    leaf p2mp-num-instances {
      type uint16;
      description
        "Number of P2MP tree instances per policy the
        peer can support";
    }

    list srv6msd {
      description "SRv6 Maximum SID Depth list";
      uses TOPO-MSD-BAG;
    }
  }

  grouping PCE-PEER-DETAIL-BAG {
    description "Detailed PCEP peer information";

    container peer-address-xr {
      description "Peer address";
      uses PCE-IP-ADDR-TYPE;
    }

    container detail-pcep-information {
      description "Detailed PCE protocol information";
      uses PCE-PCEP-DETAIL-BAG;
    }
    leaf peer-protocol {
      type Pce-proto;
      description "Protocol between PCE and peer";
    }
    leaf max-sid-depth {
      type uint32;
      description "SR-MPLS Maximum SID Depth";
    }
  }

  grouping PCE-EVENT-INFO {
    description "PCE Event information";
    leaf event-id {
      type uint32;
      description "Event ID in range 1 - 0xFFFFFFFF. 0 is invalid.";
    }
    leaf event-message {
      type string;
      description "Event message";
    }
    leaf time-stamp {
      type uint64;
      description "Event time, relative to Jan 1, 1970";
    }
  }

  grouping PCE-EVENT-BAG {
    description "Private LSP information";

    list event-buffer {
      description "LSP Event buffer";
      uses PCE-EVENT-INFO;
    }
  }

  grouping PCE-LSP-EXCLUDE-RESOURCE {
    description "Exclude resource information";

    container resource-address {
      description "Address of the resource being excluded";
      uses XTC-IP-ADDR-TYPE;
    }
    leaf resource-type {
      type Pce-lsp-exclude-resource;
      description "Resource type being excluded";
    }
    leaf exclusion-desired {
      type boolean;
      description
        "True if exclusion is desired, false when
        mandatory";
    }
  }

  grouping PCE-LSP-EXCLUDE-INFO {
    description "PCE LSP exclude information";
    leaf fail-flag {
      type boolean;
      description
        "Indicates request for a new path computation for
        an existing LSP that has failed";
    }

    list resource {
      description "Resources to be excluded";
      uses PCE-LSP-EXCLUDE-RESOURCE;
    }
  }

  grouping PCE-LSP-CONSTRAINTS-INFO {
    description "PCE LSP constraints information";

    container exclude-information {
      description "LSP exclude constraints information";
      uses PCE-LSP-EXCLUDE-INFO;
    }
  }

  grouping PCEP-BIDIR-BAG {
    description "PCEP SR Policy Bidirectional Association";

    container bidirectional-asso-source {
      description "Association Source";
      uses XTC-IP-ADDR-TYPE;
    }
    leaf bidirectional-asso-id {
      type uint16;
      description "Association ID";
    }
    leaf corouted-lsp {
      type boolean;
      description "Co-routed LSP";
    }
    leaf reverse-lsp {
      type boolean;
      description "Reverse LSP";
    }
  }

  grouping PCEP-SRPOLICY-CPATH-PREFERENCE-BAG {
    description "PCEP SR Policy CPATH-PREFERENCE";
    leaf preference {
      type uint32;
      description "Preference";
    }
  }

  grouping PCEP-SRPOLICY-CPATH-ID-BAG {
    description "PCEP SR Policy CPATH-ID";
    leaf originator-address {
      type inet:ipv6-address;
      description "Originator IPv6 address";
    }
    leaf originator-asn {
      type uint32;
      description "Originator AS number";
    }
    leaf discriminator {
      type uint32;
      description "Discriminator";
    }
    leaf protocol-origin {
      type uint8;
      description "Protocol origin";
    }
  }

  grouping PCEP-SRPOLICY-POL-NAME-BAG {
    description "PCEP SR Policy Name";
    leaf policy-name {
      type string;
      description "Policy name";
    }
  }

  grouping PCEP-SRPOLICY-POL-ID-BAG {
    description "PCEP SR Policy POL-ID";

    container endpoint {
      description "Policy endpoint";
      uses XTC-IP-ADDR-TYPE;
    }
    leaf color {
      type uint32;
      description "Policy color";
    }
  }

  grouping XTC-IP-ADDR-TYPE {
    description "XTC IP ADDR TYPE";
    leaf af-name {
      type Xtc-af-id;
      description "AFName";
    }
    leaf ipv4 {
      when "../af-name = 'ipv4'" {
        description "../AFName = 'IPv4'";
      }
      type Xtc-ipv4-address;
      description "IPv4 address type";
    }
    leaf ipv6 {
      when "../af-name = 'ipv6'" {
        description "../AFName = 'IPv6'";
      }
      type Xtc-ipv6-address;
      description "IPv6 address type";
    }
  }

  grouping PCEP-SRPAG-BAG {
    description "PCEP SR Policy Association Group";

    container srpag-asso-source {
      description "Association Source";
      uses XTC-IP-ADDR-TYPE;
    }

    container policy-id-info {
      description "POL ID";
      uses PCEP-SRPOLICY-POL-ID-BAG;
    }

    container policy-name-info {
      description "POL Name";
      uses PCEP-SRPOLICY-POL-NAME-BAG;
    }

    container candidate-path-id-info {
      description "CPATH ID";
      uses PCEP-SRPOLICY-CPATH-ID-BAG;
    }

    container candidate-path-preference {
      description "CPATH PREFERENCE";
      uses PCEP-SRPOLICY-CPATH-PREFERENCE-BAG;
    }
    leaf srpag-asso-id {
      type uint16;
      description "Association ID";
    }
    leaf candidate-path-name {
      type string;
      description "Candidate-path name";
    }
  }

  grouping PCE-LSPA-INFO {
    description "PCE LSP attribute information";
    leaf affinity-exclude-any {
      type uint32;
      description "Affinity exclude any";
    }
    leaf affinity-include-any {
      type uint32;
      description "Affinity include any";
    }
    leaf affinity-include-all {
      type uint32;
      description "Affinity include all";
    }
    leaf setup-priority {
      type uint8;
      description "Setup Priority";
    }
    leaf hold-priority {
      type uint8;
      description "Hold Priority";
    }
    leaf local-protection {
      type boolean;
      description "True, if local protection is desired";
    }
  }

  grouping PCE-LSP-RSVP-ERROR-BAG {
    description "RSVP error information";
    leaf node-address {
      type inet:ipv4-address;
      description "RSVP error node address";
    }
    leaf error-flags {
      type uint8;
      description "RSVP error flags";
    }
    leaf error-code {
      type uint8;
      description "RSVP error code";
    }
    leaf error-value {
      type uint16;
      description "RSVP error value";
    }
  }

  grouping PCE-PCEP-INFO {
    description "PCEP LSP information";

    container rsvp-error {
      description "RSVP error info";
      uses PCE-LSP-RSVP-ERROR-BAG;
    }
    leaf pcepid {
      type uint32;
      description "PCE protocol identifier";
    }
    leaf pcep-flag-d {
      type boolean;
      description "PCEP LSP delegation flag";
    }
    leaf pcep-flag-s {
      type boolean;
      description "PCEP LSP state-sync flag";
    }
    leaf pcep-flag-r {
      type boolean;
      description "PCEP LSP remove flag";
    }
    leaf pcep-flag-a {
      type boolean;
      description "PCEP LSP admin flag";
    }
    leaf pcep-flag-o {
      type uint8;
      description "PCEP LSP operation flag";
    }
    leaf pcep-flag-c {
      type uint8;
      description "PCEP LSP initiated flag";
    }
  }

  grouping PCE-RRO-INFO {
    description "RRO information";

    container sr-rro {
      description "Segment Routing RRO info";
      uses PCE-SR-HOP-TYPE;
    }
    leaf rro-type {
      type Pce-rro;
      description "RRO Type";
    }
    leaf ipv4-address {
      type inet:ipv4-address;
      description "IPv4 address of RRO";
    }
    leaf mpls-label {
      type uint32;
      description "MPLS label of RRO";
    }
    leaf flags {
      type uint8;
      description "RRO Flags";
    }
  }

  grouping SRV6-SID-BAG {
    description "PCE SRv6 SID bag";

    container endpoint-function {
      description "Endpoint behavior of the SRv6SID";
      uses MGMT-SRV6-ENDPOINT-BEHAVIOR;
    }

    container structure {
      description "The SRv6 strucutre of the SID";
      uses SRV6-SID-STRUCTURE-BAG;
    }
    leaf srv6sid {
      type inet:ipv6-address;
      description "Full SRv6 SID";
    }
    leaf type {
      type uint8;
      description "SRv6 SID Type";
    }
    leaf flags {
      type uint8;
      description "SRv6 SID flags";
    }
    leaf algorithm {
      type uint8;
      description "Flex-Algo value used for this SRv6SID";
    }
    leaf weight {
      type uint8;
      description "Weight";
    }
  }

  grouping PCE-SR-HOP-TYPE {
    description "SR hop type";

    container local-addr {
      description "Local Address";
      uses PCE-IP-ADDR-TYPE;
    }

    container remote-addr {
      description "Remote Address";
      uses PCE-IP-ADDR-TYPE;
    }

    container srv6sid {
      description "SRv6 SID";
      uses SRV6-SID-BAG;
    }
    leaf sid-type {
      type Pce-sr-sid;
      description "SID type";
    }
    leaf mpls-label {
      type uint32;
      description "Label";
    }
    leaf local-interface-index {
      type uint32;
      description
        "SNMP index of the upstream interface of this hop";
    }
    leaf remote-interface-index {
      type uint32;
      description
        "SNMP index of the downstream interface of this
        hop";
    }
  }

  grouping PCE-RSVP-HOP-TYPE {
    description "RSVP hop type";
    leaf hop-address {
      type inet:ipv4-address;
      description "RSVP hop address";
    }
    leaf loose {
      type boolean;
      description "Loose hop";
    }
  }

  grouping PCE-ERO-INFO {
    description "ERO information";
    leaf reported-metric-type {
      type uint32;
      description "Reported Metric Type";
    }
    leaf reported-metric-value {
      type uint32;
      description "Reported Metric Value";
    }
    leaf computed-metric-type {
      type uint32;
      description "Computed Metric Type";
    }
    leaf computed-metric-value {
      type uint32;
      description "Computed Metric Value";
    }
    leaf computed-hop-list-time {
      type uint32;
      description "Computed Hop List Time";
    }

    list reported-rsvp-path {
      description "Reported RSVP path";
      uses PCE-RSVP-HOP-TYPE;
    }

    list reported-sr-path {
      description "Reported SR path";
      uses PCE-SR-HOP-TYPE;
    }

    list computed-rsvp-path {
      description "Computed RSVP path";
      uses PCE-RSVP-HOP-TYPE;
    }

    list computed-sr-path {
      description "Computed SR path";
      uses PCE-SR-HOP-TYPE;
    }

    list reverse-sr-path {
      description "reverse SR path";
      uses PCE-SR-HOP-TYPE;
    }
  }

  grouping PCE-LSP-DETAIL-INFO {
    description "Detailed LSP information";

    container brief-lsp-information {
      description "Brief LSP information";
      uses PCE-LSP-INFO;
    }

    container er-os {
      description "Paths";
      uses PCE-ERO-INFO;
    }

    container lsppcep-information {
      description "PCEP related LSP information";
      uses PCE-PCEP-INFO;
    }

    container lsp-association-info {
      description "LSP association information";
      uses PCE-ASSO-INFO;
    }

    container lsp-attributes {
      description "LSP attributes";
      uses PCE-LSPA-INFO;
    }

    container sub-delegated-pce {
      description "Sub delegated PCE";
      uses PCE-IP-ADDR-TYPE;
    }

    container state-sync-pce {
      description "State-sync PCE";
      uses PCE-IP-ADDR-TYPE;
    }

    container reporting-pcc-address {
      description "Reporting PCC address";
      uses PCE-IP-ADDR-TYPE;
    }

    container srpag-info {
      description "SR Policy Association Group";
      uses PCEP-SRPAG-BAG;
    }

    container bidir-asso-info {
      description "Bidirectional Association Group";
      uses PCEP-BIDIR-BAG;
    }

    container constraints-information {
      description "Constraints for the LSP";
      uses PCE-LSP-CONSTRAINTS-INFO;
    }
    leaf signaled-bandwidth-specified {
      type boolean;
      description "True if router notifies signal bandwidth";
    }
    leaf signaled-bandwidth {
      type uint64;
      description "Signaled Bandwidth";
    }
    leaf actual-bandwidth-specified {
      type boolean;
      description "True if router notifies actual bandwidth";
    }
    leaf actual-bandwidth {
      type uint64;
      description "Actual bandwidth utilized in the data-plane";
    }
    leaf lsp-role {
      type uint32;
      description "LSP Role";
    }
    leaf computing-pce {
      type uint32;
      description "Computing PCE";
    }
    leaf preference {
      type uint32;
      description "Preference";
    }
    leaf protection-type {
      type uint32;
      description "Protection Type";
    }
    leaf drop-upon-invalidation {
      type boolean;
      description "LSP will drop upon invalidation";
    }
    leaf invalidated-traffic-dropped {
      type boolean;
      description "Invalidated Traffic Dropped";
    }
    leaf sid-algorithm {
      type uint8;
      description
        "SID Algorithm constraint - valid only if
        SIDAlgoSet is TRUE";
    }
    leaf sid-algorithm-set {
      type boolean;
      description "Specifies if SID Algorithm constraint is set";
    }
    leaf maximum-delay {
      type uint32;
      description
        "Maximum delay constraint applicable for latency
        metric-type";
    }
    leaf block-recomputation {
      type boolean;
      description
        "TRUE if path recomputation is blocked in case of
        topology change";
    }
    leaf adjacency-sids-only {
      type boolean;
      description
        "TRUE if only adjacency SIDs may be used in the
        path-computation";
    }
    leaf grpc-service-instance {
      type string;
      description "gRPC Service Instance Name";
    }
    leaf grpc-request-id {
      type uint64;
      description
        "Request ID used for sub-delegation over gRPC api";
    }
    leaf-list srlg-info {
      type uint32;
      description "List of SLRGs used by LSP";
    }

    list rro {
      description "RRO";
      uses PCE-RRO-INFO;
    }
  }

  grouping PCE-TUN-DETAIL-BAG {
    description "Tunnel detail information";

    container pcc-address {
      description "PCC address";
      uses PCE-IP-ADDR-TYPE;
    }

    container private-lsp-information {
      description "Private LSP information";
      uses PCE-EVENT-BAG;
    }
    leaf tunnel-name-xr {
      type string;
      description "Tunnel Name";
    }
    leaf xtc-controlled {
      type boolean;
      description "Allow XTC reoptimizations";
    }
    leaf color {
      type uint32;
      description "Color";
    }
    leaf interface-name {
      type string;
      description "Interface name";
    }
    leaf profile-id {
      type uint16;
      description "Profile ID";
    }
    leaf is-zombie {
      type boolean;
      description
        "PCC has disconnected, but tunnel still kept
        around";
    }
    leaf override-rule-sequence {
      type uint32;
      description "Sequence number of the override rule";
    }

    list detail-lsp-information {
      description "Detail LSP information";
      uses PCE-LSP-DETAIL-INFO;
    }
  }

  grouping PCE-LSP-COUNTS-BAG {
    description "Number of LSPs";
    leaf all-ls-ps {
      type uint32;
      description "Number of all LSPs";
    }
    leaf up-ls-ps {
      type uint32;
      description "Number of operational LSPs";
    }
    leaf admin-up-ls-ps {
      type uint32;
      description "Number of administratively up LSPs";
    }
    leaf sr-ls-ps {
      type uint32;
      description "Number of LSPs with Segment routing setup type";
    }
    leaf rsvp-ls-ps {
      type uint32;
      description "Number of LSPs with RSVP setup type";
    }
  }

  grouping PCE-LSP-PER-PEER-SUMMARY-BAG {
    description "Number of LSPs for specific peer";

    container lsp-summary {
      description "Number of LSPs for specific peer";
      uses PCE-LSP-COUNTS-BAG;
    }

    container peer-address {
      description "Peer address";
      uses PCE-IP-ADDR-TYPE;
    }
  }

  grouping PCE-LSP-SUMMARY-BAG {
    description "PCE LSP summary information";

    container all-ls-ps {
      description "Summary for all peers";
      uses PCE-LSP-COUNTS-BAG;
    }

    list peer-ls-ps-info {
      description "Number of LSPs for specific peer";
      uses PCE-LSP-PER-PEER-SUMMARY-BAG;
    }
  }

  grouping PCE-ASSO-INFO {
    description "PCE LSP association information";

    container association-source {
      description "Association Source";
      uses PCE-IP-ADDR-TYPE;
    }
    leaf association-type {
      type uint32;
      description "Association Type";
    }
    leaf association-id {
      type uint32;
      description "Association ID";
    }
    leaf shortest-path-flag {
      type boolean;
      description "Shortest path flag indication";
    }
  }

  grouping SRV6-SID-STRUCTURE-BAG {
    description "SRv6 MicroSID Structure";
    leaf locator-block-length {
      type uint8;
      description "Block Length";
    }
    leaf locator-node-length {
      type uint8;
      description "Node Length";
    }
    leaf function-length {
      type uint8;
      description "Function Length";
    }
    leaf argument-length {
      type uint8;
      description "Argument Length";
    }
  }

  grouping MGMT-SRV6-ENDPOINT-BEHAVIOR {
    description "SRv6 Endpoint Behavior Info";
    leaf type {
      type Mgmt-srv6-endpoint;
      description "Behavior type";
    }
    leaf description {
      type string;
      description "Behavior description";
    }
  }

  grouping PCE-SRV6-BSID-INFO {
    description "SRv6 Binding SID Info";

    container binding-sid-prefix {
      description "SRv6 Binding SID prefix";
      uses PCE-IP-ADDR-TYPE;
    }

    container binding-sid-behavior {
      description "Binding SID behavior";
      uses MGMT-SRV6-ENDPOINT-BEHAVIOR;
    }

    container structure {
      description "The SRv6 strucutre of the SID";
      uses SRV6-SID-STRUCTURE-BAG;
    }
  }

  grouping PCE-LSP-INFO {
    description "LSP common information";

    container source-address {
      description "Source address";
      uses PCE-IP-ADDR-TYPE;
    }

    container destination-address {
      description "Destination address";
      uses PCE-IP-ADDR-TYPE;
    }

    container srv6-binding-sid {
      description "SRv6 Binding SID";
      uses PCE-SRV6-BSID-INFO;
    }
    leaf tunnel-id {
      type uint32;
      description "Tunnel ID";
    }
    leaf lspid {
      type uint32;
      description "LSP ID";
    }
    leaf binding-sid {
      type uint32;
      description "Binding SID";
    }
    leaf lsp-setup-type {
      type Lsp-setup;
      description "LSP Setup Type";
    }
    leaf operational-state {
      type Pcep-lsp-state;
      description "Operational state";
    }
    leaf administrative-state {
      type Lsp-state;
      description "Administrative state";
    }
    leaf msd {
      type uint32;
      description "Maximum SID Depth";
    }
    leaf absolute-margin {
      type uint32;
      description "Absolute Margin";
    }
    leaf relative-margin {
      type uint32;
      description "Relative Margin";
    }
    leaf igp-bound {
      type uint32;
      description "IGP Metric Bound";
    }
    leaf te-bound {
      type uint32;
      description "TE Metric Bound";
    }
    leaf latency-bound {
      type uint32;
      description "Latency Metric Bound";
    }
    leaf hop-count-bound {
      type uint32;
      description "HopCount Metric Bound";
    }
    leaf anycast-sid-inclusion {
      type uint32;
      description "Anycast SID Inclusion";
    }
  }

  grouping PCE-IP-ADDR-TYPE {
    description "PCE IP ADDR TYPE";
    leaf af-name {
      type Pce-af-id;
      description "AFName";
    }
    leaf ipv4 {
      when "../af-name = 'ipv4'" {
        description "../AFName = 'IPv4'";
      }
      type Pce-ipv4-address;
      description "IPv4 address type";
    }
    leaf ipv6 {
      when "../af-name = 'ipv6'" {
        description "../AFName = 'IPv6'";
      }
      type Pce-ipv6-address;
      description "IPv6 address type";
    }
  }

  grouping PCE-TUN-BAG {
    description "Tunnel information";

    container pcc-address {
      description "PCC address";
      uses PCE-IP-ADDR-TYPE;
    }
    leaf tunnel-name-xr {
      type string;
      description "Tunnel Name";
    }

    list brief-lsp-information {
      description "Brief LSP information";
      uses PCE-LSP-INFO;
    }
  }
}
