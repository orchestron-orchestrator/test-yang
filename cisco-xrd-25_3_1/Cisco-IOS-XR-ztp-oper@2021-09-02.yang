module Cisco-IOS-XR-ztp-oper {

  /*** NAMESPACE / PREFIX DEFINITION ***/

  namespace "http://cisco.com/ns/yang/Cisco-IOS-XR-ztp-oper";


  prefix "ztp-oper";

  /*** LINKAGE (IMPORTS / INCLUDES) ***/

  import cisco-semver { prefix "semver"; }

  include Cisco-IOS-XR-ztp-oper-sub1 {
    revision-date 2021-09-02;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ztp package operational data.

     This module contains definitions
     for the following management objects:
       ztp: ZTP operational data

     Copyright (c) 2013-2021 by Cisco Systems, Inc.
     All rights reserved.";

  revision "2021-09-02" {
    description
      "Added breakout mode information.";
    semver:module-version "1.1.0";
  }

  revision "2019-04-05" {
    description
      "Establish semantic version baseline.";
    semver:module-version "1.0.0";
  }

  revision "2015-11-09" {
    description
      "IOS XR 6.0 revision.";
  }

  container ztp {
    config false;
    description "ZTP operational data";

    container information {
      description "ZTP information";
      uses ZTP-INFO-BAG;
    }

    container status {
      description "ZTP Status";
      uses ZTP-STATUS-BAG;
    }
  }
}
