submodule Cisco-IOS-XR-pim-oper-sub2 {

  belongs-to Cisco-IOS-XR-pim-oper {
    prefix Cisco-IOS-XR-pim-oper;
  }

  /*** LINKAGE (IMPORTS / INCLUDES) ***/

  import ietf-inet-types { prefix "inet"; }

  import Cisco-IOS-XR-types { prefix "xr"; }

  import cisco-semver { prefix "semver"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR pim package operational data.

     Copyright (c) 2013-2023 by Cisco Systems, Inc.
     All rights reserved.";

  revision "2023-08-02" {
    description
      "Changes for IR over TE-Tunnels
       2022-12-22
         Path change for Global interface table
       2022-10-31
         New addition made for Event history show command for periodic pim packets
       2022-08-26
         Addition made for Event history for periodic pim packets
       2022-04-20
         Getting rid of default context path
       2022-02-09
         Addition of new field to pim traffic bag Cisco-IOS-XR-pim-oper";
    semver:module-version "2.0.0";
  }

  revision "2021-02-17" {
    description
      "Addition made for Sticky DR neighbor tracking";
    semver:module-version "1.1.0";
  }

  revision "2019-12-24" {
    description
      "Fixed CSCvr52977.";
    semver:module-version "1.0.0";
  }

  revision "2019-08-27" {
    description
      "Providing PIM information.";
  }

  revision "2019-04-05" {
    description
      "Establish semantic version baseline.";
  }

  revision "2015-11-09" {
    description
      "IOS XR 6.0 revision.";
  }

  typedef Ipv6-address {
    type inet:ipv6-address;
    description "IPV6 Address type";
  }
  typedef Pim-afi {
    type enumeration {
      enum ipv4-unicast {
        value 0;
        description "IP v4 unicast";
      }
      enum ipv6-unicast {
        value 1;
        description "IP v6 unicast";
      }
    }
    description "Address family";
  }
  typedef Pim-interface {
    type enumeration {
      enum encap-interface {
        value 0;
        description "Encap Interface";
      }
      enum decap-interface {
        value 1;
        description "Decap Interface";
      }
      enum mdt-interface {
        value 2;
        description "MDT Interface";
      }
    }
    description "Interface Type";
  }

  grouping PIM-MA-SUMMARY {
    description "PIM MA Summary";
    leaf is-im-connection-open {
      type boolean;
      description "IM Connection Open";
    }
    leaf is-netio-connection-open {
      type boolean;
      description "Netio Connection Open";
    }
    leaf is-edm-connection-open {
      type boolean;
      description "EDM Connection Open";
    }
    leaf is-standby-edm-connection-open {
      type boolean;
      description "Standby EDM Connection Open";
    }
    leaf encap-interface-count {
      type uint32;
      description "Encap Interface Count";
    }
    leaf decap-interface-count {
      type uint32;
      description "Decap Interface Count";
    }
    leaf mdt-interface-count {
      type uint32;
      description "MDT Interface Count";
    }
  }

  grouping PIM-ADDRTYPE {
    description "PIM ADDRTYPE";
    leaf af-name {
      type Pim-afi;
      description "AFName";
    }
    leaf ipv4-address {
      when "../af-name = 'ipv4-unicast'" {
        description "../AFName = 'IPv4Unicast'";
      }
      type inet:ipv4-address;
      description "IPv4 Address";
    }
    leaf ipv6-address {
      when "../af-name = 'ipv6-unicast'" {
        description "../AFName = 'IPv6Unicast'";
      }
      type Ipv6-address;
      description "IPV6 Address";
    }
  }

  grouping PIM-MA-IDB {
    description "PIM MA interface";

    container rp-address {
      description "RP Address";
      uses PIM-ADDRTYPE;
    }

    container source-address {
      description "Source Address";
      uses PIM-ADDRTYPE;
    }
    leaf interface-name-xr {
      type xr:Interface-name;
      description "Interface Name";
    }
    leaf vrf-name {
      type string;
      description "VRF Name";
    }
    leaf interface-type {
      type Pim-interface;
      description "Interface Type";
    }
  }
}
