module Cisco-IOS-XR-linux-security-factory-reset-act {

    namespace "http://cisco.com/ns/yang/Cisco-IOS-XR-linux-security-factory-reset-act";

    prefix "factory-reset-act";

    import Cisco-IOS-XR-types { prefix "xr"; }

    import cisco-semver { prefix "semver"; }

    organization "Cisco Systems, Inc.";

    contact
    "Cisco Systems, Inc.
     Customer Service

     Postal: 170 West Tasman Drive
     San Jose, CA 95134

     Tel: +1 800 553-NETS

     E-mail: cs-yang@cisco.com";

    description
    "This module contains a collection of YANG definitions
     for Cisco IOS-XR action package configuration.

     Copyright (c) 2022 by Cisco Systems, Inc.
     All rights reserved.";

    revision "2022-04-29" {
        description
            "IOS XR 7.8.1 revision.";
        semver:module-version "1.0.0";
    }


    rpc factory-reset-shut {
        xr:xr-task "cisco-support";
        xr:cli-command "factory-reset shutdown location <location>";
        description "Action to start factory reset on location and shut it";
        input {
            leaf location {
                type string;
                mandatory true;
                description "Location string to start reset";
            }
        }
    }

    rpc factory-reset-reload {
        xr:xr-task "cisco-support";
        xr:cli-command "factory-reset reload location <location>";
        description "Action to start factory reset on location and reload it";
        input {
            leaf location {
                type string;
                mandatory true;
                description "Location string to start reset";
            }
        }
    }
}
