module Cisco-IOS-XR-lpts-pre-ifib-oper {

  /*** NAMESPACE / PREFIX DEFINITION ***/

  namespace "http://cisco.com/ns"+
    "/yang/Cisco-IOS-XR-lpts-pre-ifib-oper";


  prefix "lpts-pre-ifib-oper";

  /*** LINKAGE (IMPORTS / INCLUDES) ***/

  import Cisco-IOS-XR-types { prefix "xr"; }

  import cisco-semver { prefix "semver"; }

  include Cisco-IOS-XR-lpts-pre-ifib-oper-sub1 {
    revision-date 2022-11-01;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR lpts-pre-ifib package operational data.

     This module contains definitions
     for the following management objects:
       lpts-pifib: lpts pre-ifib data

     Copyright (c) 2013-2022 by Cisco Systems, Inc.
     All rights reserved.";

  revision "2022-11-01" {
    description
      "Update LPTS Sub Interface punt policer data.
       2022-08-26
         Added LPTS Sub Interface punt policer data.
       2022-06-20
         Enhanced LPTS Punt Policer Per NPU data.
       2022-02-11
         LPTS Punt Policer per NPU support.
       2021-10-19
         LPTS HW FLow Policer datalist support.";
    semver:module-version "2.0.0";
  }

  revision "2020-12-03" {
    description
      "LPTS HW FLow Policer Support.";
    semver:module-version "1.2.0";
  }

  revision "2020-06-24" {
    description
      "added task-name to LptsPifib class.
      2019-11-06
         LPTS Punt Policer Support.
      2019-10-23
         LPTS Punt Policer Support.";
    semver:module-version "1.1.0";
  }

  revision "2019-04-05" {
    description
      "Establish semantic version baseline.";
    semver:module-version "1.0.0";
  }

  revision "2018-11-26" {
    description
      "LPTS Domains Support.";
  }

  revision "2017-05-01" {
    description
      "Fixing backward compatibility error in module.";
  }

  revision "2016-11-22" {
    description
      "Initial revision for pre-ifib oper yang.";
  }

  revision "2015-11-09" {
    description
      "IOS XR 6.0 revision.";
  }

  typedef Lpts-pifib {
    type enumeration {
      enum isis {
        value 0;
        description "ISIS packets";
      }
      enum ipv4-frag {
        value 1;
        description "IPv4 fragmented packets";
      }
      enum ipv4-echo {
        value 2;
        description "IPv4 ICMP Echo packets";
      }
      enum ipv4-any {
        value 3;
        description "All IPv4 packets";
      }
      enum ipv6-frag {
        value 4;
        description "IPv6 fragmented packets";
      }
      enum ipv6-echo {
        value 5;
        description "IPv6 ICMP Echo packets";
      }
      enum ipv6-nd {
        value 6;
        description "IPv6 ND packets";
      }
      enum ipv6-any {
        value 7;
        description "All IPv6 packets";
      }
      enum bfd-any {
        value 8;
        description "BFD packets";
      }
      enum all {
        value 9;
        description "All packets";
      }
    }
    description "Lpts pifib";
  }

  grouping ENTRY {
    description "Common node of type-value, shadow-entries";

    list entry {
      key "entry";
      description "Data for single pre-ifib entry";
      leaf entry {
        type xr:Cisco-ios-xr-string;
        description "Single Pre-ifib entry";
      }
      uses PIFIB-SHOW-ENTRY;
    }
  }

  container lpts-pifib {
    config false;
    description "lpts pre-ifib data";

    container nodes {
      description "List of Pre-ifib Nodes";

      list node {
        key "node-name";
        description "Pre-ifib data for particular node";

        container shadow-entries {
          description "Pre-IFIB Shadow Entries (PI)";
          uses ENTRY;
        }

        container type-values {
          description "Type specific";

          list type-value {
            key "pifib-type";
            description "pifib types";
            leaf pifib-type {
              type Lpts-pifib;
              description "Type value";
            }
            uses ENTRY;
          }
        }

        container domains {
          description "data for pre-ifib domains";
          uses PIFIB-DOMAINS-DATA;
        }

        container dynamic-flows-stats {
          description "Dynamic Flows Statistics";
          uses PIFIB-DYNFLOWS-DATA;
        }

        container punt-policer-stats {
          description "Punt Policer Statistics";
          uses PIFIB-PUNT-POLICER-DATA;
        }

        container pifib-hw-flow-policer-stats {
          description "Pifib HW Flow policer Statistics";

          list pifib-hw-flow-policer-stat {
            key "entry";
            description
              "Data for single Pifib HW Flow Policer entry";
            leaf entry {
              type xr:Cisco-ios-xr-string;
              description "Single Hw Flow Policer entry";
            }
            uses PIFIB-HW-FLOW-POLICER-DATA;
          }
        }
        leaf node-name {
          type xr:Node-id;
          description "The node name";
        }
      }
    }
  }
}
