module Cisco-IOS-XR-openconfig-vlan-ext {
  namespace "http://cisco.com/ns/yang/Cisco-IOS-XR-openconfig-vlan-ext";
  prefix oc-vlan-ext;

  import openconfig-interfaces {
    prefix oc-if;
  }
  import openconfig-vlan {
    prefix oc-vlan;
  }

  organization
    "Cisco Systems, Inc.";
  contact
    "Cisco Systems, Inc.
     Customer Service

     Postal: 170 West Tasman Drive
     San Jose, CA 95134

     Tel: +1 800 553-NETS

     E-mail: cs-yang@cisco.com";
  description
    "This module is an extension for openconfig vlan model.
     This module contains the non physical interface mode type
     which determines whether the subinterface type is l2 or l3
     subinterface.

     This module contains the enums for
     l2 and l3 subinterface type.

     Copyright (c) 2013-2023 by Cisco Systems, Inc.
     All rights reserved.";

  revision 2023-08-23 {
    description
      "adding vlan type ";
    reference
      "0.1.0";
  }


  grouping vlan-subintf-type {
    description
      "grouping for the vlan type";
    container cisco {
      description
        "vendor specific operational data that are not yet avialable in
         oc model. This container contains vlan type for specifying
         configuration of l2 subinterfaces.";
      leaf vlan-type {
        type enumeration {
          enum l3-transport {
            value 0;
            description
              "l3 virtual routing";
          }
          enum l2-transport {
            value 1;
            description
              "l2 virtual routing";
          }
        }
        description
          "vlan-type leaf represents the type of subinterface as l2 or l3";
      }
    }
  }

  augment "/oc-if:interfaces/oc-if:interface/oc-if:subinterfaces/oc-if:subinterface/oc-vlan:vlan/oc-vlan:config" {
    description
      "adding vlan subinterface type for subinterfaces";
    uses vlan-subintf-type;
  }

}
