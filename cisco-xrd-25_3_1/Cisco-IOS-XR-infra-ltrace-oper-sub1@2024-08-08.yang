submodule Cisco-IOS-XR-infra-ltrace-oper-sub1 {

  belongs-to Cisco-IOS-XR-infra-ltrace-oper {
    prefix Cisco-IOS-XR-infra-ltrace-oper;
  }

  /*** LINKAGE (IMPORTS / INCLUDES) ***/

  import cisco-semver { prefix "semver"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR infra-ltrace package operational data.

     Copyright (c) 2013-2024 by Cisco Systems, Inc.
     All rights reserved.";

  revision "2024-08-08" {
    description
      "Added Buffer fill time statistics bag";
    semver:module-version "1.0.0";
  }

  revision "2022-08-01" {
    description
      "adding schema support for infra ltrace cfg path";
  }

  revision "2019-04-05" {
    description
      "Establish semantic version baseline.";
  }

  revision "2015-11-09" {
    description
      "IOS XR 6.0 revision.";
  }

  grouping EXP-PROC-BUF-ST {
    description "EXP PROC BUF ST";
    leaf proc-name {
      type string {
        length "0..32";
      }
      description "proc name";
    }
    leaf buf-name {
      type string {
        length "0..64";
      }
      description "buf name";
    }
    leaf buf-limit {
      type uint32;
      description "buf limit";
    }
  }

  grouping LTRACE-YAML-STATS {
    description "Ltrace Yaml statistics information";
    leaf ltrace-max-memory {
      type uint32;
      description "Ltrace System max Memory Limit in MB";
    }
    leaf buffer-max-memory {
      type uint32;
      description "Ltrace Buffer max Memory Limit in KB";
    }

    list buffer {
      description "List Of Exceptional Buffers";
      uses EXP-PROC-BUF-ST;
    }
  }

  grouping LTRACE-SYNC-BG {
    description "Node Ltrace information";
    leaf shmem-total {
      type uint64;
      description "Total /dev/shmem size";
    }
    leaf shmem-shm-win {
      type uint64;
      description "Total /dev/shmem/shmwin size";
    }
    leaf shmem-image {
      type uint64;
      description "Total /dev/shmem/iosxr* size";
    }
    leaf shmem-ltrace {
      type uint64;
      description "Total /dev/shmem/ltrace size";
    }
    leaf shmem-aipc {
      type uint64;
      description "Total /dev/shmem/aipc size";
    }
    leaf shmem-sld {
      type uint64;
      description "Total /dev/shmem/sld size";
    }
    leaf shmem-subdb {
      type uint64;
      description "Total /dev/shmem/subdb size";
    }
    leaf shmem-cerrno {
      type uint64;
      description "Total /dev/shmem/cerrno size";
    }
    leaf shmem-gsp-cbp {
      type uint64;
      description "Total /dev/shmem/gspcbp size";
    }
    leaf shmem-eem {
      type uint64;
      description "Total /dev/shmem/eem size";
    }
    leaf shmem-xos {
      type uint64;
      description "Total /dev/shmem/xos* size";
    }
    leaf shmem-chkpt {
      type uint64;
      description "Total /dev/shmem/chkpt* size";
    }
    leaf shmem-cdm {
      type uint64;
      description "Total /dev/shmem/cdm* size";
    }
    leaf shmem-xipc {
      type uint64;
      description "Total /dev/shmem/XIPC* size";
    }
    leaf shmem-dll {
      type uint64;
      description "Total /dev/shmem/dll* size";
    }
    leaf shmem-syslog {
      type uint64;
      description "Total /dev/shmem/logging_buffer size";
    }
    leaf shmem-misc {
      type uint64;
      description "Total /dev/shmem/misc size";
    }
    leaf max-ltrace-size {
      type uint64;
      description "Maximum size ltrace can grow upto";
    }
    leaf ltrace-running-mode {
      type string;
      description
        "Current running Ltrace mode
        (static/dynamic/default)";
    }
    leaf ltrace-running-scalefactor {
      type uint32;
      description "Current runnig scale factor";
    }
    leaf ltrace-configured-mode {
      type string;
      description "Current configured Ltrace mode";
    }
    leaf ltrace-configured-scalefactor {
      type uint32;
      description "Current configured scale factor";
    }
  }

  grouping LTRACE-BUF-STATS {
    description "Ltrace Buffer Statistics Information";
    leaf is-complaint {
      type uint32;
      description "Is This Buffer is Compliant";
    }
    leaf unique-entry-count {
      type uint32;
      description "Unique Trace Count";
    }
    leaf unique-string-bytes {
      type uint32;
      units "byte";
      description "Unique Trace String Bytes";
    }
    leaf wrap-entry-count {
      type uint32;
      description "Wrap Trace Count";
    }
    leaf application-requested-string-bytes {
      type uint32;
      units "byte";
      description "Application Requested Wrap Trace String Bytes";
    }
    leaf infra-calculated-string-bytes {
      type uint32;
      units "byte";
      description "Infra Calculated Wrap Trace String Bytes";
    }
    leaf infra-allocated-string-bytes {
      type uint32;
      units "byte";
      description "Infra Allocted Wrap Trace String Bytes";
    }
    leaf maximum-usage {
      type uint32;
      units "byte";
      description "Maximum usage in Bytes";
    }
    leaf current-usage {
      type uint32;
      units "byte";
      description "Current usage in Bytes";
    }
    leaf ltrace-buffer-name {
      type string;
      description "Ltrace Buffer Name";
    }
    leaf process-names {
      type string;
      description "Ltrace Buffer Process Name";
    }
  }
}
