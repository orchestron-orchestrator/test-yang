submodule Cisco-IOS-XR-ip-static-ipv6-oper-sub1 {

  belongs-to Cisco-IOS-XR-ip-static-ipv6-oper {
    prefix Cisco-IOS-XR-ip-static-ipv6-oper;
  }

  /*** LINKAGE (IMPORTS / INCLUDES) ***/

  import ietf-inet-types { prefix "inet"; }

  import cisco-semver { prefix "semver"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ip-static-ipv6 package operational data.

     Copyright (c) 2013-2025 by Cisco Systems, Inc.
     All rights reserved.";

  revision "2025-04-28" {
    description
      "Added support for cross-AFI next-hops
       2023-10-20
         Fixed support for ipv6-sr-policy-detail
       2023-06-21
         Added new elements to display nodeDB and Protect events
       2022-10-31
         Added support for static srv6 sid and locator
       2021-10-29
         Added leaf node for ip address algorithm";
    semver:module-version "2.0.0";
  }

  revision "2020-11-20" {
    description
      "Added leaf node for Prefer RIB over LDP";
    semver:module-version "1.2.0";
  }

  revision "2019-12-12" {
    description
      "Added leaf node for FlexAlgo for srv6";
    semver:module-version "1.1.0";
  }

  revision "2019-06-01" {
    description
      "Added oper ipv6 support for fridb, colocation, sr-policy
      2019-05-13
         Added ipv4 support for bfd sessions, object track database and segment routing";
    semver:module-version "1.1.0";
  }

  revision "2019-04-05" {
    description
      "Establish semantic version baseline.";
    semver:module-version "1.0.0";
  }

  revision "2019-01-03" {
    description
      "Added oper ipv6 support";
  }

  revision "2015-11-09" {
    description
      "IOS XR 6.0 revision.";
  }

  typedef Mgmt-srv6-endpoint {
    type enumeration {
      enum unknown {
        value 0;
        description "Unknown Endpoint type";
      }
      enum end {
        value 1;
        description "End (no PSP/USP)";
      }
      enum end-with-psp {
        value 2;
        description "End with PSP";
      }
      enum end-with-usp {
        value 3;
        description "End with USP";
      }
      enum end-with-psp-usp {
        value 4;
        description "End with PSP/USP";
      }
      enum end-x {
        value 5;
        description "End.X (no PSP/USP)";
      }
      enum end-x-with-psp {
        value 6;
        description "End.X with PSP";
      }
      enum end-x-with-usp {
        value 7;
        description "End.X with USP";
      }
      enum end-x-with-psp-usp {
        value 8;
        description "End.X with PSP/USP";
      }
      enum end-tbl {
        value 9;
        description "End.T (no PSP/USP)";
      }
      enum end-tbl-with-psp {
        value 10;
        description "End.T with PSP";
      }
      enum end-tbl-with-usp {
        value 11;
        description "End.T with USP";
      }
      enum end-tbl-with-psp-usp {
        value 12;
        description "End.T with PSP/USP";
      }
      enum end-b6-insert {
        value 13;
        description "End.B6.Insert";
      }
      enum end-b6-encaps {
        value 14;
        description "End.B6.Encaps";
      }
      enum end-bm {
        value 15;
        description "End.BM";
      }
      enum end-dx6 {
        value 16;
        description "End.DX6";
      }
      enum end-dx4 {
        value 17;
        description "End.DX4";
      }
      enum end-dt6 {
        value 18;
        description "End.DT6";
      }
      enum end-dt4 {
        value 19;
        description "End.DT4";
      }
      enum end-dt46 {
        value 20;
        description "End.DT46";
      }
      enum end-dx2 {
        value 21;
        description "End.DX2";
      }
      enum end-dx2v {
        value 22;
        description "End.DX2V";
      }
      enum end-dt2u {
        value 23;
        description "End.DT2U";
      }
      enum end-dt2m {
        value 24;
        description "End.DT2M";
      }
      enum end-s {
        value 25;
        description "End.S";
      }
      enum end-b6-insert-red {
        value 26;
        description "End.B6.Insert.Reduced";
      }
      enum end-b6-encaps-red {
        value 27;
        description "End.B6.Encaps.Reduced";
      }
      enum end-with-usd {
        value 28;
        description "End with USD";
      }
      enum end-with-psp-usd {
        value 29;
        description "End with PSP/USD";
      }
      enum end-with-usp-usd {
        value 30;
        description "End with USP/USD";
      }
      enum end-with-psp-usp-usd {
        value 31;
        description "End with PSP/USP/USD";
      }
      enum end-x-with-usd {
        value 32;
        description "End.X with USD";
      }
      enum end-x-with-psp-usd {
        value 33;
        description "End.X with PSP/USD";
      }
      enum end-x-with-usp-usd {
        value 34;
        description "End.X with USP/USD";
      }
      enum end-x-with-psp-usp-usd {
        value 35;
        description "End.X with PSP/USP/USD";
      }
      enum end-tbl-with-usd {
        value 36;
        description "End.T with USD";
      }
      enum end-tbl-with-psp-usd {
        value 37;
        description "End.T with PSP/USD";
      }
      enum end-tbl-with-usp-usd {
        value 38;
        description "End.T with USP/USD";
      }
      enum end-tbl-with-psp-usp-usd {
        value 39;
        description "End.T with PSP/USP/USD";
      }
      enum end-op {
        value 40;
        description "End.OP";
      }
      enum end-otp {
        value 41;
        description "End.OTP";
      }
      enum un-shift-only {
        value 42;
        description "uN Shift-only";
      }
      enum un {
        value 43;
        description "uN";
      }
      enum un-psp {
        value 44;
        description "uN with PSP";
      }
      enum un-usp {
        value 45;
        description "uN with USP";
      }
      enum un-psp-usp {
        value 46;
        description "uN with PSP-USP";
      }
      enum un-usd {
        value 47;
        description "uN with USD";
      }
      enum un-psp-usd {
        value 48;
        description "uN with PSP-USD";
      }
      enum un-usp-usd {
        value 49;
        description "uN with USP-USD";
      }
      enum un-psp-usp-usd {
        value 50;
        description "uN with PSP_USP-USD";
      }
      enum ua-shift-only {
        value 51;
        description "uA Shift-only";
      }
      enum ua {
        value 52;
        description "uA";
      }
      enum ua-psp {
        value 53;
        description "uA with PSP";
      }
      enum ua-usp {
        value 54;
        description "uA with USP";
      }
      enum ua-psp-usp {
        value 55;
        description "uA with PSP-USP";
      }
      enum ua-usd {
        value 56;
        description "uA with USD";
      }
      enum ua-psp-usd {
        value 57;
        description "uA with PSP-USD";
      }
      enum ua-usp-usd {
        value 58;
        description "uA with USP-USD";
      }
      enum ua-psp-usp-usd {
        value 59;
        description "uA with PSP_USP-USD";
      }
      enum udx6 {
        value 60;
        description "uDX6";
      }
      enum udx4 {
        value 61;
        description "uDX4";
      }
      enum udt6 {
        value 62;
        description "uDT6";
      }
      enum udt4 {
        value 63;
        description "uDT4";
      }
      enum udt46 {
        value 64;
        description "uDT46";
      }
      enum udx2 {
        value 65;
        description "uDX2";
      }
      enum udx2v {
        value 66;
        description "uDX2V";
      }
      enum udt2u {
        value 67;
        description "uDT2U";
      }
      enum udt2m {
        value 68;
        description "uDT2M";
      }
      enum ub6-insert {
        value 69;
        description "uB6 Insert";
      }
      enum ub6-encaps {
        value 70;
        description "uB6 Encaps";
      }
      enum ub6-insert-red {
        value 71;
        description "uB6 Insert.Red";
      }
      enum ub6-encaps-red {
        value 72;
        description "uB6 Encaps.Red";
      }
      enum ubm {
        value 73;
        description "uBM";
      }
      enum ub6-psp-usd-insert-red {
        value 79;
        description "uB6 with PSP-USD Insert.Red";
      }
      enum ub6-psp-usd-encaps-red {
        value 80;
        description "uB6 with PSP-USD Encaps.Red";
      }
      enum utef {
        value 81;
        description "PT uTEF";
      }
      enum ub6-insert-red-shift-only {
        value 82;
        description "uB6 Insert.Red Shift-only";
      }
    }
    description "SRv6 Endpoint Behavior Type";
  }
  typedef Xtc-policy-sl {
    type enumeration {
      enum xtc-policy-sl-unkown {
        value 0;
        description "Segment List type Unknown";
      }
      enum xtc-policy-sl-srmpl-sv4 {
        value 1;
        description "Segment List type SRMPLS v4";
      }
      enum xtc-policy-sl-srmpl-sv6 {
        value 2;
        description "Segment List type SRMPLS v6";
      }
      enum xtc-policy-sl-srv6 {
        value 3;
        description "Segment List type Srv6";
      }
    }
    description "Xtc policy sl";
  }
  typedef Sr-policy-state {
    type enumeration {
      enum sr-policy-state-unknown {
        value 0;
        description "Explicit Path does not exist";
      }
      enum sr-policy-state-up {
        value 1;
        description "Explicit path exists and state is up";
      }
      enum sr-policy-state-down {
        value 2;
        description "Explicit path exists but state is down";
      }
    }
    description "Sr policy state";
  }
  typedef Object-state {
    type enumeration {
      enum object-state-unknown {
        value 0;
        description "Object does not exist";
      }
      enum object-state-down {
        value 1;
        description "Object exists but state is down";
      }
      enum object-state-up {
        value 2;
        description "Object exists and state is up";
      }
    }
    description "Object state";
  }
  typedef Interface-state {
    type enumeration {
      enum interface-none {
        value 0;
        description "Interface does not exist";
      }
      enum interface-down {
        value 1;
        description "Interface exists but IP is down";
      }
      enum interface-up {
        value 2;
        description "Interface exists and IP is up";
      }
      enum interface-unknown {
        value 3;
        description "Unknown state";
      }
    }
    description "Interface state";
  }
  typedef Explicit-path-state {
    type enumeration {
      enum explicit-path-state-unknown {
        value 0;
        description "Explicit Path does not exist";
      }
      enum explicit-path-state-up {
        value 1;
        description "Explicit path exists and state is up";
      }
      enum explicit-path-state-down {
        value 2;
        description "Explicit path exists but state is down";
      }
    }
    description "Explicit path state";
  }
  typedef Nexthop-addr {
    type string;
    description "Nexthop addr";
  }
  typedef Ipv6-static-addr-bd {
    type inet:ipv6-address;
    description "Ipv6 static addr bd";
  }
  typedef Bfd-state {
    type enumeration {
      enum next-hop-bfd-not-ready {
        description "BFD for next-hop address is not ready";
      }
      enum next-hop-bfd-down {
        description "BFD for next-hop address is down";
      }
      enum next-hop-bfd-up {
        description "BFD for next-hop address is up";
      }
    }
    description "Bfd state";
  }
  typedef Nexthop-state {
    type enumeration {
      enum next-hop-unresolved {
        description "Next-hop address is not resolved";
      }
      enum next-hop-resolved {
        description "Next-hop address is resolved";
      }
      enum next-hop-unknown {
        description "Unknown state";
      }
    }
    description "Nexthop state";
  }

  grouping MGMT-SRV6-ENDPOINT-BEHAVIOR {
    description "SRv6 Endpoint Behavior Info";
    leaf type {
      type Mgmt-srv6-endpoint;
      description "Behavior type";
    }
    leaf description {
      type string;
      description "Behavior description";
    }
  }

  grouping IP-STATIC-SIDDB-BD {
    description "static loc db";

    container srv6-endpoint-behavior {
      description "SRv6 Endpoint behavior/type";
      uses MGMT-SRV6-ENDPOINT-BEHAVIOR;
    }
    leaf sid {
      type string;
      description "sid Prefix";
    }
    leaf loc-id {
      type string;
      description "locator id";
    }
    leaf sid-context {
      type string;
      description "SRv6 Sid Context";
    }
    leaf state {
      type string;
      description "state of sid";
    }
    leaf route-res {
      type string;
      description "route send result";
    }
  }

  grouping IPV6-STATIC-XTC-DB-BD {
    description "A static SR policy DB";
    leaf state {
      type Sr-policy-state;
      description "Segment Routing Policy state";
    }
    leaf srte-ifh {
      type uint32;
      description "SRTE interface handle";
    }
    leaf binding-label {
      type uint32;
      description "SR Policy Binding label";
    }
    leaf last-policy-time {
      type uint64;
      description "Last SR Policy notification time";
    }
    leaf last-policy-state {
      type Sr-policy-state;
      description "Last SR Policy  notification state";
    }
    leaf policy-sl-type {
      type Xtc-policy-sl;
      description "Segment Routing Policy Type";
    }

    list paths {
      description "Paths referenced by this SR Policy DB";
      uses IP-STATIC-PATH-ADDR-BD;
    }
  }

  grouping IP-STATIC-COLOCATION-NODE-BD {
    description "A static co-location node";
    leaf vrf-name {
      type string;
      description "VRF Name";
    }
    leaf table-name {
      type string;
      description "Table Name";
    }
    leaf table-id {
      type uint32;
      description "colocation table id";
    }
    leaf ref-count {
      type uint32;
      description "Refrence Count";
    }
  }

  grouping IP-STATIC-COLOCATION-BD {
    description "A static co-location list";

    list colocation {
      description "Colocation List of table";
      uses IP-STATIC-COLOCATION-NODE-BD;
    }
  }

  grouping IPV6-STATIC-TEDB-BD {
    description "A static tedb";
    leaf state {
      type Explicit-path-state;
      description "Explicit path state";
    }
    leaf tunnel-ifh {
      type uint32;
      description "Tunnel interface handle";
    }
    leaf binding-label {
      type uint32;
      description "Explicit path Binding label";
    }
    leaf last-te-time {
      type uint64;
      description "Last TE notification time";
    }
    leaf last-te-state {
      type Explicit-path-state;
      description "Last TE notification state";
    }

    list paths {
      description "Paths referenced by this tedb";
      uses IP-STATIC-PATH-ADDR-BD;
    }
  }

  grouping IP-STATIC-LOCDB-BD {
    description "static loc db";
    leaf loc-name {
      type string;
      description "locator name";
    }
    leaf loc-id {
      type uint32;
      description "locator id";
    }
    leaf loc-prefix {
      type string;
      description "Locator Prefix";
    }
  }

  grouping IPV6-STATIC-OTDB-BD {
    description "A static otdb";
    leaf state {
      type Object-state;
      description "Object state";
    }
    leaf last-ot-time {
      type uint64;
      description "Last OT notification time";
    }
    leaf last-ot-state {
      type Object-state;
      description "Last OT notification state";
    }

    list paths {
      description "Paths referenced by this otdb";
      uses IP-STATIC-PATH-ADDR-BD;
    }
  }

  grouping IP-STATIC-PROT-IFH-BD {
    description "Static protect interface details";
    leaf if-name {
      type string;
      description "Interface name";
    }
  }

  grouping IPV6-STATIC-PROT-NODE-BD {
    description "static protect node details";
    leaf node-id {
      type uint32;
      description "Node value";
    }
    leaf node-name {
      type string;
      description "Location of the node";
    }

    list ifh-info {
      description "Ifh info for the node";
      uses IP-STATIC-PROT-IFH-BD;
    }
  }

  grouping IP-STATIC-TDB-BD {
    description "A static tdb";
    leaf vrf-name {
      type string;
      description "VRF Name";
    }
    leaf table-name {
      type string;
      description "VRF Name";
    }
    leaf table-id-xr {
      type uint32;
      description "table id in table database";
    }
    leaf afi {
      type uint32;
      description "AFI";
    }
    leaf safi {
      type uint32;
      description "SAFI";
    }
  }

  grouping IP-STATIC-ADDR-INFO-BD {
    description "Static address route";
    leaf addr {
      type Ipv6-static-addr-bd;
      description "IP address";
    }
    leaf prefix-len {
      type uint32;
      description "Prefix length";
    }
    leaf route-tag {
      type uint32;
      description "Static route tag";
    }
    leaf algorithm {
      type uint32;
      description "IP address algorithm";
    }
    leaf flags {
      type uint32;
      description "Flags";
    }
    leaf inactive {
      type boolean;
      description "Active/Inactive";
    }
    leaf prefix-sid {
      type boolean;
      description "Prefix SID";
    }
  }

  grouping IPV6-STATIC-IDB-BD {
    description "A static idb";

    container evt-hist {
      description "Event history of interface";
      uses EVT-HIST-INFO;
    }
    leaf vrf-name {
      type string;
      description "VRF Name";
    }
    leaf table-id {
      type uint32;
      description "interface database table id";
    }
    leaf afi {
      type uint32;
      description "AFI";
    }
    leaf safi {
      type uint32;
      description "SAFI";
    }
    leaf state {
      type Interface-state;
      description "Interface state";
    }
    leaf ifh {
      type uint32;
      description "Interface handle";
    }
    leaf last-notif-time {
      type uint64;
      description "Last IM/RSI notification time";
    }
    leaf last-if-state {
      type Interface-state;
      description "Last IM notification state";
    }
    leaf ref-count {
      type uint32;
      description "Reference count";
    }
    leaf gl-ifh {
      type uint32;
      description "Global Interface handle";
    }
    leaf im-state {
      type uint32;
      description "Interface manager state";
    }
    leaf rsi-register {
      type boolean;
      description "Registration status with RSI";
    }
    leaf-list tblid-db {
      type uint32;
      description "IDB Table ID";
    }
    leaf-list fr-tblid-db {
      type uint32;
      description "FR Table ID";
    }

    list paths {
      description "Paths referenced by this idb";
      uses IP-STATIC-PATH-ADDR-BD;
    }

    list addr-info {
      description "IP address info";
      uses IP-STATIC-ADDR-INFO-BD;
    }
  }

  grouping IPV6-STATIC-PATH-BD {
    description "A static path";
    leaf vrf-name {
      type string;
      description "VRF Name";
    }
    leaf interface {
      type string;
      description "Next-hop interface";
    }
    leaf if-resolved {
      type boolean;
      description "Interface resolved indicator";
    }
    leaf object {
      type string;
      description "Tracking object";
    }
    leaf object-resolved {
      type boolean;
      description "Object resolved indicator";
    }
    leaf exp-path {
      type string;
      description "Explicit path";
    }
    leaf next-hop {
      type Nexthop-addr;
      description "Next-hop address";
    }
    leaf nh-resolved {
      type boolean;
      description "Next-hop resolved indicator";
    }
    leaf path-tag {
      type uint32;
      description "Protocol tag";
    }
    leaf path-flags {
      type uint32;
      description "Topology path flags";
    }
    leaf distance {
      type uint32;
      description "Administrative distance";
    }
    leaf ref-count {
      type uint32;
      description "Reference count";
    }
    leaf metric {
      type uint32;
      description "UCMP Metric";
    }
    leaf status {
      type uint32;
      description "Path Status";
    }
    leaf rib-time {
      type uint64;
      description "RIB add or delete time";
    }
    leaf version {
      type uint32;
      description "Path version";
    }
    leaf index {
      type string;
      description "OC index";
    }
    leaf local-label {
      type uint32;
      description "Route local Label";
    }
    leaf last-notif-time {
      type uint64;
      description "Last IM notification time";
    }
    leaf last-rib-time {
      type uint64;
      description "Last RIB notification time for nh";
    }
    leaf last-rib-result {
      type uint64;
      description "Last RIB batch result";
    }
    leaf last-bfd-state {
      type Bfd-state;
      description "State of bfd session";
    }
    leaf last-bfd-time {
      type uint64;
      description "Last BFD notification time";
    }
    leaf path-state {
      type Explicit-path-state;
      description "explicit path status";
    }
    leaf last-te-time {
      type uint64;
      description "Last TE notification time";
    }
    leaf algorithm {
      type uint32;
      description "FlexAlgo value, Valid only for ipv6_static";
    }
    leaf prefer-rib-over-ldp {
      type boolean;
      description "Give precedence to RIB over LDP";
    }
    leaf non-recurse {
      type boolean;
      description "Recurse lookup of nexthop disabled";
    }
  }

  grouping IPV6-STATIC-ROUTE-BD {
    description "A static route";

    container evt-hist {
      description "Event history of topology";
      uses EVT-HIST-INFO;
    }
    leaf vrf-name {
      type string;
      description "VRF Name";
    }
    leaf table-id {
      type uint32;
      description "Table id of static route";
    }
    leaf afi {
      type uint32;
      description "AFI";
    }
    leaf safi {
      type uint32;
      description "SAFI";
    }
    leaf best-distance {
      type uint32;
      description "Administrative distance of best path";
    }
    leaf last-tdb-time {
      type uint64;
      description "Last event occured on the tdb";
    }

    list paths {
      description "Path(s) of the route";
      uses IPV6-STATIC-PATH-BD;
    }
  }

  grouping IP-STATIC-NHDB-BFD-STAT-BD {
    description "BFD session stats";
    leaf session-up-cnt {
      type uint32;
      description "# of state change to up";
    }
    leaf session-down-cnt {
      type uint32;
      description "# of state change to down";
    }
  }

  grouping IPV6-STATIC-NHDB-BFD-BD {
    description "A static nhdb bfd session";

    container bfd-stat {
      description "Stat of bfd session";
      uses IP-STATIC-NHDB-BFD-STAT-BD;
    }
    leaf vrf-name {
      type string;
      description "VRF Name";
    }
    leaf table-id {
      type uint32;
      description "next-hop bfd table id";
    }
    leaf afi {
      type uint32;
      description "AFI";
    }
    leaf safi {
      type uint32;
      description "SAFI";
    }
    leaf ifh {
      type uint32;
      description "Interface handle";
    }
    leaf bfd-interval {
      type uint32;
      description "BFD hello interval";
    }
    leaf bfd-multiplier {
      type uint32;
      description "BFD multiplier";
    }
    leaf bfd-multihop {
      type boolean;
      description "BFD multihop";
    }
    leaf bfd-state {
      type Bfd-state;
      description "State of bfd session";
    }
    leaf bfd-source {
      type Ipv6-static-addr-bd;
      description "Multihop session source IP";
    }
  }

  grouping IP-STATIC-PROT-INTF-PATHS-BD {
    description "Static protect interface paths";
    leaf prefix {
      type Ipv6-static-addr-bd;
      description "Interface path prefix address";
    }
    leaf prefix-len {
      type uint8;
      description "Interface path prefix length";
    }
    leaf rib-update-time {
      type uint64;
      description "Last time path was updated to RIB (in nsec)";
    }
  }

  grouping IPV6-STATIC-PROT-INTF-EVENT-BD {
    description "Static protect interface paths";

    container evt-hist {
      description "Event history for the interface on the node";
      uses EVT-HIST-INFO;
    }
    leaf node-id {
      type uint32;
      description "Node value";
    }
    leaf node-name {
      type string;
      description "Location of the node";
    }
    leaf if-name {
      type string;
      description "Interface name";
    }

    list paths {
      description "Paths associated for that interface";
      uses IP-STATIC-PROT-INTF-PATHS-BD;
    }
  }

  grouping EVT-HIST-ENTRY {
    description "Event history Entry";
    leaf evt-timestamp {
      type string;
      description "The timestamp of the event";
    }
    leaf evt-name {
      type string;
      description "Event name";
    }
    leaf evt-type {
      type uint8;
      description "Event type";
    }
    leaf evt-many {
      type boolean;
      description "Multiple instance flag";
    }
    leaf evt-sticky {
      type boolean;
      description "Sticky flag";
    }
    leaf-list evt-data {
      type uint32;
      description "Optional data";
    }
  }

  grouping EVT-HIST-INFO {
    description "Per object event history";
    leaf evt-class-name {
      type string;
      description "Class name string";
    }
    leaf evt-granularity-ms {
      type uint32;
      units "millisecond";
      description "Granularity of timestamps, in milliseconds";
    }

    list evt-entry {
      description "Array of event entries";
      uses EVT-HIST-ENTRY;
    }
  }

  grouping IP-STATIC-PATH-BFD-BD {
    description "A static bfd";
    leaf enable {
      type boolean;
      description "TRUE if bfd is enabled";
    }
  }

  grouping IP-STATIC-PATH-ADDR-BD {
    description "Static address path";
    leaf prefix {
      type Ipv6-static-addr-bd;
      description "The path's prefix address";
    }
    leaf prefix-len {
      type uint8;
      description "The path's prefix length";
    }
    leaf vrf-name {
      type string;
      description "VRF Name";
    }
  }

  grouping IPV6-STATIC-NHDB-BD {
    description "A static nhdb";

    container evt-hist {
      description "Event history of next-hop";
      uses EVT-HIST-INFO;
    }
    leaf vrf-name {
      type string;
      description "VRF Name";
    }
    leaf table-id {
      type uint32;
      description "next-hop table id";
    }
    leaf afi {
      type uint32;
      description "AFI";
    }
    leaf safi {
      type uint32;
      description "SAFI";
    }
    leaf state {
      type Nexthop-state;
      description "Next-hop address state";
    }
    leaf conn-state {
      type Nexthop-state;
      description "Next-hop address connected state";
    }
    leaf ifh {
      type uint32;
      description "Interface handleto which RIB resolves this";
    }
    leaf conn-ifh {
      type uint32;
      description "Interface handle to which this is connected";
    }
    leaf conn-ref-count {
      type uint32;
      description
        "Number of paths for which conn_state is resolved";
    }
    leaf bfd-interval {
      type uint32;
      description "BFD hello interval";
    }
    leaf bfd-multiplier {
      type uint32;
      description "BFD multiplier";
    }
    leaf bfd-state {
      type Bfd-state;
      description "State of bfd session";
    }
    leaf last-rib-time {
      type uint64;
      description "Last RIB notification time";
    }
    leaf last-rib-state {
      type Nexthop-state;
      description "Last RIB notification state";
    }
    leaf last-bfd-time {
      type uint64;
      description "Last BFD notification time";
    }
    leaf last-bfd-state {
      type Bfd-state;
      description "Last BFD notification state";
    }

    list paths {
      description "Paths referenced by this nhdb";
      uses IP-STATIC-PATH-ADDR-BD;
    }

    list bfds {
      description "Paths bfd state";
      uses IP-STATIC-PATH-BFD-BD;
    }
  }

  grouping IP-STATIC-FRIDB-BD {
    description "A static fridb";
    leaf if-name {
      type string;
      description "Interface name";
    }
    leaf if-handle {
      type uint32;
      description "Interface handle";
    }
    leaf-list tblid-db {
      type uint32;
      description "Table ID database";
    }
  }
}
