module Cisco-IOS-XR-linux-xlnc-act {

  /*** NAMESPACE / PREFIX DEFINITION ***/

  namespace "http://cisco.com/ns"+
    "/yang/Cisco-IOS-XR-linux-xlnc-act";

  prefix "linux-xlnc-act";

  /*** LINKAGE (IMPORTS / INCLUDES) ***/

  import Cisco-IOS-XR-types { prefix "xr"; }

  import cisco-semver { prefix "semver"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR linux-xlnc action commands.

     Copyright (c) 2023 by Cisco Systems, Inc.
     All rights reserved.";

  revision "2023-11-14" {
    description
      "First implementation clearing XLNC status";
    semver:module-version "1.0.0";
  }


  /*** Action commands. ***/

  rpc clear-status {
    xr:xr-task "interface & network";
    description
      "Clear current XLNC status";
    input {
      leaf interface {
        type xr:Interface-name;
        must 'not(../vrf)';
        description "Interface name";
      }
      leaf vrf {
        type string {
          length "1..32";
        }
        must 'not(../interface)';
        description "VRF name";
      }
    }
  }
}
