module Cisco-IOS-XR-lib-type6-cfg {

  /*** NAMESPACE / PREFIX DEFINITION ***/

  namespace "http://cisco.com/ns/yang/Cisco-IOS-XR-lib-type6-cfg";


  prefix "lib-type6-cfg";

  /*** LINKAGE (IMPORTS / INCLUDES) ***/

  import cisco-semver { prefix "semver"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR lib-type6 package configuration.

     This module contains definitions
     for the following management objects:
       password6: Configure masterkey

     Copyright (c) 2013-2019 by Cisco Systems, Inc.
     All rights reserved.";

  revision "2019-04-05" {
    description
      "Establish semantic version baseline.";
    semver:module-version "1.0.0";
  }

  revision "2018-09-22" {
    description
      "Fixed type translation error.";
  }

  revision "2015-11-09" {
    description
      "IOS XR 6.0 revision.";
  }

  typedef Password-encryption {
    type enumeration {
      enum type6 {
        value 2;
        description "Type6";
      }
    }
    description "Password encryption";
  }

  container password6 {
    description "Configure masterkey";

    container encryption {
      description "Enable password encryption";
      leaf aes {
        type Password-encryption;
        description "encryption type used to store key";
      }
    }
  }
}
