submodule Cisco-IOS-XR-spirit-corehelper-context-oper-sub1 {

  belongs-to Cisco-IOS-XR-spirit-corehelper-context-oper {
    prefix Cisco-IOS-XR-spirit-corehelper-context-oper;
  }

  /*** LINKAGE (IMPORTS / INCLUDES) ***/

  import cisco-semver { prefix "semver"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR spirit-corehelper-context package operational data.

     Copyright (c) 2013-2020 by Cisco Systems, Inc.
     All rights reserved.";

  revision "2020-10-01" {
    description
      "Adding show context yang model";
    semver:module-version "1.0.0";
  }

  revision "2019-04-05" {
    description
      "Establish semantic version baseline.";
  }

  revision "2015-11-09" {
    description
      "IOS XR 6.0 revision.";
  }

  grouping COREHELPER-CONTEXT-CONTEXT {
    description "Show context output";
    leaf context {
      type string {
        length "0..4096";
      }
      description "output of show context";
    }
  }
}
