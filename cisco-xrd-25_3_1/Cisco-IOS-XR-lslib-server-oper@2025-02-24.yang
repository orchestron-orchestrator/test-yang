module Cisco-IOS-XR-lslib-server-oper {

  /*** NAMESPACE / PREFIX DEFINITION ***/

  namespace "http://cisco.com/ns"+
    "/yang/Cisco-IOS-XR-lslib-server-oper";


  prefix "lslib-server-oper";

  /*** LINKAGE (IMPORTS / INCLUDES) ***/

  import Cisco-IOS-XR-types { prefix "xr"; }

  import cisco-semver { prefix "semver"; }

  include Cisco-IOS-XR-lslib-server-oper-sub1 {
    revision-date 2025-02-24;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR lslib-server package operational data.

     This module contains definitions
     for the following management objects:
       lslib-server: LSLIB Server operational data

     Copyright (c) 2013-2025 by Cisco Systems, Inc.
     All rights reserved.";

  revision "2025-02-24" {
    description
      "Added producer name and total count in producer stats. Modified unknown_error as unknown_nlri_error_count";
    semver:module-version "1.0.0";
  }

  revision "2025-02-14" {
    description
      "Made uptime as string and added producer name leaf";
  }

  revision "2025-02-12" {
    description
      "Added total count of NLRI in producer details oper.";
  }

  revision "2024-10-28" {
    description
      "Initial Oper yang";
  }

  revision "2019-04-05" {
    description
      "Establish semantic version baseline.";
  }

  revision "2015-11-09" {
    description
      "IOS XR 6.0 revision.";
  }

  container lslib-server {
    config false;
    description "LSLIB Server operational data";

    container producer-lsdb-statistics {
      description
        "Statistics information about the NLRIs present
        in LSDB from Producers";

      list producer-lsdb-statistic {
        description
          "Statistics information about the NLRIs present
          in LSDB from one Producer";
        leaf inst-id {
          type uint32 {
            range "0..4294967295";
          }
          description "Instance Identifier";
        }
        leaf prod-proc {
          type uint32 {
            range "1..8";
          }
          description "Producer Process";
        }
        uses LSLIB-SERVER-SHOW-PROD-STATS;
      }
    }

    container producer-histories {
      description "Information about disconnected LSLIB Producers";

      list producer-history {
        description "Information about a particular LSLIB Producer";
        leaf inst-id {
          type uint32 {
            range "0..4294967295";
          }
          description "Instance Identifier";
        }
        leaf prod-proc {
          type uint32 {
            range "1..8";
          }
          description "Producer Process";
        }
        uses LSLIB-SERVER-SHOW-PRODUCER;
      }
    }

    container memory-chunks {
      description "Information about Memory Chunks";

      list memory-chunk {
        key "chunk-name";
        description "Information about a particular Memory Chunk";
        leaf chunk-name {
          type xr:Cisco-ios-xr-string;
          description "Name of Chunk memory";
        }
        uses LSLIB-SERVER-MEM-CHUNK;
      }
    }

    container clients {
      description "Information about active clients";

      list client {
        key "client-id";
        description "Information about a particular active client";
        leaf client-id {
          type uint32 {
            range "1..4294967295";
          }
          description "Client Identifier";
        }
        uses LSLIB-SERVER-SHOW-CLIENT;
      }
    }

    container client-histories {
      description "Information about disconnected clients";

      list client-history {
        key "client-id";
        description
          "Information about a particular disconnected
          client";
        leaf client-id {
          type uint32 {
            range "1..4294967295";
          }
          description "Client Identifier";
        }
        uses LSLIB-SERVER-SHOW-CLIENT;
      }
    }

    container producers {
      description "Information about LSLIB Producers";

      list producer {
        description "Information about a particular LSLIB Producer";
        leaf inst-id {
          type uint32 {
            range "0..4294967295";
          }
          description "Instance Identifier";
        }
        leaf prod-proc {
          type uint32 {
            range "1..8";
          }
          description "Producer Process";
        }
        uses LSLIB-SERVER-SHOW-PRODUCER;
      }
    }

    container nlri-lsdb-statistics {
      description
        "Statistics information about the NLRIs present
        in LSDB";
      uses LSLIB-SERVER-SHOW-LSDB-STATS;
    }

    container memory-heaps {
      description "Information about Memory Heaps";

      list memory-heap {
        key "heap-name";
        description "Information about a particular Memory Heap";
        leaf heap-name {
          type xr:Cisco-ios-xr-string;
          description "Name of Heap memory";
        }
        uses LSLIB-SERVER-MEM-HEAP;
      }
    }
  }
}
