module Cisco-IOS-XR-gil-ma-oper {

  /*** NAMESPACE / PREFIX DEFINITION ***/

  namespace "http://cisco.com/ns/yang/Cisco-IOS-XR-gil-ma-oper";


  prefix "gil-ma-oper";

  /*** LINKAGE (IMPORTS / INCLUDES) ***/

  import Cisco-IOS-XR-types { prefix "xr"; }

  import cisco-semver { prefix "semver"; }

  include Cisco-IOS-XR-gil-ma-oper-sub1 {
    revision-date 2023-03-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR gil-ma package operational data.

     This module contains definitions
     for the following management objects:
       generic-interface-list: GenericInterfaceList Management Agent
         Operational Table

     Copyright (c) 2013-2023 by Cisco Systems, Inc.
     All rights reserved.";

  revision "2023-03-09" {
    description
      "Initial GIL MA Support";
    semver:module-version "1.0.0";
  }

  revision "2019-04-05" {
    description
      "Establish semantic version baseline.";
  }

  revision "2015-11-09" {
    description
      "IOS XR 6.0 revision.";
  }

  container generic-interface-list {
    config false;
    description
      "GenericInterfaceList Management Agent Operational
      Table";

    container capability {
      description "Generic interface list platform capabilities";
      uses GIL-MA-PDCAP;
    }

    container ports {
      description "Generic interface list port table";

      list port {
        key "interface-name";
        description "Interface name";
        leaf interface-name {
          type xr:Interface-name;
          description "Interface Name";
        }
        uses GIL-MA-PORT;
      }
    }

    container idbs {
      description "Generic interface list idb table";

      list idb {
        key "interface-name";
        description "Interface name";
        leaf interface-name {
          type xr:Interface-name;
          description "Interface Name";
        }
        uses GIL-MA-IDB;
      }
    }
  }
}
