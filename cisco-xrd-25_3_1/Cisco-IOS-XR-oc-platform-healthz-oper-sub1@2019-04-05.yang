submodule Cisco-IOS-XR-oc-platform-healthz-oper-sub1 {

  belongs-to Cisco-IOS-XR-oc-platform-healthz-oper {
    prefix Cisco-IOS-XR-oc-platform-healthz-oper;
  }

  /*** LINKAGE (IMPORTS / INCLUDES) ***/

  import cisco-semver { prefix "semver"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR oc-platform-healthz package operational data.

     Copyright (c) 2013-2019 by Cisco Systems, Inc.
     All rights reserved.";

  revision "2019-04-05" {
    description
      "Establish semantic version baseline.";
    semver:module-version "1.0.0";
  }

  revision "2015-11-09" {
    description
      "IOS XR 6.0 revision.";
  }

  typedef Openconfig-platform-healthz-status-enum {
    type enumeration {
      enum unspecified {
        value 0;
        description
          "The component's health status has not yet been
          checked by the system.";
      }
      enum healthy {
        value 1;
        description
          "The component is in a HEALTHY state, and is
          operating within the expected parameters.";
      }
      enum unhealthy {
        value 2;
        description
          "The component is in a unhealthy state, it is
          not performing the function expected of it.";
      }
    }
    description "Openconfig platform healthz status enum";
  }
  typedef Yang2bag-string {
    type string;
    description "Yang2bag string";
  }

  grouping HEALTHZ-STATE {
    description "HEALTHZ STATE";
    leaf status {
      type Openconfig-platform-healthz-status-enum;
      description
        "The status of the component, indicating its
        current health";
    }
    leaf last-unhealthy {
      type uint64;
      units "nanosecond";
      description
        "The time at which the component as last observed
        to be unhealthy represented as nanoseconds since
        the Unix epoch";
    }
    leaf unhealthy-count {
      type uint64;
      description
        "The number of status checks that have determined
        this component to be in an unhealthy state";
    }
  }

  grouping OVERLAY-OC-PLATFORM-HEALTHZ-HEALTHZ {
    description "The health of the component";

    container state {
      description
        "Operational state parameters relating to
        component health";
      uses HEALTHZ-STATE;
    }
  }

  grouping OVERLAY-OC-PLATFORM-HEALTHZ-STATE {
    description "Operational state data for each component";
    leaf name {
      type Yang2bag-string;
      description
        "Device name for the component -- this may not be
        a configurable parameter on many implementations";
    }
    leaf type {
      type Yang2bag-string;
      description "Type of component as identified by the system";
    }
    leaf location {
      type Yang2bag-string;
      description
        "System-supplied description of the location of
        the component within the system";
    }
    leaf mfg-name {
      type Yang2bag-string;
      description
        "System-supplied identifier for the manufacturer
        of the component";
    }
    leaf parent {
      type Yang2bag-string;
      description "Reference to the name of the parent component";
    }
  }

  grouping STATE {
    description "STATE";
    leaf name {
      type Yang2bag-string;
      description "Reference to the name of the subcomponent";
    }
  }

  grouping OVERLAY-OC-PLATFORM-HEALTHZ-SUBCOMPONENT {
    description "List of subcomponent references";

    container state {
      description "Operational state data for the subcomponent";
      uses STATE;
    }
  }
}
