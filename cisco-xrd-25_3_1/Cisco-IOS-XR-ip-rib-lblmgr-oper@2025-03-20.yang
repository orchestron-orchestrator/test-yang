module Cisco-IOS-XR-ip-rib-lblmgr-oper {

  /*** NAMESPACE / PREFIX DEFINITION ***/

  namespace "http://cisco.com/ns"+
    "/yang/Cisco-IOS-XR-ip-rib-lblmgr-oper";


  prefix "ip-rib-lblmgr-oper";

  /*** LINKAGE (IMPORTS / INCLUDES) ***/

  import Cisco-IOS-XR-types { prefix "xr"; }

  import cisco-semver { prefix "semver"; }

  include Cisco-IOS-XR-ip-rib-lblmgr-oper-sub2 {
    revision-date 2025-03-20;
  }

  include Cisco-IOS-XR-ip-rib-lblmgr-oper-sub1 {
    revision-date 2025-03-20;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ip-rib-lblmgr package operational data.

     This module contains definitions
     for the following management objects:
       rib-manager: RIB Manager operational data

     Copyright (c) 2013-2025 by Cisco Systems, Inc.
     All rights reserved.";

  revision "2025-03-20" {
    description
      "Added label producer info to RIB EDM routes";
    semver:module-version "1.0.0";
  }

  revision "2025-01-06" {
    description
      "Optimized route and path schema";
  }

  revision "2024-11-22" {
    description
      "Added option to display MPLS routes with pending delete NHGs";
  }

  revision "2024-10-29" {
    description
      "Added last clear time of rib statistics";
  }

  revision "2024-10-01" {
    description
      "Add potential label routes";
  }

  revision "2024-08-16" {
    description
      "Added label-summary";
  }

  revision "2024-07-11" {
    description
      "Add unviable label routes";
  }

  revision "2024-02-15" {
    description
      "New rib-manager schema";
  }

  revision "2024-02-06" {
    description
      "New label-manager schema";
  }

  revision "2019-04-05" {
    description
      "Establish semantic version baseline.";
  }

  revision "2015-11-09" {
    description
      "IOS XR 6.0 revision.";
  }

  grouping MPLS {
    description "Common node of active, standby, node";

    container mpls {
      description "MPLS Routing Information";

      container labels {
        description "Label table";

        list label {
          key "label-key";
          description "Data for label";
          leaf label-key {
            type uint32 {
              range "0..1048575";
            }
            description "Label value";
          }
          uses LBL-INFO;
        }
      }

      container label-summary {
        description "Label Summary";
        uses LBLMGR-SUMMARY;
      }

      container forwardings {
        description "Label forwarding table";

        list forwarding {
          key "label-key";
          description "Forwarding information of a specific label ";
          leaf label-key {
            type uint32 {
              range "0..1048575";
            }
            description "Label value";
          }
          uses RIB-EDM-ROUTE;
        }
      }

      container unviables {
        description "Unviable label forwarding entry table";

        list unviable {
          key "label-key";
          description
            "Unviable forwarding information for a specific
            label";
          leaf label-key {
            type uint32 {
              range "0..1048575";
            }
            description "Label value";
          }
          uses RIB-EDM-ROUTE;
        }
      }

      container pending-nhgs {
        description "Forwarding entries with pending NHGs table";

        list pending-nhg {
          key "label-key";
          description
            "Potential NHG information for a specific label";
          leaf label-key {
            type uint32 {
              range "0..1048575";
            }
            description "Label value";
          }
          uses RIB-EDM-ROUTE;
        }
      }

      container potentials {
        description "Potential label forwarding entry table";

        list potential {
          key "label-key";
          description
            "Potential forwarding information for a
            specific label";
          leaf label-key {
            type uint32 {
              range "0..1048575";
            }
            description "Label value";
          }
          uses RIB-EDM-ROUTE;
        }
      }
    }
  }

  container rib-manager {
    config false;
    description "RIB Manager operational data";

    container nodes {
      description "Location for RIB Manager operational data";

      list node {
        key "node-name";
        description
          "The RIB Manager operational data for a
          particular node";
        leaf node-name {
          type xr:Node-id;
          description "The identifier for the node";
        }
        uses MPLS;
      }
    }

    container global {
      description "Global RIB Manager operational data";

      container active {
        description "Active RIB Manager operational data";
        uses MPLS;
      }

      container standby {
        description "Standby RIB Manager operational data";
        uses MPLS;
      }
    }
  }
}
