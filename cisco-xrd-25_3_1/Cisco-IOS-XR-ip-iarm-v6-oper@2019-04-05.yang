module Cisco-IOS-XR-ip-iarm-v6-oper {

  /*** NAMESPACE / PREFIX DEFINITION ***/

  namespace "http://cisco.com/ns/yang/Cisco-IOS-XR-ip-iarm-v6-oper";


  prefix "ip-iarm-v6-oper";

  /*** LINKAGE (IMPORTS / INCLUDES) ***/

  import ietf-inet-types { prefix "inet"; }

  import Cisco-IOS-XR-types { prefix "xr"; }

  import cisco-semver { prefix "semver"; }

  include Cisco-IOS-XR-ip-iarm-v6-oper-sub1 {
    revision-date 2019-04-05;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ip-iarm-v6 package operational data.

     This module contains definitions
     for the following management objects:
       ipv6arm: IPv6 Address Repository Manager (IPv6 ARM)
         operational data

     Copyright (c) 2013-2019 by Cisco Systems, Inc.
     All rights reserved.";

  revision "2019-04-05" {
    description
      "Establish semantic version baseline.";
    semver:module-version "1.0.0";
  }

  revision "2019-01-22" {
    description
      "Fixing yang usability issues.";
  }

  revision "2017-05-01" {
    description
      "Fixing backward compatibility error in module.";
  }

  revision "2016-12-19" {
    description
      "IOS XR 6.2.1 revision.";
  }

  revision "2015-11-09" {
    description
      "IOS XR 6.0 revision.";
  }

  typedef Ipv6arm-prefix-length {
    type uint32 {
      range "0..128";
    }
    description "Ipv6arm prefix length";
  }

  container ipv6arm {
    config false;
    description
      "IPv6 Address Repository Manager (IPv6 ARM)
      operational data";

    container addresses {
      description "IPv6 ARM address database information";

      container vrfs {
        description "IPv6 ARM address database information per VRF";

        list vrf {
          key "vrf-name";
          description
            "IPv6 ARM address database information in a VRF";

          container networks {
            description
              "IPv6 ARM address database information by
              network";

            list network {
              description "An IPv6 Address in IPv6 ARM";
              leaf address {
                type inet:ipv6-address-no-zone;
                description "Ipv6 Address in the Network";
              }
              leaf prefix-length {
                type Ipv6arm-prefix-length;
                description
                  "IPv6 Arm prefix length for this address in
                  the Network";
              }
              leaf interface {
                type xr:Interface-name;
                description
                  "Ingress/Egress interface handle for this
                  address in the Network";
              }
              uses IP-ARM-EDM-DB-NET-BAG-TYPE;
            }
          }

          container interfaces {
            description
              "IPv6 ARM address database information by
              interface";

            list interface {
              key "interface";
              description "An IPv6 address in IPv6 ARM";
              leaf interface {
                type xr:Interface-name;
                description "Interface";
              }
              uses IP-ARM-EDM-DB-IF-BAG-TYPE;
            }
          }
          leaf vrf-name {
            type xr:Cisco-ios-xr-string {
              length "1..32";
            }
            description "VRF name";
          }
        }
      }
    }

    container summary {
      description "IPv6 ARM summary information";
      uses IP-ARM-EDM-SUMMARY-BAG-TYPE;
    }

    container vrf-summaries {
      description "IPv6 ARM VRFs summary information";

      list vrf-summary {
        key "vrf-name";
        description "IPv6 ARM VRF summary information";
        leaf vrf-name {
          type xr:Cisco-ios-xr-string {
            length "1..32";
          }
          description "VRF name";
        }
        uses IP-ARM-EDM-DB-VRF-BAG-TYPE;
      }
    }
    leaf multicast-host-interface {
      type xr:Interface-name;
      description "Interface Handle of Default Multicast Host";
    }
  }
}
