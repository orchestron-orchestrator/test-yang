submodule Cisco-IOS-XR-l2-eth-infra-oper-sub3 {

  belongs-to Cisco-IOS-XR-l2-eth-infra-oper {
    prefix Cisco-IOS-XR-l2-eth-infra-oper;
  }

  /*** LINKAGE (IMPORTS / INCLUDES) ***/

  import ietf-yang-types { prefix "yang"; }

  import cisco-semver { prefix "semver"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR l2-eth-infra package operational data.

     Copyright (c) 2013-2022 by Cisco Systems, Inc.
     All rights reserved.";

  revision "2022-03-11" {
    description
      "Added leaf number-of-ranges indicating count of vlan-ranges in tags-to-match.
       2021-07-07
         Added hardware timestamp support for MAC accounting stats.";
    semver:module-version "1.1.0";
  }

  revision "2019-04-05" {
    description
      "Establish semantic version baseline.";
    semver:module-version "1.0.1";
  }

  revision "2015-11-09" {
    description
      "IOS XR 6.0 revision.";
  }

  grouping MAC-ACC-STATS {
    description "Per MAC address stats information";
    leaf mac-address {
      type yang:mac-address;
      description "48bit MAC address";
    }
    leaf packets {
      type uint64;
      description "Number of packets counted";
    }
    leaf bytes {
      type uint64;
      units "byte";
      description "Number of bytes counted";
    }
    leaf hardware-timestamp {
      type uint64;
      units "millisecond";
      description
        "Time when MAC counters were last read from
        hardware (in msecs)";
    }
  }

  grouping MAC-ACC-INTF-INFO {
    description "Per interface MAC accounting information";
    leaf is-ingress-enabled {
      type boolean;
      description "MAC accounting on on ingress";
    }
    leaf is-egress-enabled {
      type boolean;
      description "MAC accounting on on egress";
    }
    leaf number-available-ingress {
      type uint32;
      description "MAC accounting entries available on ingress";
    }
    leaf number-available-egress {
      type uint32;
      description "MAC accounting entries available on egress";
    }
    leaf number-available-on-node {
      type uint32;
      description "MAC accountng entries available across the node";
    }
  }

  grouping MAC-ACC-INTF {
    description
      "All MAC accounting information and statistics for
      an interface";

    container state {
      description "MAC accounting state for the interface";
      uses MAC-ACC-INTF-INFO;
    }

    list ingress-statistic {
      description "Ingress MAC accounting statistics";
      uses MAC-ACC-STATS;
    }

    list egress-statistic {
      description "Egress MAC accounting statistics";
      uses MAC-ACC-STATS;
    }
  }
}
