module Cisco-IOS-XR-manageability-object-tracking-datatypes {

  /*** NAMESPACE / PREFIX DEFINITION ***/

  namespace "http://cisco.com/ns/yang"+
    "/Cisco-IOS-XR-manageability-object-tracking-datatypes";


  prefix "manageability-object-tracking-datatypes";

  /*** LINKAGE (IMPORTS / INCLUDES) ***/

  import cisco-semver { prefix "semver"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of generally useful
     derived YANG data types.

     Copyright (c) 2013-2019 by Cisco Systems, Inc.
     All rights reserved.";

  revision "2019-11-22" {
    description
      "Changed Track Name type from String to Identifier.";
    semver:module-version "2.0.0";
  }

  revision "2019-04-05" {
    description
      "Establish semantic version baseline.";
    semver:module-version "1.0.0";
  }

  revision "2017-05-01" {
    description
      "Fixing backward compatibility error in module.";
  }

  revision "2015-11-09" {
    description
      "IOS XR 6.0 revision.";
  }

  typedef Object-tracking-boolean-sign {
    type enumeration {
      enum without-not {
        value 0;
        description "Object without not";
      }
      enum with-not {
        value 1;
        description "Object with not";
      }
    }
    description "Object tracking boolean sign";
  }
  typedef Object-tracking-address-family {
    type enumeration {
      enum ipv4-unicast {
        value 0;
        description "IPv4 unicast address family";
      }
      enum ipv4-multicast {
        value 1;
        description "IPv4 multicast address family";
      }
      enum ipv4-labeled-unicast {
        value 2;
        description "IPv4 labeled-unicast address family";
      }
      enum ipv4-tunnel {
        value 3;
        description "IPv4 tunnel address family";
      }
      enum vpnv4-unicast {
        value 4;
        description "VPNv4 unicast address family";
      }
      enum ipv6-unicast {
        value 5;
        description "IPv6 unicast address family";
      }
      enum ipv6-multicast {
        value 6;
        description "IPv6 multicast address family";
      }
      enum ipv6-labeled-unicast {
        value 7;
        description "IPv6 labeled-unicast address family";
      }
      enum vpnv6-unicast {
        value 8;
        description "VPNv6 unicast address family";
      }
      enum ipv4-mdt {
        value 9;
        description "IPv4 MDT address family";
      }
      enum l2vpn-vpls {
        value 10;
        description "L2VPN VPLS-VPWS address family";
      }
      enum ipv4rt-constraint {
        value 11;
        description "IPv4 rt-filter address family";
      }
      enum ipv4-mvpn {
        value 12;
        description "IPv4 MVPN address family";
      }
      enum ipv6-mvpn {
        value 13;
        description "IPv6 MVPN address family";
      }
      enum l2vpn-evpn {
        value 14;
        description "L2VPN EVPN address family";
      }
      enum lsls {
        value 15;
        description "Link-state link-state address family";
      }
      enum vpnv4-multicast {
        value 16;
        description "VPNv4 Multicast address family";
      }
      enum vpnv6-multicast {
        value 17;
        description "VPNv6 Multicast address family";
      }
      enum ipv4-flowspec {
        value 18;
        description "IPv4 flowspec address family";
      }
      enum ipv6-flowspec {
        value 19;
        description "IPv6 flowspec address family";
      }
      enum vpnv4-flowspec {
        value 20;
        description "VPNv4 flowspec address family";
      }
      enum vpnv6-flowspec {
        value 21;
        description "VPNv6 flowspec address family";
      }
      enum l2vpn-mspw {
        value 22;
        description "L2VPN MSPW address family";
      }
      enum ipv4-sr-policy {
        value 23;
        description
          "IPv4 Segment Routing (SR) policy address family";
      }
      enum ipv6-sr-policy {
        value 24;
        description
          "IPv6 Segment Routing (SR) policy address family";
      }
      enum all-address-family {
        value 25;
        description "All Address Families";
      }
    }
    description "Object tracking address family";
  }
  typedef Object-tracking-name-string {
    type string {
      length "1..32";
      pattern '[a-zA-Z0-9_\-]+';
    }
    description "Object tracking name string";
  }
  typedef Object-tracking-delay {
    type uint32 {
      range "1..3600";
    }
    description "Object tracking delay";
  }
}
