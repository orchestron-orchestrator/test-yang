module Cisco-IOS-XR-infra-xtc-agent-oper {

  /*** NAMESPACE / PREFIX DEFINITION ***/

  namespace "http://cisco.com/ns/yang"+
    "/Cisco-IOS-XR-infra-xtc-agent-oper";


  prefix "infra-xtc-agent-oper";

  /*** LINKAGE (IMPORTS / INCLUDES) ***/

  import ietf-inet-types { prefix "inet"; }

  import Cisco-IOS-XR-types { prefix "xr"; }

  import cisco-semver { prefix "semver"; }

  include Cisco-IOS-XR-infra-xtc-agent-oper-sub3 {
    revision-date 2025-06-22;
  }

  include Cisco-IOS-XR-infra-xtc-agent-oper-sub2 {
    revision-date 2025-06-22;
  }

  include Cisco-IOS-XR-infra-xtc-agent-oper-sub1 {
    revision-date 2025-06-22;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR infra-xtc-agent package operational data.

     This module contains definitions
     for the following management objects:
       pcc: Path-computation client in XTC
       xtc: XTC Agent operational data

     Copyright (c) 2013-2025 by Cisco Systems, Inc.
     All rights reserved.";

  revision "2025-06-22" {
    description
      "Added more details to next hop container.
       2025-04-24
         Added interface name where interface handle was fixed to use actual internal handle
       2025-04-14
         Removed explicit-bsids container and added explicit-bsid-db container
       2025-01-20
         Added drop-upon-invalidation under pcc/plsps/plsp/path
       2024-11-26
         Added explicit BSID container
       2024-11-01
         Added grpc policy attributes to policy container
       2024-09-25
         Changed the GRPC protocol origin id value
       2024-09-15
         Added bandwidth leaf under candidate path segment list to store allocated bandwidth value
       2024-08-21
         Added invalidation-drop-cp and invalidation-drop-enabled leaves under candidate-paths list. Added path-invalidation-drop-policy-count leaf under policy-summary container. Added invalidated-traffic-dropped leaf under plsp/path list.
       2024-08-16
         Added new field to contain IGP IANA Metric Types
       2024-08-01
         Added new field metric type value to be filled with IGP IANA metric types
       2024-07-22
         Deprecated metric-type in last-notify/effective-metric. rib-nh-metric-pending enum is added to Xtc-policy-lsp-sm-state.
       2024-07-21
         Added grpc service-instance for policy candidate-path
       2024-07-19
         Added user-defined and unknown metric types. Added flex-algo-admin-distances.
       2024-06-11
         Added grpc service-instance list
       2024-04-22
         Added Candidate Path and Instance in TreeSID
       2024-04-09
         SR MPLS Next Hop table addition
       2024-01-17
         sr algo bag definiton for xtc topology
       2023-12-20
         new policy path type for mixed paths.
       2023-10-27
         Display PM reverse-path segment-lists configured.
       2023-10-17
         Display of adj sids in topo for ipv6 links.
       2023-10-12
         Added fields for path-type of a policy and candidate path
       2023-08-07
         Display of associated resource lists for policies.
       2023-05-10
         Added conn-initiated, is-holddown-timer-running, is-dead-timer-running, and is-pce-initiated-redelegation-timer-running flags inside pcep-conn. Furthermore, added is-delegation-fallback-timer-running and is-state-timer-running inside plsp.
       2023-05-04
         Display Flex-Algo information for P2MP policies.
       2023-01-24
         Added fields for Flex-algo ASLA attributes on IPv4 and IPv6 links
       2022-11-07
         SR MPLS UCMP IGP weights addition.
       2022-10-26
         Dynamic CS Persistent PM and LSP, added fields for CP,LSP state and new SM transitions.
       2022-06-15
         Removed obsolete srv6-prefix container.
       2022-06-08
         Dynamic CS, added summary fields for standby CP and LSP
       2022-06-03
         Removed prefix-metric entry from the topology node.
       2022-05-17
         Renamed srv6usid to srv6-sid since all SRv6 SIDs are not micro SIDs
       2022-05-12
         Added checkpoint id in policy lsp segment list bag.
       2022-03-03
         Added is-srv6-local and is-srv6-remote in peer container.
       2022-03-03
         Added SID length and SID format for explicit path policy.
       2022-01-17
         Change the type of extended-value leaf from leaf-list to list.
       2021-11-21
         Added prefix-metric entry in the topology node.
       2021-11-09
         Added unreliable flag and update drop count in topology summary bag.
       2021-10-21
         Adding algorithm and computation time to path query results
       2021-09-27
         Added leaf max-install-standby-cpaths under grouping XTC-POLICY-BAG. Added leaf max-install-standby-cpaths under grouping XTC-GLOBAL-INFO-BAG.
       2021-08-31
         Added leaf segment-algorithm-set under grouping XTC-SEGMENTS-BAG.";
    semver:module-version "5.0.0";
  }

  revision "2021-07-27" {
    description
      "Added invalid reason leaf under segment-list container
      2021-06-14
          Added SL First Label and Start Index field in LSP SL MOI bag. Added NH Seperation enabled field in Global info bag. IosSetYangSchemaRev Cisco-IOS-XR-infra-xtc-agent-oper";
    semver:module-version "4.1.0";
  }

  revision "2021-05-21" {
    description
      "Added path invalidation drop flag in policy bag.
      2021-04-22
           Added TE metric field for Flex-algo ASLA.
      2021-02-18
           Remove deprecated performance-measurement oper bag and renamed pm config field name in xtc_pm_lsp_info. Added performance-measurement config data bag in lsp bag.
      2021-02-08
           Added performance-measurement config data bag in lsp bag.
      2020-12-13
           Added performance-measurement liveness-detection oper schema.
      2020-10-27
           Added A flag set field in show command to support A flag sent from PM side
      2020-09-16
           Adding operational nodes for new features path invalidation drop protected and unprotected path
      2020-09-04
           Modified the Extended-Affinities and ASLA-Extended-Affinities to be list instead of a leaf-list
      2020-05-12
           Add SRv6TE policy operational data
      2020-05-05
           changes related to treat SRv6 and SID as well-known when parsing XML for yang";
    semver:module-version "4.0.0";
  }

  revision "2020-01-16" {
    description
      "Removed event buffer from SR-TE policy model. Implement new statistic info for policy performance-measurement session. Added support for per-flow policy output. Added additional filter for policy type i.e. per-flow and per-destination.";
    semver:module-version "3.0.0";
  }

  revision "2019-09-09" {
    description
      "PCE/SRTE topology should display P-flag set for OSPF prefix-SID with explicit-null";
    semver:module-version "2.0.0";
  }

  revision "2019-05-01" {
    description
      "Added operational models for interface database.";
    semver:module-version "1.0.0";
  }

  revision "2019-04-15" {
    description
      "Hierarchical changes to policy forwarding model to organize the paths under the proper segment lists and LSPs.";
  }

  revision "2019-04-05" {
    description
      "Establish semantic version baseline.";
  }

  revision "2018-11-28" {
    description
      "Various modifications to policy-related models for better compatibility with the IETF policy draft.";
  }

  revision "2017-09-11" {
    description
      "Initial version";
  }

  revision "2015-11-09" {
    description
      "IOS XR 6.0 revision.";
  }

  typedef Xtcigp-protocol {
    type enumeration {
      enum unknown {
        value 0;
        description "Unknown protocol";
      }
      enum isis {
        value 1;
        description "ISIS protocol";
      }
      enum ospf {
        value 2;
        description "OSPF protocol";
      }
      enum bgp {
        value 3;
        description "BGP protocol";
      }
      enum te {
        value 4;
        description "TE protocol";
      }
    }
    description "Xtcigp protocol";
  }
  typedef Xtc-label {
    type uint32 {
      range "16..1048575";
    }
    description "Xtc label";
  }
  typedef Xtc-registration-entry {
    type enumeration {
      enum color {
        value 0;
        description "Color";
      }
      enum color-endpoint {
        value 1;
        description "Color and Endpoint";
      }
      enum policy-name {
        value 2;
        description "Policy Name";
      }
    }
    description "Xtc registration entry";
  }
  typedef Xtc-address-family {
    type enumeration {
      enum ipv4 {
        value 1;
        description "IPv4 address family";
      }
      enum ipv6 {
        value 2;
        description "IPv6 address family";
      }
    }
    description "Xtc address family";
  }

  grouping POLICY-FORWARDING-TABLE {
    description "Common node of xtc, forwarding";

    container policy-forwardings {
      description "Forwarding information for policies";

      list policy-forwarding {
        key "name";
        description "Forwarding information for the policy";
        leaf name {
          type xr:Cisco-ios-xr-string;
          description "Policy Name";
        }
        uses XTC-FWDING-POLICY-BAG;
      }
    }
  }

  container pcc {
    config false;
    description "Path-computation client in XTC";

    container plsps {
      description "PCC PLSP database in XTC";

      list plsp {
        key "plsp-id";
        description "PCC PLSP information";
        leaf plsp-id {
          type uint32;
          description "PLSP ID";
        }
        uses PCEP-PLSP-BAG;
      }
    }

    container peers {
      description "PCC peer database in XTC";

      list peer {
        key "peer-addr";
        description "PCC peer information";
        leaf peer-addr {
          type inet:ip-address-no-zone;
          description "Peer Address";
        }
        uses PCEP-CONN-BAG;
      }
    }
  }

  container xtc {
    config false;
    description "XTC Agent operational data";

    container global-info {
      description "Global information";
      uses XTC-GLOBAL-INFO-BAG;
    }

    container grpc-service-instances {
      description "GRPC service instances";

      list grpc-service-instance {
        key "name";
        description "GRPC service instance";
        leaf name {
          type string {
            length "1..128";
          }
          description "service instance name";
        }
        uses XTC-GRPC-SERVICE-INSTANCE-BAG;
      }
    }

    container policies {
      description "Policy database in XTC Agent";

      list policy {
        key "id";
        description "Policy information";
        leaf id {
          type uint32;
          description "Policy ID";
        }
        uses XTC-POLICY-BAG;
      }
    }

    container first-segments {
      description "First segments of all segment-lists";

      list first-segment {
        key "label";
        description "first-segment of an SR-TE segment-list";
        leaf label {
          type Xtc-label;
          description "Label";
        }
        uses XTC-FS-BAG;
      }
    }

    container interfaces {
      description "Interface database in XTC Agent";

      list interface {
        key "interface-name";
        description "Interface information";
        leaf interface-name {
          type xr:Interface-name;
          description "Interface name";
        }
        uses XTC-INTERFACE-BAG;
      }
    }

    container policy-summary {
      description "Summary of all policies";
      uses XTC-POLICY-SUMMARY-BAG;
    }

    container p2mp-policy-infos {
      description
        "P2MP policy database indexed by Root address in
        XTC Agent";

      list p2mp-policy-info {
        key "root-address tree-id";
        description "Policy information";
        leaf root-address {
          type inet:ip-address-no-zone;
          description "Root Address";
        }
        leaf tree-id {
          type uint32;
          description "P2MP Policy Tree-ID";
        }
        uses XTC-TREESID-BAG;
      }
    }

    container trace-buffer-summaries {
      description "Summary of all trace buffers";

      list trace-buffer-summary {
        key "name";
        description "Summary of specific trace buffer";
        leaf name {
          type xr:Cisco-ios-xr-string;
          description "Trace buffer name";
        }
        uses CMN-TRACE-BUFFER-SUMMARY-BAG;
      }
    }

    container srv6 {
      description "SRv6TE specific information";

      container next-hops {
        description "Next Hop Information";

        list next-hop {
          key "prefix";
          description "Next Hop detailed information";
          leaf prefix {
            type inet:ip-address-no-zone;
            description "Prefix";
          }
          uses XTC-NEXT-HOP;
        }
      }

      container rib-stats {
        description "RIB Stats";
        uses XTC-RIB-STATS;
      }

      container locators {
        description "Locators Information";

        list locator {
          key "name";
          description "Locator detailed information";
          leaf name {
            type xr:Cisco-ios-xr-string;
            description "Locator name";
          }
          uses XTC-SRV6U-LOCATOR;
        }
      }
    }

    container on-demand-colors {
      description "On-Demand Color database in XTC Agent";

      list on-demand-color {
        key "color";
        description "On Demand Color information";
        leaf color {
          type uint32;
          description "Color";
        }
        uses XTC-ON-DEMAND-COLOR-BAG;
      }
    }

    container forwarding {
      description "Forwarding information";
      uses POLICY-FORWARDING-TABLE;
    }

    container controller {
      description "Controller information";

      container policy-requests {
        description "Table containing policy requests";

        list policy-request {
          key "source-address endpoint-type endpoint-address color"+
            " route-distinguisher";
          description "Policy request information";
          leaf source-address {
            type inet:ip-address-no-zone;
            description "Source Address";
          }
          leaf endpoint-type {
            type Xtc-address-family;
            description "Endpoint Address Type";
          }
          leaf endpoint-address {
            type inet:ip-address-no-zone;
            description "Endpoint Address";
          }
          leaf color {
            type uint32 {
              range "1..4294967295";
            }
            description "Color";
          }
          leaf route-distinguisher {
            type uint32 {
              range "0..4294967295";
            }
            description "Route Distinguisher";
          }
          uses XTC-CONTROLLER-POLICY-REQ-BAG;
        }
      }
    }

    container p2mp-policies {
      description "P2MP policy database in XTC Agent";

      list p2mp-policy {
        key "name";
        description "Policy information";
        leaf name {
          type xr:Cisco-ios-xr-string;
          description "Policy name";
        }
        uses XTC-TREESID-BAG;
      }
    }

    container registrations {
      description "Registrations";

      list registration {
        description "Registration";
        leaf entry-type {
          type Xtc-registration-entry;
          description "Entry Type";
        }
        leaf color {
          type uint32 {
            range "1..4294967295";
          }
          description "Color";
        }
        leaf endpoint {
          type inet:ip-address-no-zone;
          description "Endpoint Address";
        }
        leaf policy-name {
          type xr:Cisco-ios-xr-string;
          description "Policy Name";
        }
        uses XTC-REGIST-ENTRY-BAG;
      }
    }

    container topology-nodes {
      description "Node database in XTC Agent";

      list topology-node {
        key "node-identifier";
        description "Node information";
        leaf node-identifier {
          type uint32;
          description "Node Identifier";
        }
        uses XTC-TOPO-NODE-BAG;
      }
    }

    container topology-summaries {
      description "Node summary table";

      list topology-summary {
        description "Node summary database";
        leaf af {
          type Xtc-address-family;
          description
            "Only show data related to the specified
            address family";
        }
        leaf protocol {
          type Xtcigp-protocol;
          description "Match nodes from the specified IGP protocol";
        }
        uses XTC-TOPO-SUMMARY-BAG;
      }
    }

    container prefix-infos {
      description "Prefixes database in XTC Agent";

      list prefix-info {
        key "node-identifier";
        description "Prefix information";
        leaf node-identifier {
          type uint32;
          description "Node ID";
        }
        uses XTC-PFX-BAG;
      }
    }

    container interface-summary {
      description "Summary of all interfaces";
      uses XTC-INTERFACE-SUMMARY-BAG;
    }

    container database {
      description "Database Information";

      container next-hop-db {
        description "Next Hop Database Information";

        container next-hop-labels {
          description "Next Hop Label Database Information";

          list next-hop-label {
            key "label";
            description
              "Next Hop Label Database detailed information";
            leaf label {
              type uint32;
              description "Label";
            }
            uses XTC-NEXT-HOP-LABEL;
          }
        }

        container next-hop-ipv6s {
          description "Next Hop Information";

          list next-hop-ipv6 {
            key "prefix";
            description "Next Hop detailed information";
            leaf prefix {
              type inet:ip-address-no-zone;
              description "Prefix";
            }
            uses XTC-NEXT-HOP-IPV6;
          }
        }

        container next-hop-ipv4s {
          description "IPv4 Next Hop Database Information";

          list next-hop-ipv4 {
            key "prefix";
            description
              "IPv4 Next Hop Database detailed information";
            leaf prefix {
              type inet:ip-address-no-zone;
              description "Prefix";
            }
            uses XTC-NEXT-HOP-IPV4;
          }
        }
      }

      container explicit-bsiddb {
        description "Explicit BSID Database Information";

        container explicit-srv6bsids {
          description "Explicit SRv6 BSID Database Information";

          list explicit-srv6bsid {
            key "address";
            description "Explicit SRv6 BSID detailed information";
            leaf address {
              type inet:ip-address-no-zone;
              description "SRv6 BSID Address";
            }
            uses XTC-REDIST-BSID-BAG;
          }
        }
      }
    }
    uses POLICY-FORWARDING-TABLE;
  }
}
