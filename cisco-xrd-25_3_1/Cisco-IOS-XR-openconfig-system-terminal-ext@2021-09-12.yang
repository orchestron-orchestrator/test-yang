module Cisco-IOS-XR-openconfig-system-terminal-ext {

  // namespace
  namespace "http://cisco.com/ns/yang/"+
        "Cisco-IOS-XR-openconfig-system-terminal-ext";

  prefix "oc-term-ext";

  // import some basic types
  import openconfig-system { prefix oc-sys; }

  // meta
  import cisco-semver { prefix "semver"; }

   organization "Cisco Systems, Inc.";

   contact
    "Cisco Systems, Inc.
     Customer Service

     Postal: 170 West Tasman Drive
     San Jose, CA 95134

     Tel: +1 800 553-NETS

     E-mail: cs-yang@cisco.com";

  description
    "This module defines IPv4/Ipv6 and vrf specific configuration data
     for telnet server.

    Copyright (c) 2013-2020 by Cisco Systems, Inc.
    All rights reserved.";


  revision "2021-09-12" {
    description
      "Initial version";
    reference "0.1.0";
    semver:module-version "1.0.0";
  }


  // identity statements

  // typedef statements

  // grouping statements

  grouping system-telnet-server-config {
    description
      "Configuration data for telnet server";

    leaf session-limit {
      type uint16;
      mandatory true;
      description
        "Set a limit on the number of simultaneous active terminal
        sessions to the system for the protocol (e.g., ssh,
        telnet, ...) ";
    }  
}

  grouping system-telnet-server-state {
    description
      "State data for telnet server";

      leaf enable {
        type boolean;
        default false;
        description
          "Enables the telnet server.  Telnet is disabled by
          default";
      }

    leaf session-limit {
      type uint16;
      mandatory true;
      description
        "Set a limit on the number of simultaneous active terminal
        sessions to the system for the protocol (e.g., ssh,
        telnet, ...) ";
    }
}

  // data definition statements

  // augment statements

  augment "/oc-sys:system/oc-sys:telnet-server" {
    description "This augment extends the configuration data of
                'oc-sys:telnet-server'";
    container ipv4 {
      description
        "Configuration for IPv4";
      list vrf {
        key "vrf-name";
        description
          "Configuration for a particular VRF";
        leaf vrf-name {
          type string {
            length "1..64";
          }
          description "VRF Name";
        }
        container config {
          description "Configuration data for telnet";
          uses system-telnet-server-config;
        }
        container state {
          config false;
          description "Operational state data for telnet";
          uses system-telnet-server-state;
        }
      }
    }
    container ipv6 {
      description
        "Configuration for IPv6";

      list vrf {
        key "vrf-name";
        description
          "Configuration for a particular VRF";
        leaf vrf-name {
          type string {
            length "1..64";
          }
          description "VRF Name";
        }
        container config {
          description "Configuration data for telnet";
          uses system-telnet-server-config;
        }
        container state {
          config false;
          description "Operational state data for telnet";
          uses system-telnet-server-state;
        }
      }
    }
  }

  // rpc statements

  // notification statements

}
