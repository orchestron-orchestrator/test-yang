module Cisco-IOS-XR-fpmgr-cfg {

  /*** NAMESPACE / PREFIX DEFINITION ***/

  namespace "http://cisco.com/ns/yang/Cisco-IOS-XR-fpmgr-cfg";


  prefix "fpmgr-cfg";

  /*** LINKAGE (IMPORTS / INCLUDES) ***/

  import Cisco-IOS-XR-types { prefix "xr"; }

  import cisco-semver { prefix "semver"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR fpmgr package configuration.

     This module contains definitions
     for the following management objects:
       fault-manager: Fault mgr

     Copyright (c) 2013-2019 by Cisco Systems, Inc.
     All rights reserved.";

  revision "2019-04-05" {
    description
      "Establish semantic version baseline.";
    semver:module-version "1.0.0";
  }

  revision "2015-11-09" {
    description
      "IOS XR 6.0 revision.";
  }

  typedef Nsas {
    type enumeration {
      enum unknown {
        value 0;
        description "Unkown severity";
      }
      enum nonreported {
        value 1;
        description "Non reported severity";
      }
      enum nonfaulted {
        value 2;
        description "Non faulted severity";
      }
      enum minor {
        value 3;
        description "Minor severity";
      }
      enum major {
        value 4;
        description "Major severity";
      }
      enum critical {
        value 5;
        description "Critical severity";
      }
    }
    description "Nsas";
  }
  typedef Sas {
    type enumeration {
      enum unknown {
        value 0;
        description "Unkown severity";
      }
      enum nonreported {
        value 1;
        description "Non reported severity";
      }
      enum nonfaulted {
        value 2;
        description "Non faulted severity";
      }
      enum minor {
        value 3;
        description "Minor severity";
      }
      enum major {
        value 4;
        description "Major severity";
      }
      enum critical {
        value 5;
        description "Critical severity";
      }
    }
    description "Sas";
  }

  container fault-manager {
    description "Fault mgr";

    list fault-profile {
      key "fault-profile-name";
      description "Fault profile name";

      container racks {
        description "Apply fault profile";

        list rack {
          key "rack";
          description "rack numnber";
          leaf rack {
            type xr:Cisco-ios-xr-string;
            description " ";
          }

          list slot {
            key "slot";
            description "None";

            container ports {
              description "Configure a port";

              list port {
                key "port";
                description "None";
                leaf propagate {
                  type uint32;
                  description
                    "Propagate fault profile on child entities
                    of port";
                }
                leaf port {
                  type xr:Cisco-ios-xr-string;
                  description " ";
                }
              }
            }
            leaf propagate {
              type uint32;
              description
                "Apply fault profile on child entities of
                card";
            }
            leaf slot {
              type xr:Cisco-ios-xr-string;
              description " ";
            }
          }
        }
      }

      container subsystems {
        description "Fault identifier";

        list subsystem {
          key "subsystem";
          description "Subsystem name";
          leaf subsystem {
            type xr:Cisco-ios-xr-string;
            description " ";
          }

          list fault-type {
            key "fault-type";
            description "Fault type name";
            leaf fault-type {
              type xr:Cisco-ios-xr-string;
              description " ";
            }

            list fault-tag {
              key "fault-tag";
              description "Fault tag name";
              leaf fault-tag {
                type xr:Cisco-ios-xr-string;
                description " ";
              }
              leaf sas {
                type Sas;
                description "Fault severity selection";
              }
              leaf nsas {
                type Nsas;
                description "Fault severity selection";
              }
            }
          }
        }
      }
      leaf description {
        type string {
          length "1..128";
        }
        description "Fault profile description";
      }
      leaf enable {
        type empty;
        description
          "Enable Fault profile name. Deletion of this
          object also causes deletion of all associated
          objects under FaultProfile.";
      }
      leaf fault-profile-name {
        type xr:Cisco-ios-xr-string {
          length "1..32";
        }
        description "Fault profile";
      }
    }
  }
}
