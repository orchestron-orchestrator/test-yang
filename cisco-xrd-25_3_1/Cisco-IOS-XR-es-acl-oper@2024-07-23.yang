module Cisco-IOS-XR-es-acl-oper {

  /*** NAMESPACE / PREFIX DEFINITION ***/

  namespace "http://cisco.com/ns/yang/Cisco-IOS-XR-es-acl-oper";


  prefix "es-acl-oper";

  /*** LINKAGE (IMPORTS / INCLUDES) ***/

  import Cisco-IOS-XR-types { prefix "xr"; }

  import cisco-semver { prefix "semver"; }

  import Cisco-IOS-XR-common-acl-datatypes { prefix "dt1"; }

  include Cisco-IOS-XR-es-acl-oper-sub1 {
    revision-date 2024-07-23;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR es-acl package operational data.

     This module contains definitions
     for the following management objects:
       es-acl: Root class of ES ACL Oper schema tree

     Copyright (c) 2013-2024 by Cisco Systems, Inc.
     All rights reserved.";

  revision "2024-07-23" {
    description
      "Increasing acl name length to 128 chars";
    semver:module-version "1.1.0";
  }

  revision "2019-04-05" {
    description
      "Establish semantic version baseline.";
    semver:module-version "1.0.0";
  }

  revision "2017-05-01" {
    description
      "Fixing backward compatibility error in module.";
  }

  revision "2015-11-09" {
    description
      "IOS XR 6.0 revision.";
  }

  typedef Es-acl-name {
    type xr:Cisco-ios-xr-string {
      length "1..128";
    }
    description "Es acl name";
  }

  container es-acl {
    config false;
    description "Root class of ES ACL Oper schema tree";

    container active {
      description
        "Out Of Resources, Limits to the resources
        allocatable";

      container oor {
        description
          "Out Of Resources, Limits to the resources
          allocatable";

        container acl-summary {
          description "Resource Limits pertaining to ACLs only";

          container details {
            description
              "Details containing the resource limits of the
              ACLs";
            uses ES-ACL-EDM-OOR-DETAIL;
          }
        }

        container oor-acls {
          description "Resource occupation details for ACLs";

          list oor-acl {
            key "name";
            description
              "Resource occupation details for a particular
              ACL";
            leaf name {
              type Es-acl-name;
              description "Name of the Access List";
            }
            uses ES-ACL-EDM-OOR-DETAIL;
          }
        }
      }

      container list {
        description "List containing ACLs";

        container acls {
          description "ACL class displaying Usage and Entries";

          list acl {
            key "name";
            description "Name of the Access List";

            container acl-sequence-numbers {
              description
                "Table of all the SequenceNumbers per ACL";

              list acl-sequence-number {
                key "sequence-number";
                description "Sequence Number of an ACL entry";
                leaf sequence-number {
                  type dt1:Acl-sequence-number-range;
                  description "ACLEntry Sequence Number";
                }
                uses ES-ACL-EDM-ACE;
              }
            }
            leaf name {
              type Es-acl-name;
              description "Name of the Access List";
            }
          }
        }
      }

      container usages {
        description
          "Table of Usage statistics of ACLs at different
          nodes";

        list usage {
          description "Usage statistics of an ACL at a node";
          leaf location {
            type xr:Node-id;
            description "Node where ACL is applied";
          }
          leaf application-id {
            type dt1:Acl-usage-app-id-enum;
            description "Application ID";
          }
          leaf name {
            type Es-acl-name;
            description "Name of the ACL";
          }
          leaf usage-details {
            type string;
            mandatory true;
            description "Usage Statistics Details";
          }
        }
      }
    }
  }
}
