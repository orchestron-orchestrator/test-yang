module Cisco-IOS-XR-openconfig-system-fpd-ext {

  // namespace
  namespace "http://cisco.com/ns/yang/"+
        "Cisco-IOS-XR-openconfig-system-fpd-ext";

  prefix "oc-fpd-ext";

  // import some basic types
  import openconfig-system { prefix oc-sys; }
  import openconfig-platform-types { prefix oc-platform-types; }

  // meta
  import cisco-semver { prefix "semver"; }

   organization "Cisco Systems, Inc.";

   contact
    "Cisco Systems, Inc.
     Customer Service

     Postal: 170 West Tasman Drive
     San Jose, CA 95134

     Tel: +1 800 553-NETS

     E-mail: cs-yang@cisco.com";

  description
    "This module defines Power Module FPD upgrade related configuration.

    Copyright (c) 2024 by Cisco Systems, Inc.
    All rights reserved.";


  revision "2024-05-10" {
    description
      "Initial version";
    reference "0.1.0";
    semver:module-version "1.0.0";
  }


  // identity statements

  // typedef statements

  // grouping statements

  grouping system-fpd-config {
    description
      "Configuration data for system-wide fpd upgrade configuration";

    leaf enable-auto-upgrade {
      type boolean;
      default true;
      description
        "Enable FPD auto-upgrade. If this is set to true, then the system
         will automatically upgrade all the FPDs available in the system
         to the latest version. If this is set to false, then the system
         will not automatically upgrade FPDs.";
    }

    leaf-list disable-upgrade {
      type identityref {
          base oc-platform-types:OPENCONFIG_HARDWARE_COMPONENT;
        }
      description
        "List of components whose FPDs should not be automatically upgraded by
         the system. If a component is listed here, then the system will not
         automatically upgrade the FPDs on it to the latest version available
         in the system.";
    }
  }

  grouping system-fpd-state {
    description
      "Operational state data for system-wide fpd upgrade configuration";
  }

  grouping system-fpd-top {
    description
      "Top-level grouping for system-wide fpd configuration";

    container fpd {
      description
        "Top-level container for fpd configuration data";

      container config {
        description
          "Configuration data for system fpd";

        uses system-fpd-config;
      }

      container state {

        config false;

        description
          "Operational state data for system fpd";

        uses system-fpd-config;
        uses system-fpd-state;
      }
    }
  }
  // data definition statements

  // augment statements

  augment "/oc-sys:system" {
    container cisco {
        description
          "Top-level container for cisco specific configuration and operational state data";

        uses system-fpd-top;
      }
    description "Augment system with Cisco specific configuration and operational state data";
  }
  // rpc statements

  // notification statements

}
