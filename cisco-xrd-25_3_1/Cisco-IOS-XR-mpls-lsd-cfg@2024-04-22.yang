module Cisco-IOS-XR-mpls-lsd-cfg {

  /*** NAMESPACE / PREFIX DEFINITION ***/

  namespace "http://cisco.com/ns/yang/Cisco-IOS-XR-mpls-lsd-cfg";


  prefix "mpls-lsd-cfg";

  /*** LINKAGE (IMPORTS / INCLUDES) ***/

  import Cisco-IOS-XR-types { prefix "xr"; }

  import cisco-semver { prefix "semver"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR mpls-lsd package configuration.

     This model is deprecated and is replaced by
     Cisco-IOS-XR-um-mpls-lsd-cfg.yang which will provide the
     compatible functionalities.

     This module contains definitions
     for the following management objects:
       mpls-lsd: MPLS LSD configuration data

     Copyright (c) 2013-2024 by Cisco Systems, Inc.
     All rights reserved.";

  revision "2024-04-22" {
    description
      "Deprecated ltrace-buffer multiplier configuration.
       2023-12-15
         Added static-only to label-range
       2021-09-13
         Removed previously deprecated app-reg-delay disable and mplslsrmib cache timer/size configs";
    semver:module-version "3.0.0";
  }

  revision "2020-11-26" {
    description
      "Added a new block type PFP under exisiting label blocks config";
    semver:module-version "2.0.0";
  }

  revision "2019-08-20" {
    description
      "MPLS label block config default values added.";
    semver:module-version "1.1.0";
  }

  revision "2019-05-12" {
    description
      "Deprecated the native model, replaced by UM model.";
    semver:module-version "1.0.0";
  }

  revision "2019-04-05" {
    description
      "Establish semantic version baseline.";
  }

  revision "2018-06-15" {
    description
      "Allow min..max in range when min == max.";
  }

  revision "2015-11-09" {
    description
      "IOS XR 6.0 revision.";
  }

  typedef Label-block {
    type enumeration {
      enum cbf {
        value 3;
        description "CBF block";
      }
      enum pfp {
        value 4;
        description "PFP block";
      }
    }
    description "Label block";
  }
  typedef Label-block-client-name {
    type xr:Cisco-ios-xr-string {
      length "1..48";
    }
    description "Label block client name";
  }
  typedef Label-range {
    type enumeration {
      enum lower-upper {
        value 0;
        description "Start and end of block";
      }
      enum lower-size {
        value 1;
        description "Start and size of block";
      }
    }
    description "Label range";
  }
  typedef Mpls-ip-ttl-propagate-disable {
    type enumeration {
      enum all {
        value 0;
        description
          "Disable IP TTL propagation for all MPLS packets";
      }
      enum forward {
        value 1;
        description
          "Disable IP TTL propagation for only forwarded
          MPLS packets";
      }
      enum local {
        value 2;
        description
          "Disable IP TTL propagation for only locally
          generated MPLS packets";
      }
    }
    description "Mpls ip ttl propagate disable";
  }

  grouping TTL-EXPIRATION-POP {
    description "Common node of ipv4, ipv6";
    leaf ttl-expiration-pop {
      type uint32 {
        range "1..10";
      }
      description "Number of labels to pop upon MPLS IP TTL expiry";
    }
  }

  container mpls-lsd {
    status "deprecated";
    description
      "This model is deprecated and is replaced by
      Cisco-IOS-XR-um-mpls-lsd-cfg.yang which will
      provide the compatible functionalities.  MPLS LSD
      configuration data";

    container ipv6 {
      description "Configure IPv6 parameters";
      uses TTL-EXPIRATION-POP;
    }

    container ipv4 {
      description "Configure IPv4 parameters";
      uses TTL-EXPIRATION-POP;
    }

    container label-databases {
      description "Table of label databases";

      list label-database {
        key "label-database-id";
        description "A label database";

        container label-range {
          description "Label range";
          leaf minvalue {
            when "../static-only = 'false'" {
              description "../StaticOnly = 'false'";
            }
            type uint32 {
              range "16000..1048575";
            }
            description "Minimum label value";
          }
          leaf max-value {
            when "../static-only = 'false'" {
              description "../StaticOnly = 'false'";
            }
            type uint32 {
              range "16000..1048575";
            }
            description "Maximum label value";
          }
          leaf min-static-value {
            when "../static-only = 'false'" {
              description "../StaticOnly = 'false'";
            }
            type uint32 {
              range "16..1048575";
            }
            description "Minimum static label value";
          }
          leaf max-static-value {
            when "../static-only = 'false'" {
              description "../StaticOnly = 'false'";
            }
            type uint32 {
              range "16..1048575";
            }
            description "Maximum static label value";
          }
          leaf static-only {
            type boolean;
            description "Restrict label range to static only";
          }
        }

        container label-blocks {
          description "A label blocks database";

          list label-block {
            key "block-name";
            description "Label block";
            leaf block-name {
              type xr:Cisco-ios-xr-string;
              description "Label block identifier";
            }
            leaf block-type {
              type Label-block;
              description "Label block type";
            }
            leaf range-type {
              type Label-range;
              default "lower-upper";
              description "Label range type";
            }
            leaf lower-bound {
              type uint32 {
                range "16000..1048575";
              }
              default "16000";
              description "Lower bound of block";
            }
            leaf upper-bound {
              when "../range-type != 'lower-size'" {
                description "../RangeType != LowerSize";
              }
              type uint32 {
                range "16000..1048575";
              }
              default "16000";
              description "Upper bound of block";
            }
            leaf block-size {
              when "../range-type != 'lower-upper'" {
                description "../RangeType != LowerUpper";
              }
              type uint32 {
                range "1..1032576";
              }
              default "1";
              description "Size of block";
            }
            leaf client-instance-name {
              type Label-block-client-name;
              default "any";
              description "Client instance name";
            }
          }
        }
        leaf label-database-id {
          type uint32 {
            range "0";
          }
          description "Label database identifier";
        }
      }
    }
    leaf ltrace-multiplier {
      type uint32 {
        range "2..5";
      }
      description
        "This configuration is deprecated. It does not
        take effect.";
    }
    leaf mpls-entropy-label {
      type empty;
      description "Enable MPLS Entropy Label";
    }
    leaf mpls-ip-ttl-propagate-disable {
      type Mpls-ip-ttl-propagate-disable;
      description
        "Disable Propagation of IP TTL onto the label
        stack";
    }
  }
}
