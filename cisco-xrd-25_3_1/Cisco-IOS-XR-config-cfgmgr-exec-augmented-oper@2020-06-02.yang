module Cisco-IOS-XR-config-cfgmgr-exec-augmented-oper {

    namespace "http://cisco.com/ns/yang"+
        "/Cisco-IOS-XR-config-cfgmgr-exec-augmented-oper";
    prefix "config-cfgmgr-exec-augmented-oper";
    
    import cisco-semver { prefix "semver"; }
    import Cisco-IOS-XR-config-cfgmgr-exec-oper { prefix "cfgmgr-exec"; }
    
    organization "Cisco Systems, Inc.";
    
    contact 
        "
     Cisco Systems, Inc.
     Customer Service

     Postal: 170 W Tasman Drive
     San Jose, CA 95134

     Tel: +1 1800 553-NETS

     E-mail: cs-yang@cisco.com";

    description
        "This module contains a collection of YANG definitions
         for Cisco IOS-XR config-cfgmgr-exec-oper package operational data.

         Copyright (c) 2020 by Cisco Systems, Inc.
         All rights reserved.";
    
    revision "2020-06-02" {
        description
            "Initial revision to augment Cisco-IOS-XR-config-cfgmgr-exec-oper.yang model.";
    semver:module-version "1.0.0";
    }


    augment "/cfgmgr-exec:config-manager/cfgmgr-exec:global/cfgmgr-exec:config-commit" {
        leaf last-commit-id {
            type string;
            description
                "Identifier for the last commit in devices with a system admin console.
                 A client can use this to detect if the config datastore is modified in
                 either the XR or the system admin VMs.";
        }
        description "Augmenting Cisco-IOS-XR-config-cfgmgr-exec-oper model with
                   last-commit-id.";
    }
}
