module Cisco-IOS-XR-controller-otu-clear-prbs-act {

  namespace "http://cisco.com/ns/yang/Cisco-IOS-XR-controller-otu-clear-prbs-act";

  prefix controller-otu-clear-prbs-act;

  import Cisco-IOS-XR-types {
    prefix csc;
  }

  import cisco-semver { prefix "semver"; }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR to support PRBS related actions for controller-otu module.

     Copyright (c) 2024 by Cisco Systems, Inc.
     All rights reserved.";

  revision 2024-02-04 {
    description
      "Clear prbs cumulative statistics for otu and cohdsp controllers";
    semver:module-version "1.0.0";
  }


  rpc clear-controller-prbsdetails {
    description
      "Clear prbs cumulative statistics";
    input {
      leaf controller-name {
        type csc:Interface-name;
        mandatory true;
        description
          "Controller name in R/S/I/P format";
      }
     leaf prbs-details {
        type empty;
        mandatory true;
        description
          "clear prbs bit-errors counter";
      }
    }
  }
}
