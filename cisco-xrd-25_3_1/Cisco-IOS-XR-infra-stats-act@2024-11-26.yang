module Cisco-IOS-XR-infra-stats-act {
  namespace "http://cisco.com/ns/yang/Cisco-IOS-XR-infra-stats-act";
  prefix infra-statistics-act;

  import cisco-semver {
    prefix semver;
  }

  import Cisco-IOS-XR-types {
    prefix xr;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR action package configuration.

     Copyright (c) 2023-2024 by Cisco Systems, Inc.
     All rights reserved.";

  revision 2024-11-26 {
    description
      "Modified to use the xr:Interface-name-regex type instead of string.";
    semver:module-version "1.0.0";
  }

  revision "2024-11-13" {
    description
      "Modified the node name to match the response.";
    semver:module-version "1.0.0";
  }

  revision "2023-11-29" {
    description
      "IOS XR 24.2.0 Initial release.";
  }

  typedef stats-enum {
      type enumeration {
           enum generic {
            value 0;
            description "Generic Stats";
           }

           enum protocol {
            value 1;
            description "Protocol Stats";
           }
      }
    description "Enum for the stats type";
  }

  grouping generic-counters-values {
        description "Generic Counter";

        leaf packets-received {
            type uint64;
            description "Total Packets received";
        }

        leaf bytes-received {
            type uint64;
            description "Total Bytes received";
        }

        leaf packets-sent {
            type uint64;
            description "Total Packets sent";
        }

        leaf bytes-sent {
            type uint64;
            description "Total Bytes sent";
        }

        leaf multicast-packets-received {
            type uint64;
            description "Total no. of multicast packets received";
        }

        leaf broadcast-packets-received {
            type uint64;
            description "Total no. of broadcast packets received";
        }

        leaf multicast-packets-sent {
            type uint64;
            description "Total no. of multicast packets sent";
        }

        leaf broadcast-packets-sent {
            type uint64;
            description "Total no. of broadcast packets sent";
        }

        leaf output-drops {
            type uint32;
            description "No. of packet dropped before being transmitted";
        }

        leaf output-queue-drops {
            type uint32;
            description "Number of packets dropped due to configured output policy";
        }

        leaf input-drops {
            type uint32;
            description "Total input drops";
        }

        leaf input-queue-drops {
            type uint32;
            description "Placeholder for packets dropped due to configure input policy";
        }

        leaf runt-packets-received {
            type uint32;
            description "Received packets which are too small to be handled";
        }

        leaf giant-packets-received {
            type uint32;
            description "Received packets which are too large to be handled";
        }

        leaf throttled-packets-received {
            type uint32;
            description "No. of times the receiver on the port is was disabled";
        }

        leaf parity-packets-received {
            type uint32;
            description "No. of parity errors on the interface";
        }

        leaf unknown-protocol-packets-received {
            type uint32;
            description "No. of packets dropped because they were destined for higher level protocols not configure or running on the interface";
        }

        leaf input-errors {
            type uint32;
            description "Total input errors";
        }

        leaf crc-errors {
            type uint32;
            description "Input CRC errors";
        }

        leaf input-overruns {
            type uint32;
            description "No. of input packets received with FIFO or DMA overrun errors";
        }

        leaf framing-errors-received {
            type uint32;
            description "No. of packets received with framing error";
        }

        leaf input-ignored-packets {
            type uint32;
            description "Packets dropped due to internal driver error or hardware errors";
        }

        leaf input-aborts {
            type uint32;
            description "No. of packets whose reciept was aborted";
        }

        leaf output-errors {
            type uint32;
            description "Total packets that could not be transmitted due to internal driver error";
        }

        leaf output-underruns {
            type uint32;
            description "Transmitted packets with FIFO or DMA underrun errors";
        }

        leaf output-buffer-failures {
            type uint32;
            description "No. of no resource error received on output";
        }

        leaf output-buffers-swapped-out {
            type uint32;
            description "No. of packets swapped to DRAM or main memory";
        }

        leaf applique {
            type uint32;
            description "No. of unrecoverable error which have occured on the applique";
        }

        leaf resets {
            type uint32;
            description "Number of hardware resets";
        }

        leaf carrier-transitions {
            type uint32;
            description "No. of times the carrier detect signal of interface has changed state";
        }

        leaf availability-flag {
            type uint32;
            description "Availability bit mask";
        }

        leaf last-data-time {
            type uint64;
            description "Time when counters were last written (in seconds)";
        }

        leaf hardware-timestamp {
            type uint64;
            description "Time when counters were last read by Primary collector from hardware (in msecs";
        }

        leaf seconds-since-last-clear-counters {
            type uint32;
            description "Time elapsed since last clear command executed (in Seconds)";
        }

        leaf last-discontinuity-time {
            type uint32;
            description "SysUpTime when counters were last reset (in seconds)";
        }

        leaf seconds-since-packet-received {
            type uint32;
            description "Time elapsed since packet received (in Seconds)";
        }

        leaf seconds-since-packet-sent {
            type uint32;
            description "Time elapsed since packet sent (in Seconds)";
        }
  }

  grouping protocol-stats {
      description "Protocol stats group";

      leaf interface-name  {
          type xr:Interface-name;
          description "Interface name";
      }

      leaf protocol-name {
          type string;
          description "Name of the protocol";
      }

      leaf bytes-received {
          type uint64;
          description "Total no. of Bytes received";
      }

      leaf packets-received {
          type uint64;
          description "Total no. of Packets received";
      }

      leaf bytes-sent {
          type uint64;
          description "Total no. of Bytes sent";
      }

      leaf packets-sent {
          type uint64;
          description "Total no. of Packets sent";
      }

      leaf protocol {
          type uint32;
          description "Protocol number";
      }

      leaf last-data-time {
          type uint64;
          description "Time when counters were last written (in seconds)";
      }

      leaf input-data-rate {
          type uint64;
          description "Input data rate in 1000's of bps";
      }

      leaf input-packet-rate {
          type uint64;
          description "Input packets per second";
      }

      leaf output-data-rate {
          type uint64;
          description "Output data rate in 1000's of bps";
      }

      leaf output-packet-rate {
          type uint64;
          description "Output packets per second";
      }

      leaf hardware-timestamp {
          type uint64;
          description "Time when counters were last read by Primary collector from hardware (in msecs)";
      }
  }

  grouping interface-stats {
    description "Interface stats";

    leaf interface-name  {
        type xr:Interface-name;
        description "Interface name";
    }

    container generic-counters {
        description "Generic set of interface counters";
        uses generic-counters-values;
    }

    container intf-proto-stats {
        description "Protocol stats";
        list intf-proto-data {
            description "Interface counters per protocol";
            uses protocol-stats;
        }
    }
  }

  rpc infra-statistics-latest {
    description
      "Latest stats";

    input {
        leaf interface-name {
        type xr:Interface-name-regex;
        mandatory true;
        description
          "Interface name";
      }

      leaf stats-type {
        type stats-enum;
        mandatory true;
        description
          "Stats type";
      }
    }

    output {
       container response {
          description "Response container";
          container interfaces {
              description "Interface stats";
              list interface {
                description "Interface";
                uses interface-stats;
              }
          }
       }
    }
  }
}
