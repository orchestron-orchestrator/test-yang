submodule Cisco-IOS-XR-ip-rib-lblmgr-oper-sub1 {

  belongs-to Cisco-IOS-XR-ip-rib-lblmgr-oper {
    prefix Cisco-IOS-XR-ip-rib-lblmgr-oper;
  }

  /*** LINKAGE (IMPORTS / INCLUDES) ***/

  import ietf-inet-types { prefix "inet"; }

  import ietf-yang-types { prefix "yang"; }

  import Cisco-IOS-XR-types { prefix "xr"; }

  import cisco-semver { prefix "semver"; }

  include Cisco-IOS-XR-ip-rib-lblmgr-oper-sub2 {
    revision-date 2025-03-20;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ip-rib-lblmgr package operational data.

     Copyright (c) 2013-2025 by Cisco Systems, Inc.
     All rights reserved.";

  revision "2025-03-20" {
    description
      "Added label producer info to RIB EDM routes";
    semver:module-version "1.0.0";
  }

  revision "2025-01-06" {
    description
      "Optimized route and path schema";
  }

  revision "2024-11-22" {
    description
      "Added option to display MPLS routes with pending delete NHGs";
  }

  revision "2024-10-29" {
    description
      "Added last clear time of rib statistics";
  }

  revision "2024-10-01" {
    description
      "Add potential label routes";
  }

  revision "2024-08-16" {
    description
      "Added label-summary";
  }

  revision "2024-07-11" {
    description
      "Add unviable label routes";
  }

  revision "2024-02-15" {
    description
      "New rib-manager schema";
  }

  revision "2024-02-06" {
    description
      "New label-manager schema";
  }

  revision "2019-04-05" {
    description
      "Establish semantic version baseline.";
  }

  revision "2015-11-09" {
    description
      "IOS XR 6.0 revision.";
  }

  typedef Internal-id-context-nhg-key {
    type enumeration {
      enum nhg-key-type-invalid {
        value 0;
        description "InternalID context NHG key invalid/unset";
      }
      enum nhg-key-type-name {
        value 1;
        description "InternalID context NHG key type name";
      }
    }
    description "InternalID context NHG key type";
  }
  typedef Rib-edm-sl-id {
    type enumeration {
      enum invalid {
        description "Invalid Segment List";
      }
      enum srv6 {
        description "SRv6 Segment List";
      }
      enum mpls {
        description "MPLS Segment List";
      }
    }
    description "Rib edm sl id";
  }
  typedef Rib-via-aft-id {
    type enumeration {
      enum none {
        description "Via None";
      }
      enum via-nh-aft-id {
        description "Via Next-hop AFT ID";
      }
      enum via-nh-group-aft-id {
        description "Via Next-hop Group AFT ID";
      }
    }
    description "Rib via aft id";
  }
  typedef Mac-address {
    type yang:mac-address;
    description "MAC address type";
  }
  typedef Rib-path-attr {
    type enumeration {
      enum rib-path-attr-sub-parent-ifh {
        description "rib path attr sub parent ifh";
      }
      enum rib-path-attr-xc-id {
        description "rib path attr xc id";
      }
      enum rib-path-attr-span-diag-ifh {
        description "rib path attr span diag ifh";
      }
      enum rib-path-attr-vni {
        description "rib path attr vni";
      }
      enum rib-path-attr-label {
        description "rib path attr label";
      }
    }
    description "Rib path attr";
  }
  typedef Ospf-area-id {
    type enumeration {
      enum id-ip {
        description "id ip";
      }
      enum id-int {
        description "id int";
      }
    }
    description "Ospf area id";
  }
  typedef Rib-edm-safi-id {
    type enumeration {
      enum none {
        value 0;
        description "No sub-address family";
      }
      enum unicast {
        value 1;
        description "Unicast SAFI";
      }
      enum multicast {
        value 2;
        description "Multicast SAFI";
      }
    }
    description "Rib edm safi id";
  }
  typedef Rib-in6-addr {
    type inet:ipv6-address;
    description "Rib in6 addr";
  }
  typedef Rib-in4-addr {
    type inet:ipv4-address;
    description "Rib in4 addr";
  }
  typedef Rib-edm-afi-id {
    type enumeration {
      enum none {
        value 0;
        description "No address family";
      }
      enum ipv4 {
        value 1;
        description "IPv4 AFI";
      }
      enum ipv6 {
        value 2;
        description "IPv6 AFI";
      }
    }
    description "Rib edm afi id";
  }
  typedef Rib-edm-route {
    type enumeration {
      enum invalid {
        value 0;
        description "No route type";
      }
      enum prefix-route {
        value 1;
        description "Prefix Route";
      }
      enum label-route {
        value 2;
        description "Labelled Route";
      }
      enum label-prefix-route {
        value 3;
        description "Labelled Prefix Route";
      }
    }
    description "Rib edm route";
  }

  grouping MGMT-RIB-IID-CTX-NHG-KEY-NAME {
    description "InternalID context NHG key name";
    leaf name {
      type string;
      description "Name";
    }
  }

  grouping MGMT-RIB-IID-CTX-NHG-KEY {
    description "MGMT RIB IID CTX NHG KEY";

    container nhg-name {
      when "../internal-id-context-nhg-key-type ="+
        " 'nhg-key-type-name'" {
          description
            "../InternalIDContextNHGKeyType =
            'NHGKeyTypeName'";
      }
      description "InternalID context for NHG name";
      uses MGMT-RIB-IID-CTX-NHG-KEY-NAME;
    }
    leaf internal-id-context-nhg-key-type {
      type Internal-id-context-nhg-key;
      description "InternalIDContextNHGKeyType";
    }
  }

  grouping RIB-EDM-PATH-VIA-NHG {
    description "Information of via NHG";

    container key {
      description "NHG key";
      uses MGMT-RIB-IID-CTX-NHG-KEY;
    }
    leaf iid {
      type uint32;
      description "IID value";
    }
  }

  grouping RIB-EDM-PATH-SL-ID-INFO {
    description "Information of Segment List Identifier";
    leaf type {
      type Rib-edm-sl-id;
      description "Segment List ID type";
    }
    leaf sl-id {
      type uint32;
      description "Segment List ID";
    }
  }

  grouping RIB-EDM-PATH-VIA-AFT-ID {
    description "Information of Via aft ID attribute in path";
    leaf aft-id {
      type uint64;
      description "AFT ID for this path";
    }
    leaf vrf-id {
      type uint32;
      description "VRF ID for this path";
    }
    leaf type {
      type Rib-via-aft-id;
      description "Type of AFT ID";
    }
    leaf vrf-name {
      type string;
      description "VRF name";
    }
  }

  grouping RIB-EDM-PATH-IP-TUNNEL-INFO {
    description "Information of IP tunnel Info attribute in path";

    container src-ip-addr {
      description "Source IP Address";
      uses RIB-EDM-IP-ADDR;
    }

    container dst-ip-addr {
      description "Destination IP Address";
      uses RIB-EDM-IP-ADDR;
    }
    leaf auto-created {
      type boolean;
      description "Tunnel is auto created";
    }
    leaf tunnel-type {
      type string;
      description "Tunnel Type";
    }
    leaf flags {
      type uint32;
      description "VXLAN Network Identifier Flags";
    }
    leaf evni {
      type uint32;
      description "Egress VXLAN Network Identifier";
    }
    leaf tunnel-id {
      type uint32;
      description "Tunnel ID";
    }
    leaf vni {
      type uint32;
      description "VXLAN Network Identifier";
    }
    leaf rtep-id {
      type uint64;
      description "Remote Tunnel End Point ID";
    }
    leaf src-mac {
      type Mac-address;
      description "Source MAC Address";
    }
    leaf dst-mac {
      type Mac-address;
      description "Destination MAC Address";
    }
    leaf dscp {
      type uint8;
      description "DSCP";
    }
    leaf ttl {
      type uint8;
      description "TTL";
    }
  }

  grouping RIB-EDM-VIA-SRV6-SID {
    description "Information related to Via-SRv6-SID";
    leaf sid {
      type inet:ipv6-address;
      description "Via-SRv6-SID value";
    }
    leaf resolution-length {
      type uint8;
      description "FIB Resolution length";
    }
  }

  grouping RIB-EDM-PATH-SRV6-INFO {
    description "RIB path's SRv6 related information";

    container srv6-carrier-format {
      description "SRv6 Carrier Format";
      uses MGMT-SRV6-SID-FMT;
    }

    container srv6-headend-behavior {
      description "SRv6 headend behavior/type info";
      uses MGMT-SRV6-HEADEND-BEHAVIOR;
    }

    list srv6-carrier {
      description "List of SRv6 Carriers with one or more SIDs";
      uses MGMT-SRV6-SID;
    }
  }

  grouping RIB-EDM-PATH-GROUPING-INFO {
    description "Information of Path Grouping";
    leaf grouping-id {
      type uint32;
      description "Grouping ID for this path";
    }
  }

  grouping RIB-EDM-PATH-L2-INFO {
    description "Information of L2 Info attribute in path";
    leaf xcid {
      type uint32;
      description "L2 Cross Connect ID for this path";
    }
    leaf ac-interface {
      type xr:Interface-name;
      description "L2 AC Interface";
    }
    leaf split-horizon-group-id {
      type uint32;
      description "L2 Split Horizon Group ID";
    }
    leaf bridge-id {
      type uint32;
      description "L2 Bridge ID";
    }
  }

  grouping PATH-ATTR {
    description "PATH ATTR";
    leaf path-attr-type {
      type Rib-path-attr;
      description "PathAttrType";
    }
    leaf subscriber-parent-interface {
      when "../path-attr-type = 'rib-path-attr-sub-parent-ifh'" {
        description "../PathAttrType = 'RIBPathAttrSubParentIfh'";
      }
      type xr:Interface-name;
      description "Subscriber Parent Interface for this path";
    }
    leaf xc-id {
      when "../path-attr-type = 'rib-path-attr-xc-id'" {
        description "../PathAttrType = 'RIBPathAttrXC_ID'";
      }
      type uint32;
      description "L2 Cross Connect ID for this path";
    }
    leaf span-diag-interface {
      when "../path-attr-type = 'rib-path-attr-span-diag-ifh'" {
        description "../PathAttrType = 'RIBPathAttrSpanDiagIfh'";
      }
      type xr:Interface-name;
      description "SPAN Diagnostics Interface for this path";
    }
    leaf vxlan-network-id {
      when "../path-attr-type = 'rib-path-attr-vni'" {
        description "../PathAttrType = 'RIBPathAttrVNI'";
      }
      type uint32;
      description "VXLAN Network Identifier for this path";
    }
    leaf route-label {
      xr:event-telemetry "Subscribe Telemetry Event";
      when "../path-attr-type = 'rib-path-attr-label'" {
        description "../PathAttrType = 'RIBPathAttrLabel'";
      }
      type uint32;
      description "Label associated with this path";
    }
  }

  grouping OSPF-AREA-ID {
    description "OSPF AREA ID";
    leaf area-id-type {
      type Ospf-area-id;
      description "AreaIDType";
    }
    leaf id-ip-addr {
      when "../area-id-type = 'id-ip'" {
        description "../AreaIDType = 'ID_IP'";
      }
      type Rib-in4-addr;
      description "IP address format";
    }
    leaf id-int {
      when "../area-id-type = 'id-int'" {
        description "../AreaIDType = 'ID_Int'";
      }
      type uint32;
      description "Integer format";
    }
  }

  grouping RIB-EDM-PATH {
    description "Information of a rib path";

    container address {
      xr:event-telemetry "Subscribe Telemetry Event";
      description "Nexthop";
      uses RIB-EDM-IP-ADDR;
    }

    container information-source {
      xr:event-telemetry "Subscribe Telemetry Event";
      description "Infosource";
      uses RIB-EDM-IP-ADDR;
    }

    container ospf-area-id {
      xr:event-telemetry "Subscribe Telemetry Event";
      description "OSPF area associated with the path";
      uses OSPF-AREA-ID;
    }

    container path-attribute {
      description "Path attribute";
      uses PATH-ATTR;
    }

    container iid {
      description "Internal ID attribute";
      uses RIB-EDM-IP-ADDR;
    }

    container l2-info {
      description "L2 Info for this path";
      uses RIB-EDM-PATH-L2-INFO;
    }

    container path-grouping-info {
      description "Grouping Info for this path";
      uses RIB-EDM-PATH-GROUPING-INFO;
    }

    container srv6-info {
      description "SRv6 related information";
      uses RIB-EDM-PATH-SRV6-INFO;
    }

    container via-srv6-sid {
      description "Via-SRv6-SID value";
      uses RIB-EDM-VIA-SRV6-SID;
    }

    container ip-tunnel-info {
      description "IP Tunnel Info for this path";
      uses RIB-EDM-PATH-IP-TUNNEL-INFO;
    }

    container via-aft-id {
      description "Via AFT ID info for this path";
      uses RIB-EDM-PATH-VIA-AFT-ID;
    }

    container segment-list-id-info {
      description "Segment List ID Info";
      uses RIB-EDM-PATH-SL-ID-INFO;
    }

    container via-nhg {
      description "Via NHG info for this path";
      uses RIB-EDM-PATH-VIA-NHG;
    }
    leaf interface-name {
      xr:event-telemetry "Subscribe Telemetry Event";
      type xr:Interface-name;
      description "Interface handle for the path's nexthop";
    }
    leaf metric {
      xr:event-telemetry "Subscribe Telemetry Event";
      type uint32;
      description "Metrics";
    }
    leaf load-metric {
      xr:event-telemetry "Subscribe Telemetry Event";
      type uint32;
      description "Load Metrics";
    }
    leaf minimum-recurse-length {
      type uint8;
      description
        "Minimum netmask length of recursive resolving
        route";
    }
    leaf looped {
      type boolean;
      description "Looping path";
    }
    leaf next-hop-table-id {
      xr:event-telemetry "Subscribe Telemetry Event";
      type uint32;
      description "The table to which the next hop belongs";
    }
    leaf next-hop-vrf-name {
      xr:event-telemetry "Subscribe Telemetry Event";
      type string;
      description "VRF Name of the nh table";
    }
    leaf next-hop-table-name {
      xr:event-telemetry "Subscribe Telemetry Event";
      type string;
      description "NH table name";
    }
    leaf next-hop-afi {
      xr:event-telemetry "Subscribe Telemetry Event";
      type Rib-edm-afi-id;
      description "NH Address Family";
    }
    leaf next-hop-safi {
      xr:event-telemetry "Subscribe Telemetry Event";
      type Rib-edm-safi-id;
      description "NH Sub Address Family";
    }
    leaf tunnel-id {
      xr:event-telemetry "Subscribe Telemetry Event";
      type uint32;
      description "Tunnel ID associated with this path";
    }
    leaf path-id {
      xr:event-telemetry "Subscribe Telemetry Event";
      type uint32;
      description "Path id of this path";
    }
    leaf backup-path-id {
      xr:event-telemetry "Subscribe Telemetry Event";
      type uint32;
      description "Path id of this path's backup";
    }
    leaf ref-cnt-of-backup {
      type uint32;
      description
        "For backup paths, the number of active paths
        protected by the backup path";
    }
    leaf next-hop-id {
      xr:event-telemetry "Subscribe Telemetry Event";
      type uint32;
      description "NHID associated with this path";
    }
    leaf next-hop-id-refcount {
      type uint32;
      description "NHID references";
    }
    leaf stats-next-hop-id {
      type uint32;
      description "Path NHID used for StatsID";
    }
    leaf stats-next-hop-id-refcount {
      type uint32;
      description "Stats NHID references";
    }
    leaf binding-label {
      xr:event-telemetry "Subscribe Telemetry Event";
      type uint32;
      description "binding Label for this path";
    }
    leaf nexthop-id-feid {
      type uint64;
      description "Fib nhid encap id";
    }
    leaf mpls-feid {
      type uint64;
      description "Fib mpls encap id";
    }
    leaf viable {
      type boolean;
      description "Path Viability";
    }
    leaf-list label-stack {
      xr:event-telemetry "Subscribe Telemetry Event";
      type uint32;
      description "Outgoing label stack for this path";
    }

    list remote-backup-addr {
      max-elements "2";
      description "Remote backup node address";
      uses RIB-EDM-IP-ADDR;
    }
  }

  grouping RIB-EDM-ROUTE-AFT-INFO {
    description "RIB route's AFT info";
    leaf aft-id {
      type uint64;
      description "AFT ID for this route";
    }
    leaf vrf-id {
      type uint32;
      description "VRF ID for this route";
    }
    leaf transaction-id {
      type uint64;
      description "Transaction ID";
    }
    leaf vrf-name {
      type string;
      description "VRF Name";
    }
  }

  grouping RIB-EDM-ROUTE-SRV6-INFO {
    description "RIB route's SRv6 related information";

    container srv6-endpoint-behavior {
      description "SRv6 Endpoint behavior/type";
      uses MGMT-SRV6-ENDPOINT-BEHAVIOR;
    }

    container srv6-format {
      description "SRv6 Format";
      uses MGMT-SRV6-SID-FMT;
    }
    leaf is-srv6-locator {
      type boolean;
      description "Route corresponds to an SRv6 remote locator";
    }
    leaf srv6-locator-algo {
      type uint8;
      description "SRv6 Algo corresponding to SRv6 remote locator";
    }
  }

  grouping RIB-EDM-ALGO-LABEL-SET {
    description "Algorithm ID to Local Label information";
    leaf algorithm-id {
      type uint8;
      description "Algorithm Identifier";
    }
    leaf label {
      type uint32;
      description "Local label";
    }
    leaf metric {
      type uint32;
      description
        "Route Metric associated with Algorithm
        Identifier";
    }
  }

  grouping RIB-EDM-IP-ADDR {
    description "RIB EDM IP ADDR";
    leaf afi {
      type Rib-edm-afi-id;
      description "AFI";
    }
    leaf none {
      when "../afi = 'none'" {
        description "../AFI = 'None'";
      }
      type uint8;
      description "No address family";
    }
    leaf ipv4 {
      when "../afi = 'ipv4'" {
        description "../AFI = 'IPv4'";
      }
      type Rib-in4-addr;
      description "IPv4 address type";
    }
    leaf ipv6 {
      when "../afi = 'ipv6'" {
        description "../AFI = 'IPv6'";
      }
      type Rib-in6-addr;
      description "IPv6 address type";
    }
  }

  grouping RIB-EDM-IP-PFX {
    description "IPv4/IPv6 IP address and Prefix length";

    container ip-address {
      description "IPv4/IPv6 address";
      uses RIB-EDM-IP-ADDR;
    }
    leaf prefix-length {
      type uint8;
      description "Prefix length";
    }
  }

  grouping RIB-EDM-ROUTE {
    description
      "Information of a rib route head and rib proto
      route";

    container prefix {
      description "Route prefix";
      uses RIB-EDM-IP-PFX;
    }

    container srv6-info {
      description "SRv6 related information";
      uses RIB-EDM-ROUTE-SRV6-INFO;
    }

    container aft {
      description "Route AFT info";
      uses RIB-EDM-ROUTE-AFT-INFO;
    }
    leaf type {
      type Rib-edm-route;
      description "Type of the route - prefix or label";
    }
    leaf route-version {
      type uint32;
      description
        "Route version, incremented by one on each active
        route change";
    }
    leaf protocol-id {
      xr:event-telemetry "Subscribe Telemetry Event";
      type uint32;
      description "Protocol advertising the route";
    }
    leaf protocol-name {
      xr:event-telemetry "Subscribe Telemetry Event";
      type string;
      description " Name of Protocol";
    }
    leaf instance {
      type string;
      description "Instance name";
    }
    leaf client-id {
      type uint32;
      description "Client adding the route to RIB";
    }
    leaf mirrored {
      type boolean;
      description "Mirrored";
    }
    leaf route-type {
      xr:event-telemetry "Subscribe Telemetry Event";
      type uint16;
      description "Type of route installed in RIB";
    }
    leaf priority {
      xr:event-telemetry "Subscribe Telemetry Event";
      type uint8;
      description "Route priority";
    }
    leaf svd-type {
      type uint8;
      description "SVD Type of route";
    }
    leaf l2-route-type {
      type uint8;
      description "Type of route associated with L2 Service";
    }
    leaf flags {
      xr:event-telemetry "Subscribe Telemetry Event";
      type uint32;
      description "Route flags";
    }
    leaf extended-flags {
      xr:event-telemetry "Subscribe Telemetry Event";
      type uint64;
      description "Extended Route flags";
    }
    leaf tag {
      xr:event-telemetry "Subscribe Telemetry Event";
      type uint32;
      description "Opaque proto specific info";
    }
    leaf distance {
      xr:event-telemetry "Subscribe Telemetry Event";
      type uint32;
      description "Distance of the route";
    }
    leaf diversion-distance {
      type uint32;
      description "Diversion distance of the route";
    }
    leaf metric {
      xr:event-telemetry "Subscribe Telemetry Event";
      type uint32;
      description "Route metric";
    }
    leaf attribute-identity {
      type uint32;
      description "BGP Attribute ID";
    }
    leaf traffic-index {
      type uint8;
      description "BGP Traffic Index";
    }
    leaf route-precedence {
      xr:event-telemetry "Subscribe Telemetry Event";
      type uint8;
      description "IP precedence for this route";
    }
    leaf qos-group {
      xr:event-telemetry "Subscribe Telemetry Event";
      type uint8;
      description "Route qos group";
    }
    leaf flow-tag {
      xr:event-telemetry "Subscribe Telemetry Event";
      type uint8;
      description "Flow tag for this route";
    }
    leaf fwd-class {
      xr:event-telemetry "Subscribe Telemetry Event";
      type uint8;
      description "Forward Class";
    }
    leaf pic-count {
      type uint8;
      description "Number of pic paths in this route";
    }
    leaf active {
      type boolean;
      description "Is the route active or backup";
    }
    leaf unviable {
      type boolean;
      description "Is the route unviable";
    }
    leaf potential {
      type boolean;
      description
        "Is the route in potential install (the route
        update is held back to ensure lossless updates
        requirements are met)";
    }
    leaf has-potential {
      type boolean;
      description
        "Route has potential updates (updates that are
        held back to ensure lossless updates
        requirements are met)";
    }
    leaf diversion {
      type boolean;
      description "Route has a diversion path";
    }
    leaf diversion-proto-name {
      type string;
      description "Diversion route protocol name";
    }
    leaf route-age {
      type uint32;
      units "second";
      description "Age of route (seconds)";
    }
    leaf route-label {
      type uint32;
      description "Local label of the route";
    }
    leaf label-proto-id {
      type uint32;
      description "Label producer protocol ID";
    }
    leaf label-proto-name {
      type string;
      description "Label producer protocol name";
    }
    leaf version {
      type uint32;
      description "Route Version";
    }
    leaf tbl-version {
      type uint64;
      description "Table Version";
    }
    leaf route-modify-time {
      type uint64;
      units "nanosecond";
      description "Route modification time(nanoseconds)";
    }
    leaf prefix-feid {
      type uint64;
      description "Fib per-prefix encap id";
    }
    leaf no-fib-redist {
      type boolean;
      description "Should the route be redistributed to FIB";
    }
    leaf flexible-algorithm {
      type uint8;
      description "Flexible Algorithm associated with route";
    }
    leaf table-id {
      type uint32;
      description "Table id";
    }

    list algorithm-label {
      description
        "List of Algorithm Labels associated with this
        Prefix";
      uses RIB-EDM-ALGO-LABEL-SET;
    }

    list route-path {
      description "Path(s) of the route";
      uses RIB-EDM-PATH;
    }
  }
}
