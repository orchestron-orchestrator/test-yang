module Cisco-IOS-XR-openconfig-platform-pipeline-counters-ext {
  yang-version "1";
  namespace "http://cisco.com/ns/yang/Cisco-IOS-XR-openconfig-platform-pipeline-counters-ext";
  prefix "cisco";
  
  import openconfig-extensions { prefix oc-ext; }
  import openconfig-platform { prefix oc-platform; }
  import openconfig-platform-pipeline-counters { prefix oc-ppc; }
  
  organization
    "Cisco Systems, Inc";

  contact
    "Cisco Systems
     Customer Service
     Postal: 170 West Tasman Drive
     San Jose, CA 95134

     Tel: +1 800 553-NETS

     E-mail: cs-yang@cisco.com";

  description
    "Adding augments to oc-ppc yang for providing vendor based counters.";

  oc-ext:openconfig-version "0.1.0";
  oc-ext:catalog-organization "openconfig";
  oc-ext:origin "openconfig";

  revision "2024-08-30" {
    description
      "Initial revision to support vendor cisco container";
  }


 augment "/oc-platform:components/oc-platform:component/oc-platform:integrated-circuit/oc-ppc:pipeline-counters/oc-ppc:drop/oc-ppc:vendor" {
    description
    "Vendor container";
    container cisco {
      description
      "Cisco specific Drop container";
    }
  }
}
