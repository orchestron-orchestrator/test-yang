submodule Cisco-IOS-XR-linux-os-reboot-history-oper-sub1 {

  belongs-to Cisco-IOS-XR-linux-os-reboot-history-oper {
    prefix Cisco-IOS-XR-linux-os-reboot-history-oper;
  }

  /*** LINKAGE (IMPORTS / INCLUDES) ***/

  import cisco-semver { prefix "semver"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR linux-os-reboot-history package operational data.

     Copyright (c) 2013-2023 by Cisco Systems, Inc.
     All rights reserved.";

  revision "2023-03-03" {
    description
      "Added container last-reboot.";
    semver:module-version "1.1.0";
  }

  revision "2021-07-28" {
    description
      "Changed task-name from basic-services to system";
    semver:module-version "1.0.1";
  }

  revision "2019-04-05" {
    description
      "Establish semantic version baseline.";
    semver:module-version "1.0.1";
  }

  revision "2015-11-09" {
    description
      "IOS XR 6.0 revision.";
  }

  grouping HISTORY-DETAIL {
    description "Reboot history details";
    leaf no {
      type uint32;
      description "Number count";
    }
    leaf time {
      type string;
      description "Time of reboot";
    }
    leaf cause-code {
      type uint32;
      description "Cause code for reboot";
    }
    leaf reason {
      type string;
      description "Reason for reboot";
    }
  }

  grouping HISTORY {
    description "Reboot history information";

    container last-reboot {
      description "Last Reboot record";
      uses HISTORY-DETAIL;
    }

    list reboot-history {
      description "Last Reboots";
      uses HISTORY-DETAIL;
    }
  }
}
