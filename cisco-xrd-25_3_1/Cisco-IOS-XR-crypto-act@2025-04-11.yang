module Cisco-IOS-XR-crypto-act {
  namespace "http://cisco.com/ns/yang/Cisco-IOS-XR-crypto-act";
  prefix crypto-act;

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR action package configuration.

     Copyright (c) 2016-2025 by Cisco Systems, Inc., and/or its affiliates.
     All rights reserved.";

  revision 2025-04-11 {
    description
      "Added support for clearing certificates for both normal and OpenSSH trustpoints, as well as clearing the OpenSSH certificate revocation list.
       2024-08-27
         Added support to enroll certificate via file on local filesystem
       2023-07-05
         Fixed range format issue in dsa key generation rpc
       2023-04-07
         Added Support to generate authentication-ssh for input user label
       2022-11-30
         Added Support to generate authentication-ssh keys
       2022-06-02
         Added support to import more than one auth key for a user
       2022-03-20
         Added OpenSSH cert support
       2021-10-19
         Added key-label node to key-generate-dsa";
    semver:module-version "1.3.0";
  }

  revision "2020-09-18" {
    description
      "Change user task for ca-crl-request from cisco-support to crypto";
    semver:module-version "1.2.0";
  }

  revision "2019-10-01" {
    description
      "Made changes to be RFC6087 compliant";
    semver:module-version "1.1.0";
  }

  revision "2019-06-18" {
    description
      "IOS XR 7.0.1 revision.";
    semver:module-version "1.0.0";
  }

  revision "2019-04-05" {
    description
      "Establish semantic version baseline.";
  }

  revision "2016-04-17" {
    description
      "IOS XR 6.1.1 revision.";
  }

  grouping KEY-MODULUS {
    description
      "Key modulus grouping";
    leaf key-label {
      type string;
      description
        "RSA keypair label";
    }
    leaf key-modulus {
      type int32 {
        range "512..4096";
      }
      mandatory true;
      description
        "Key modulus in the range of 512 to 4096 for your General Purpose Keypair. Choosing a key modulus greater than 512 may take a few minutes";
    }
  }

  rpc key-generate-rsa-general-keys {
    description
      "Generate a general purpose RSA key pair for signing and encryption";
    input {
      uses KEY-MODULUS;
    }
  }
  rpc key-generate-rsa-usage-keys {
    description
      "Generate seperate RSA key pairs for signing and encryption";
    input {
      uses KEY-MODULUS;
    }
  }
  rpc key-generate-rsa {
    description
      "Generate seperate RSA key pairs for signing and encryption";
    input {
      uses KEY-MODULUS;
    }
  }
  rpc key-generate-dsa {
    description
      "Generate DSA keys";
    input {
      leaf key-modulus {
        type int32 {
          range "512..1024";
        }
        mandatory true;
        description
          "Key modulus size can be 512, 768 or 1024 bits.";
      }
      leaf key-label {
        type string;
        description
          "DSA key label";
      }
    }
  }
  rpc key-generate-authentication-ssh-rsa-keys {
    description
      "Generate Authentication SSH keys for passwordless operations";
    input {
      leaf key-modulus {
        type int32 {
          range "512..4096";
        }
        mandatory true;
        description
          "Key modulus in the range of 512 to 4096 for your General Purpose Keypair. Choosing a key modulus greater than 512 may take a few minutes";
      }
      leaf key-label {
          type string;
          description
              "Username to which the generated keys will be affiliated.";
      }
    }
  }
  rpc key-generate-ecdsa {
    description
      "Generate a ECDSA key of curve type nistp256 | nistp384 | nistp521";
    input {
      leaf key-modulus {
        type enumeration {
          enum nistp256 {
            value 0;
            description
              "nistp256";
          }
          enum nistp384 {
            value 1;
            description
              "nistp384";
          }
          enum nistp521 {
            value 2;
            description
              "nistp521";
          }
        }
        mandatory true;
        description
          "Key modulus";
      }
      leaf key-label {
        type string;
        description
          "ECDSA key label";
      }
    }
  }
  rpc key-generate-ed25519 {
    description
      "Generate a Ed25519 key-pair";
    input {
      leaf key-label {
        type string;
        description
          "Ed25519 key label";
      }
    }
  }
  rpc key-zeroize-rsa {
    description
      "Remove RSA keys";
    input {
      leaf key-label {
        type string;
        description
          "RSA key label";
      }
    }
  }
  rpc key-zeroize-dsa {
    description
      "Remove DSA keys";
  }
  rpc key-zeroize-authentication-ssh-rsa {
    description
      "Remove authentication-ssh keys";
    input {
      leaf key-label {
        type string;
        description
          "Key label";
      }
    }
  }
  rpc key-zeroize-ecdsa {
    description
      "Remove ECDSA key of curve type nistp256 | nistp384 | nistp521";
    input {
      leaf key-modulus {
        type enumeration {
          enum nistp256 {
            value 0;
            description
              "nistp256";
          }
          enum nistp384 {
            value 1;
            description
              "nistp384";
          }
          enum nistp521 {
            value 2;
            description
              "nistp521";
          }
        }
        mandatory true;
        description
          "Key modulus";
      }
      leaf key-label {
        type string;
        description
          "ECDSA key label";
      }
    }
  }
  rpc key-zeroize-authentication-rsa {
    description
      "Remove RSA authentication key";
    input {
      leaf key-num {
        type enumeration {
          enum second {
            value 2;
            description
              "second key";
          }
          enum third {
            value 4;
            description
              "third key";
          }
          enum fourth {
            value 8;
            description
              "fourth key";
          }
        }
        description
          "RSA pubkey number";
      }
    }
  }
  rpc key-zeroize-authentication-rsa-username {
    description
      "Remove RSA authentication key";
    input {
      leaf username {
        type string;
        mandatory true;
        description
          "Username";
      }
      leaf key-num {
        type enumeration {
          enum second {
            value 2;
            description
              "second key";
          }
          enum third {
            value 4;
            description
              "third key";
          }
          enum fourth {
            value 8;
            description
              "fourth key";
          }
        }
        description
          "RSA pubkey number";
      }
    }
  }
  rpc key-zeroize-authentication-rsa-all {
    description
      "Remove RSA authentication key";
  }
  rpc key-zeroize-ed25519 {
    description
      "Remove ed25519 keys";
    input {
      leaf key-label {
        type string;
        description
          "Ed25519 key label";
      }
    }
  }
  rpc key-import-authentication-rsa {
    description
      "Remove RSA authentication key";
    input {
      leaf path {
        type string;
        mandatory true;
        description
          "Path to RSA pubkey file";
      }
      leaf key-num {
        type enumeration {
          enum second {
            value 2;
            description
              "second key";
          }
          enum third {
            value 4;
            description
              "third key";
          }
          enum fourth {
            value 8;
            description
              "fourth key";
          }
        }
        description
          "RSA pubkey number";
      }
    }
  }
  rpc key-import-authentication-rsa-username {
    description
      "RSA authentication key for user";
    input {
      leaf path {
        type string;
        mandatory true;
        description
          "Path to RSA pubkey file";
      }
      leaf username {
        type string;
        mandatory true;
        description
          "Username";
      }
      leaf key-num {
        type enumeration {
          enum second {
            value 2;
            description
              "second key";
          }
          enum third {
            value 4;
            description
              "third key";
          }
          enum fourth {
            value 8;
            description
              "fourth key";
          }
        }
        description
          "RSA pubkey number";
      }
    }
  }
  rpc ca-authenticate {
    description
      "Get the certification authority certificate";
    input {
      leaf server-name {
        type string;
        mandatory true;
        description
          "CA Server Name";
      }
      leaf file-path {
          type string {
              length "1..256";
          }
          description
              "Location of file containing the CA certificate(s) on router in case of local enrollment.";
      }
    }
  }
  rpc ca-enroll {
    description
      "Request a certificate from a CA";
    input {
      leaf server-name {
        type string;
        mandatory true;
        description
          "CA Server Name";
      }
      leaf file-path {
          type string {
              length "1..256";
          }
          description
              "Location of file to which the CSR will be written in case of local enrollment.";
      }
    }
  }
  rpc ca-import-certificate {
    description
      "Import a certificate from a s/tftp server or the terminal";
    input {
      leaf server-name {
        type string;
        mandatory true;
        description
          "CA Server Name";
      }
      leaf file-path {
          type string {
              length "1..256";
          }
          description
              "Location of file containing the leaf certificate(s) on router in case of local enrollment.";
      }
    }
  }
  rpc ca-clear-certificates {
    description
        "Remove all crypto certificates associated with a trustpoint.";
    input {
        leaf server-name {
            type string {
                length "1..128";
            }
            mandatory true;
            description
                "Trustpoint Name";
        }
    }
  }
  rpc ca-cancel-enroll {
    description
      "Cancel enrollment from a CA";
    input {
      leaf server-name {
        type string;
        mandatory true;
        description
          "CA Server Name";
      }
    }
  }
  rpc ca-crl-request {
    description
      "Actions on certificate revocation lists";
    input {
      leaf uri {
        type string;
        mandatory true;
        description
          "CRL Distribution Point in URI format";
      }
    }
    output {
      leaf certificate {
        type string;
        mandatory true;
        description
          "Certificate returned";
      }
    }
  }
  rpc ca-trustpool-import-url {
    description
      "Manual import trustpool certificates from URL";
    input {
      leaf url {
        type string;
        description
          "in URL format";
      }
    }
  }
  rpc ca-trustpool-import-url-clean {
    description
      "Remove downloaded certificates in trustpool";
    input {
      leaf url {
        type string;
        description
          "in URL format";
      }
    }
  }

  rpc ca-openssh-authenticate {                                                         
    description                                                                 
      "Get the OpenSSH certification authority certificate";                            
    input {                                                                     
      leaf server-name {                                                        
        type string;                                                            
        mandatory true;                                                         
        description                                                             
          "Certificate Authority Server Name";                                                     
      }
      leaf path {                                                               
        type string;                                                            
        mandatory true;                                                         
        description                                                             
          "Path to Certificate";                                                       
      }                                                                         
    }                                                                           
  }                                                                             
  rpc ca-openssh-enroll {                                                               
    description                                                                 
      "Request hostkey from router";                                        
    input {                                                                     
      leaf server-name {                                                        
        type string;                                                            
        mandatory true;                                                         
        description                                                             
          "Certificate Authority Server Name";                                                     
      }                                                                         
    }                                                                           
  }                                                                             
  rpc ca-openssh-import-certificate {                                                   
    description                                                                 
      "Import certificate from a file";              
    input {                                                                     
      leaf server-name {                                                        
        type string;                                                            
        mandatory true;                                                         
        description                                                             
          "Certificate Authority Server Name";                                                     
      } 
      leaf path {
        type string;                                                            
        mandatory true;                                                         
        description                                                             
          "Path to Certificate";                                                     
      }                                                                        
    }                                                                           
  }
  rpc ca-openssh-revoke {
    description                                                                 
      "Add a revoked certificate/key";
    input {
      leaf path {
        type string;                                                            
        mandatory true;                                                         
        description                                                             
          "Path to Certificate";                                                      
      }                                                                         
    }
  }    
  rpc ca-openssh-clear-certificates {
    description
        "Remove all crypto certificates with an OpenSSH-based trustpoint.";
    input {
        leaf server-name {
            type string {
                length "1..128";
            }
            mandatory true;
            description
                "OpenSSH Trustpoint Name";
        }
    }
  }
  rpc ca-openssh-clear-revoked-list {
      description
          "Clear the openssh certificate revoked list";
  }
}
