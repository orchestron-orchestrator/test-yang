module Cisco-IOS-XR-lib-type6-act {
  namespace "http://cisco.com/ns/yang/Cisco-IOS-XR-lib-type6-act";
  prefix lib-type6-act;

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR action package configuration.

     Copyright (c) 2018-2021, 2024 by Cisco Systems, Inc.
     All rights reserved.";

  revision "2024-04-12" {
    description
      "Added ike as client.";
    semver:module-version "2.2.0";
  }

  revision "2021-04-06" {
    description
      "Added masterkey update abort support.";
    semver:module-version "2.1.0";
  }

  revision "2020-10-16" {
    description
      "Changed the input type of clear-type6-client to enum";
    semver:module-version "2.0.0";
  }

  revision "2019-10-01" {
    description
      "Made changes to be RFC6087 compliant";
    semver:module-version "1.1.0";
  }

  revision "2019-04-05" {
    description
      "Establish semantic version baseline.";
    semver:module-version "1.0.0";
  }

  revision "2018-10-19" {
    description
      "IOS XR 6.3.1 revision.";
  }

  typedef Client-name {
    type enumeration {
      enum keychain {
        value 0;
        description "keychain";
      }
      enum snmp {
        value 1;
        description "snmp";
      }
      enum radiusd {
        value 2;
        description "radiusd";
      }
      enum tacacsd {
        value 3;
        description "tacacsd";
      }
      enum ike {
        value 4;
        description "ike";
      }
    }
    description "Type6 client name";
  }

  grouping MASTER-KEY {
    description
      "Master Key Group";
    leaf old-key {
      type string;
      mandatory true;
      description
        "key already added/key to be replaced";
    }
    leaf new-key {
      type string;
      mandatory true;
      description
        "New master key to be added ";
    }
  }

  rpc master-key-add {
    description
      "To add a new master key";
    input {
      leaf new-key {
        type string;
        description
          "New master key to be added";
      }
    }
  }
  rpc master-key-delete {
    description
      "Remove Master key";
  }
  rpc master-key-update {
    description
      "To update master key";
    input {
      uses MASTER-KEY;
    }
  }
  rpc clear-type6-client {
    description
      "To clear type6 client";
    input {
      leaf client-name {
        type Client-name;
        mandatory true;
        description
          "Client Name";
      }
    }
  }

  rpc masterkey-update-abort {
      description
          "Abort masterkey update operation";
  }
}
