module Cisco-IOS-XR-ip-rib-ipv4-oper {

  /*** NAMESPACE / PREFIX DEFINITION ***/

  namespace "http://cisco.com/ns/yang/Cisco-IOS-XR-ip-rib-ipv4-oper";


  prefix "ip-rib-ipv4-oper";

  /*** LINKAGE (IMPORTS / INCLUDES) ***/

  import ietf-inet-types { prefix "inet"; }

  import Cisco-IOS-XR-types { prefix "xr"; }

  import cisco-semver { prefix "semver"; }

  include Cisco-IOS-XR-ip-rib-ipv4-oper-sub2 {
    revision-date 2023-11-01;
  }

  include Cisco-IOS-XR-ip-rib-ipv4-oper-sub1 {
    revision-date 2023-11-01;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ip-rib-ipv4 package operational data.

     This model is deprecated and is replaced by
     Cisco-IOS-XR-ip-rib-oper.yang which will provide the
     compatible functionalities.

     This module contains definitions
     for the following management objects:
       ipv6-rib: RIB operational data
       rib-stdby: RIB standby node operational data
       rib: RIB operational data
       ipv6-rib-stdby: RIB standby node IPv6 operational data

     Copyright (c) 2013-2023 by Cisco Systems, Inc.
     All rights reserved.";

  revision "2023-11-01" {
    description
      "Deprecated. Move to Cisco-IOS-XR-ip-rib-oper";
    semver:module-version "5.0.0";
  }

  revision "2021-07-20" {
    description
      "Flexible Algorithm attribute added to IP Route
      2021-06-24
          L2 Path attribute extended with support for Split Horizong Group and BridgeID
      2021-03-25
          Add FIB redistribution flag to route bag";
    semver:module-version "4.1.0";
  }

  revision "2020-12-11" {
    description
      "Add forwarding sidlist
      2020-10-16
           Route model now includes optional SRv6 SID Format field for SRv6 Local SID routes
      2020-09-30
           Nexthop notification model now includes client specific registration flags";
    semver:module-version "4.0.0";
  }

  revision "2020-05-29" {
    description
      "Updated the max number of elements for opaque stats to 16 Extended rib edm path to include IID info and SID Format type
      2020-04-02
         Increased path_num size in redist hist route bag to 16 bits";
    semver:module-version "3.0.0";
  }

  revision "2019-11-05" {
    description
      "Extended Nexthop and NexhopPrefix paths to include all by NH flags
      2019-10-22
         Extended rib_edm_client_stats_summary to include client stats on bcdl ugs Extended rib_edm_local_label to support AIB prefer Extended rib_edm_path to include recursion length field Extended rib_edm_path to include metric field Extended iidmgr_summary to include oor summary info Extended rib_edm_route to include l3 route type field";
    semver:module-version "2.0.0";
  }

  revision "2019-06-28" {
    description
      "Fixed NexthopPrefix path";
    semver:module-version "1.0.0";
  }

  revision "2019-06-08" {
    description
      "Added RPF list and NHIDs";
  }

  revision "2019-05-30" {
    description
      "Fixed adverts and backup paths";
  }

  revision "2019-05-17" {
    description
      "Added Nexthops Summary, Nexthop Route, Longer Routes, Redist Clients and Client Stasts";
  }

  revision "2019-04-25" {
    description
      "Updated yang schema to extend Native Yang model for the data exposed via CLI";
  }

  revision "2019-04-05" {
    description
      "Establish semantic version baseline.";
  }

  revision "2019-02-21" {
    description
      "Yang evaluator: updates to schema descriptions and ranges";
  }

  revision "2019-01-11" {
    description
      "Route lookup key is limited to Prefix and Prefix Length";
  }

  revision "2018-11-20" {
    description
      "Add keys for route lookup via restconf.";
  }

  revision "2018-11-06" {
    description
      "Support Algorithm Label List per route";
  }

  revision "2015-11-09" {
    description
      "IOS XR 6.0 revision.";
  }

  typedef Rpf-head-count-range {
    type uint32 {
      range "0..4294967295";
    }
    description "Rpf head count range";
  }
  typedef Rib-saf-name {
    type string {
      pattern '(Unicast)|(Multicast)';
    }
    description
      "Unicast:   Comment: Ucast string for <safi_name>,
      Multicast: Comment: Mcast string for <safi_name>";
  }
  typedef Rib-af-name {
    type string {
      pattern '(IPv4)|(IPv6)';
    }
    description
      "IPv4: Comment: v4 string for <afi_name>, IPv6:
      Comment: v6 string for <afi_name>";
  }
  typedef Nhid-hist-count-range {
    type uint32 {
      range "0..4294967295";
    }
    description "Nhid hist count range";
  }
  typedef Table-id-range {
    type uint32 {
      range "0..4294967295";
    }
    description "Table id range";
  }
  typedef Nhid-entry-count-range {
    type uint32 {
      range "0..4294967295";
    }
    description "Nhid entry count range";
  }

  grouping IID-MGR-INFO {
    description "Common node of iid-mgr-active, iid-mgr-standby";

    container iid-mgr-info {
      description "IID Manager information";
      uses IIDMGR-INFO;
    }
  }

  grouping RIBNHG-TABLE {
    description "Common node of ipv6-rib, ipv6-rib-stdby";

    container ribnhg-table {
      description "RIB next hop groups";

      container rib-unviable-nhg-names {
        description "RIB unviable NHG Names";

        list rib-unviable-nhg-name {
          key "nhg-name";
          description "RIB unviable NHG";
          leaf nhg-name {
            type xr:Cisco-ios-xr-string;
            description "NHG Name";
          }
          uses RIB-EDM-NHG;
        }
      }

      container ribnhg-names {
        description "RIB NHG Names";

        list ribnhg-name {
          key "nhg-name";
          description "RIB NHG";
          leaf nhg-name {
            type xr:Cisco-ios-xr-string;
            description "NHG Name";
          }
          uses RIB-EDM-NHG;
        }
      }
    }
  }

  grouping ALL-IID-TABLE {
    description "Common node of iid-mgr-active, iid-mgr-standby";

    container all-iids {
      description
        "Operational container for all (Active and Stale)
        IIDs";

      list all-iid {
        key "iid-prefix";
        description "Operational data for a given IID";
        leaf iid-prefix {
          type inet:ipv6-address-no-zone;
          description "IID Value as IPv6 prefix";
        }
        uses IIDMGR-IID-INFO;
      }
    }
  }

  grouping RIB-NH-ID-HISTORY-TABLE {
    description
      "Common node of rib, rib-stdby, ipv6-rib,
      ipv6-rib-stdby";

    container rib-nh-id-histories {
      description "nhids history";

      list rib-nh-id-history {
        key "nh-idi-hist-count";
        description "NH Id history count";
        leaf nh-idi-hist-count {
          type Nhid-hist-count-range;
          description "NH Id hist count";
        }
        uses RIB-EDM-NHID-HIST-OBJ;
      }
    }
  }

  grouping VRF-TABLE {
    description
      "Common node of rib, rib-stdby, ipv6-rib,
      ipv6-rib-stdby";

    container vrfs {
      description "VRF table";

      list vrf {
        key "vrf-name";
        description "Specific VRF";

        container afs {
          description "Address Family (AF) table";

          list af {
            key "af-name";
            description "Specific AF information";

            container safs {
              description "Subsequent Address Family (SAF) table";

              list saf {
                key "saf-name";
                description "Specific SAF information";

                container ip-rib-route-table-names {
                  description "Global container of routes";

                  list ip-rib-route-table-name {
                    key "route-table-name";
                    description
                      "IP RIB Route table name for a topology";

                    container routes {
                      description "Route information ";

                      list route {
                        key "network";
                        description
                          "Route information of a specific Network
                          Address ";
                        leaf network {
                          type inet:ip-prefix;
                          description "Network Prefix and Length";
                        }
                        uses RIB-EDM-ROUTE;
                      }
                    }

                    container nexthop-damping-histories {
                      description "Nexthop damping history";

                      list nexthop-damping-history {
                        key "index";
                        description
                          "List the nexthop damping history";
                        leaf index {
                          type uint32 {
                            range "0..4294967295";
                          }
                          description "Index";
                        }
                        uses RIB-EDM-NH-DAMP-HIST-INFO;
                      }
                    }

                    container deleted-routes {
                      description "Deleted";

                      list deleted-route {
                        key "network";
                        description
                          "Route information for a specific
                          deleted address ";
                        leaf network {
                          type inet:ip-prefix;
                          description "Deleted Prefix and Length";
                        }
                        uses RIB-EDM-ROUTE;
                      }
                    }

                    container destination-kw {
                      description "Destination KW";

                      container dest-best-routes {
                        description "Best Local";

                        list dest-best-route {
                          key "address";
                          description
                            "Best local route information for a
                            specific Address ";
                          leaf address {
                            type inet:ip-address-no-zone;
                            description "Network Address";
                          }
                          uses RIB-EDM-ROUTE;
                        }
                      }

                      container dest-q-routes {
                        description "Quarantine";

                        list dest-q-route {
                          key "network";
                          description
                            "Route information of a specific
                            quarantined address ";
                          leaf network {
                            type inet:ip-prefix;
                            description
                              "Quarantined network address  and
                              Length";
                          }
                          uses RIB-EDM-ROUTE;
                        }
                      }

                      container dest-backup-kw {
                        description "Backup";

                        container dest-backup-prefixes {
                          description
                            "Backup adresses prefix table";

                          list dest-backup-prefix {
                            key "network-addr network-prefix";
                            description
                              "Route information of a specific
                              Backup Address ";

                            container dest-backup-routes {
                              description
                                "Backup adresses route table";

                              list dest-backup-route {
                                key "protoid";
                                description
                                  "Route information of a specific
                                  Backup Address and Client ";
                                leaf protoid {
                                  type uint32 {
                                    range "0..96";
                                  }
                                  description "Proto ID";
                                }
                                uses RIB-EDM-ROUTE;
                              }
                            }
                            leaf network-addr {
                              type inet:ip-address;
                              description
                                "Backup Prefix and Length (address
                                part)";
                            }
                            leaf network-prefix {
                              type uint16 {
                                range "0..128";
                              }
                              description
                                "Backup Prefix and Length (prefix
                                part)";
                            }
                          }
                        }
                      }

                      container dest-potential-kw {
                        description "Potential";

                        container dest-potential-prefixes {
                          description
                            "Potential addresses prefix table
                            (Prefixes with updates that are held
                            back to ensure lossless updates
                            requirements are met)";

                          list dest-potential-prefix {
                            key "network-addr network-prefix";
                            description
                              "Route information of a specific
                              Backup Address ";

                            container dest-potential-routes {
                              description
                                "Potential addresses route table
                                (Prefixes with updates that are held
                                back to ensure lossless updates
                                requirements are met)";

                              list dest-potential-route {
                                key "protoid potential";
                                description
                                  "Route information of a specific
                                  Potential Address and Client ";
                                leaf protoid {
                                  type uint32 {
                                    range "0..96";
                                  }
                                  description "Proto ID";
                                }
                                leaf potential {
                                  type boolean;
                                  description
                                    "Unresolved Nexthop Tree";
                                }
                                uses RIB-EDM-ROUTE;
                              }
                            }
                            leaf network-addr {
                              type inet:ip-address;
                              description
                                "Potential Prefix and Length (address
                                part)";
                            }
                            leaf network-prefix {
                              type uint16 {
                                range "0..128";
                              }
                              description
                                "Potential Prefix and Length (prefix
                                part)";
                            }
                          }
                        }
                      }

                      container dest-next-hop-routes {
                        description "Resolving next hop";

                        list dest-next-hop-route {
                          key "address";
                          description
                            "Nexthop information for a specific
                            address";
                          leaf address {
                            type inet:ip-address-no-zone;
                            description "Network Address";
                          }
                          uses RIB-EDM-ROUTE;
                        }
                      }
                    }

                    container protocol {
                      description
                        "Contains the classification of routes by
                        protocol";

                      container mobile {
                        description "Mobile Protocol";
                        uses NON-AS;
                      }

                      container subscriber {
                        description "Subscriber Protocol";
                        uses NON-AS;
                      }

                      container connected {
                        description "Connected Protocol";

                        container l2vpn {
                          description "L2VPN";
                          uses PROTOCOL-ROUTE-TABLE;
                          uses INFORMATION;
                        }
                        uses NON-AS;
                      }

                      container dagr {
                        description
                          "DAGR Protocol(Direct-Attached Gateway
                          Redundancy) Protocol";
                        uses NON-AS;
                      }

                      container rip {
                        description "RIP Protocol";
                        uses NON-AS;
                      }

                      container iid-local {
                        description "Internal ID Local Protocol";
                        uses NON-AS;
                      }

                      container ospf {
                        description "OSPF Protocol";
                        uses AS;
                      }

                      container srv6-local {
                        description "SRv6-Local Protocol";
                        uses NON-AS;
                      }

                      container static {
                        description "Static Protocol";
                        uses NON-AS;
                      }

                      container rpl {
                        description "RPL Protocol";
                        uses AS;
                      }

                      container application {
                        description "Application Protocol";
                        uses NON-AS;
                      }

                      container te-client {
                        description "TEClient Protocol";
                        uses NON-AS;
                      }

                      container eigrp {
                        description "EIGRP Protocol";
                        uses AS;
                      }

                      container local {
                        description "Local Protocol";

                        container smiap {
                          description "SMIAP";
                          uses PROTOCOL-ROUTE-TABLE;
                          uses INFORMATION;
                        }

                        container lspv {
                          description
                            "LSPV(Label Switched Path Verification)
                            Protocol";
                          uses PROTOCOL-ROUTE-TABLE;
                          uses INFORMATION;
                        }
                        uses NON-AS;
                      }

                      container bgp {
                        description "BGP Protocol";
                        uses AS;
                      }

                      container isis {
                        description "ISIS Protocol";
                        uses AS;
                      }
                    }

                    container opaques {
                      description "Opaque information ";

                      list opaque {
                        key "opaque-client-id opaque-proto-id"+
                          " opaque-key-type opaque-key-size"+
                          " opaque-data-size opaque-string";
                        description "Opaque item ";
                        leaf opaque-client-id {
                          type uint32 {
                            range "0..2501";
                          }
                          description "Opaque Client ID";
                        }
                        leaf opaque-proto-id {
                          type uint32 {
                            range "0..96";
                          }
                          description "Opaque Proto ID";
                        }
                        leaf opaque-key-type {
                          type uint32 {
                            range "0..24";
                          }
                          description
                            "The type of the opaque key installed
                            in the RIB table";
                        }
                        leaf opaque-key-size {
                          type uint32 {
                            range "0..4294967295";
                          }
                          description
                            "The size of the opaque key installed
                            in the RIB table";
                        }
                        leaf opaque-data-size {
                          type uint32 {
                            range "0..4294967295";
                          }
                          description
                            "The size of the opaque data installed
                            in the RIB table";
                        }
                        leaf opaque-string {
                          type xr:Cisco-ios-xr-string;
                          description
                            "The opaque data installed in the RIB
                            table";
                        }
                        uses RIB-EDM-OPAQUE-OBJ;
                      }
                    }

                    container q-routes {
                      description "Quarantine";

                      list q-route {
                        key "network";
                        description
                          "Route information for a specific
                          quarantined address ";
                        leaf network {
                          type inet:ip-prefix;
                          description
                            "Quarantined Prefix and Length";
                        }
                        uses RIB-EDM-ROUTE;
                      }
                    }

                    container longer-route-prefixes {
                      description "Longer routes prefix table";

                      list longer-route-prefix {
                        key "network-addr network-prefix";
                        description
                          "Net/mask to match longer routes";

                        container longer-route-last-prefixes {
                          description
                            "Longer route last prefix table";

                          list longer-route-last-prefix {
                            key "network";
                            description
                              "Information of all matching longer
                              routes for a prefix/mask under a
                              given table";
                            leaf network {
                              type inet:ip-prefix;
                              description
                                "Network address and Length";
                            }
                            uses RIB-EDM-ROUTE;
                          }
                        }
                        leaf network-addr {
                          type inet:ip-address;
                          description
                            "Network address and Length (address
                            part)";
                        }
                        leaf network-prefix {
                          type uint16 {
                            range "0..128";
                          }
                          description
                            "Network address and Length (prefix
                            part)";
                        }
                      }
                    }

                    container nexthops {
                      description
                        "Nexthop notification registerations
                        under a given table";

                      list nexthop {
                        key "network table-id unresolved-nh-tree"+
                          " exact-match allow-default recurse"+
                          " cross-table pack-sfs pack-backup-paths"+
                          " backup-route best-metric algo-label-set"+
                          " track-cross-table";
                        description
                          "List the nexthop notification
                          registeration under a given table";
                        leaf network {
                          type inet:ip-prefix;
                          description "Network address and Length";
                        }
                        leaf table-id {
                          type Table-id-range;
                          description "Network Table Id";
                        }
                        leaf unresolved-nh-tree {
                          type boolean;
                          description "Unresolved Nexthop Tree";
                        }
                        leaf exact-match {
                          type boolean;
                          description "Exact match";
                        }
                        leaf allow-default {
                          type boolean;
                          description "Allow Default";
                        }
                        leaf recurse {
                          type boolean;
                          description "Recurse";
                        }
                        leaf cross-table {
                          type boolean;
                          description "Cross table nextHop";
                        }
                        leaf pack-sfs {
                          type boolean;
                          description
                            "Pack SFS paths for Multicast";
                        }
                        leaf pack-backup-paths {
                          type boolean;
                          description "Pack backup paths";
                        }
                        leaf backup-route {
                          type boolean;
                          description "Backup route notifications";
                        }
                        leaf best-metric {
                          type boolean;
                          description "Return lowest metric";
                        }
                        leaf algo-label-set {
                          type boolean;
                          description "Pack Algo Label Set";
                        }
                        leaf track-cross-table {
                          type boolean;
                          description "Track cross table nexthop";
                        }
                        uses RIB-EDM-NH-ADDR;
                      }
                    }

                    container unviable-routes {
                      description "Unviable";

                      list unviable-route {
                        key "network protoid";
                        description
                          "Information for an unviable route
                          provided by a protocol.";
                        leaf network {
                          type inet:ip-prefix;
                          description "Unviable Prefix and Length";
                        }
                        leaf protoid {
                          type uint32 {
                            range "0..96";
                          }
                          description "Unviable Proto ID";
                        }
                        uses RIB-EDM-ROUTE;
                      }
                    }

                    container backup-routes {
                      description
                        "Backup route information for the given
                        table";

                      list backup-route {
                        key "network protoid";
                        description
                          "Route information for a specific backup
                          address ";
                        leaf network {
                          type inet:ip-prefix;
                          description "Backup Prefix and Length";
                        }
                        leaf protoid {
                          type uint32 {
                            range "0..96";
                          }
                          description "Proto ID";
                        }
                        uses RIB-EDM-ROUTE;
                      }
                    }

                    container ribtph-entries {
                      description
                        "List of entries in
                        tracked-prefix-history db";

                      list ribtph-entry {
                        key "id";
                        description
                          "Event information that occured to a
                          specific prefix";
                        leaf id {
                          type xr:Cisco-ios-xr-string;
                          description "History entry ID";
                        }
                        uses RIB-EDM-TPH-DB-ENTRY;
                      }
                    }

                    container adverts-list {
                      description "Route advertiser information ";

                      container advert-prefixes {
                        description "Route advertiser prefix table";

                        list advert-prefix {
                          key "network-addr network-prefix";
                          description
                            "Route advertiser information of a
                            specific Network Address ";

                          container adverts {
                            description "Route advertiser table";

                            list advert {
                              key "protoid";
                              description
                                "Route advertiser information of a
                                specific Network Address and Client";
                              leaf protoid {
                                type uint32 {
                                  range "0..96";
                                }
                                description "Proto ID";
                              }
                              uses RIB-EDM-ADVERT;
                            }
                          }
                          leaf network-addr {
                            type inet:ip-address;
                            description
                              "Network address and Length (address
                              part)";
                          }
                          leaf network-prefix {
                            type uint16 {
                              range "0..128";
                            }
                            description
                              "Network address and Length (prefix
                              part)";
                          }
                        }
                      }
                    }
                    leaf route-table-name {
                      type xr:Cisco-ios-xr-string;
                      description "Name of the route table";
                    }
                  }
                }
                leaf saf-name {
                  type Rib-saf-name;
                  description "Name of the SAF";
                }
              }
            }
            leaf af-name {
              type Rib-af-name;
              description "Name of the AF";
            }
          }
        }
        leaf vrf-name {
          type string;
          description "Name of the VRF";
        }
      }
    }
  }

  grouping RIB-STATS {
    description
      "Common node of rib, rib-stdby, ipv6-rib,
      ipv6-rib-stdby";

    container rib-stats {
      description "Statistics summary";

      container rib-stats-summary {
        description "Summary";
        uses RIB-EDM-STATS-SUMMARY;
      }
    }
  }

  grouping AS {
    description "Common node of bgp, ospf, isis, eigrp, rpl";

    list as {
      key "as";
      description "Autonomous System of protocol";
      leaf as {
        type xr:Cisco-ios-xr-string;
        description "Autonomous system";
      }
      uses PROTOCOL-ROUTE-TABLE;
      uses INFORMATION;
    }
  }

  grouping RIB-RPF-LIST-TABLE {
    description
      "Common node of rib, rib-stdby, ipv6-rib,
      ipv6-rib-stdby";

    container rib-rpfs {
      description "Route prefix table";

      list rib-rpf {
        key "table-id";
        description "Table Id";

        container rib-rpf-list-routes {
          description "rpf list table route";

          list rib-rpf-list-route {
            key "network";
            description "Last route prefix and prefix length";
            leaf network {
              type inet:ip-prefix;
              description "Network address and Length";
            }
            uses RIB-EDM-RPFLIST-OBJ;
          }
        }

        container rib-rpf-list-summary-head-counts {
          description "rpf list table summary";

          list rib-rpf-list-summary-head-count {
            key "rpf-head-count";
            description "RPF Head count";
            leaf rpf-head-count {
              type Rpf-head-count-range;
              description "RPF Head count";
            }
            uses RIB-EDM-RPFLIST-OBJ;
          }
        }
        leaf table-id {
          type Table-id-range;
          description "Table ID";
        }
      }
    }
  }

  grouping INFORMATION {
    description "Common node of as, non-as, l2vpn, smiap, lspv";

    container information {
      description "Protocol related Information";
      uses RIB-EDM-PROTO;
    }
  }

  grouping RIB-TABLE {
    description
      "Common node of rib, rib-stdby, ipv6-rib,
      ipv6-rib-stdby";

    container rib-table-ids {
      description "RIB table";

      list rib-table-id {
        key "tableid";
        description "Specific Table";

        container summary-protos {
          description "RIB table summary";

          list summary-proto {
            key "protoid";
            description
              "Route summary information for a specific
              table/protocol ";
            leaf protoid {
              type uint32 {
                range "0..96";
              }
              description "Proto ID";
            }
            uses RIB-EDM-PROTO-ROUTE-SUMM-DETAIL;
          }
        }

        container rib-table-itf-hndls {
          description "RIB table interface";

          list rib-table-itf-hndl {
            key "handle";
            description "Interface handle";
            leaf handle {
              type uint32 {
                range "0..4294967295";
              }
              description "Itf Handle";
            }

            list itf-route {
              key "address";
              description
                "Route information for a specific
                table/interface ";
              leaf address {
                type inet:ip-address-no-zone;
                description "Network Address";
              }
              uses RIB-EDM-ROUTE;
            }
          }
        }

        container information {
          description "Table related Information";
          uses RIB-EDM-TABLE;
        }

        container rib-nexthop-prefixes {
          description "RIB table nexthop client table";

          list rib-nexthop-prefix {
            key "network unresolved-nh-tree";
            description "Route address, Prefix length";

            container rib-nexthop-routes {
              description "Nexthop route table";

              list rib-nexthop-route {
                key "table-id exact-match allow-default recurse"+
                  " cross-table pack-sfs pack-backup-paths"+
                  " backup-route best-metric algo-label-set"+
                  " track-cross-table";
                description
                  "Route information for a specific
                  table/interface";
                leaf table-id {
                  type Table-id-range;
                  description "Network Table Id";
                }
                leaf exact-match {
                  type boolean;
                  description "Exact Match";
                }
                leaf allow-default {
                  type boolean;
                  description "Allow Default";
                }
                leaf recurse {
                  type boolean;
                  description "Recurse";
                }
                leaf cross-table {
                  type boolean;
                  description "Cross table nextHop";
                }
                leaf pack-sfs {
                  type boolean;
                  description "Pack SFS paths for Multicast";
                }
                leaf pack-backup-paths {
                  type boolean;
                  description "Pack backup paths";
                }
                leaf backup-route {
                  type boolean;
                  description "Backup route notifications";
                }
                leaf best-metric {
                  type boolean;
                  description "Return lowest metric";
                }
                leaf algo-label-set {
                  type boolean;
                  description "Pack Algo Label Set";
                }
                leaf track-cross-table {
                  type boolean;
                  description "Track cross table nexthop";
                }
                uses RIB-EDM-NH-ADDR;
              }
            }
            leaf network {
              type inet:ip-prefix;
              description "Route address and Length";
            }
            leaf unresolved-nh-tree {
              type boolean;
              description "Unresolved Nexthop Tree";
            }
          }
        }

        container nexthops-summary {
          description "Nexthops summary";
          uses RIB-EDM-NH-STATS;
        }
        leaf tableid {
          type xr:Hex-integer;
          description "Table ID";
        }
      }
    }
  }

  grouping RIB-MAX-DEPTH {
    description
      "Common node of rib, rib-stdby, ipv6-rib,
      ipv6-rib-stdby";

    container rib-max-depth {
      description "Information of maximum recursion depth in RIB";
      uses RIB-EDM-RECURSION-DEPTH-MAX;
    }
  }

  grouping RIB-IID-MGR {
    description "Common node of ipv6-rib, ipv6-rib-stdby";

    container rib-iid-mgr {
      description "RIB IID Operational Data";

      container iid-mgr-active {
        description "Active RIB IID operational data";
        uses IID-MGR-INFO;
        uses IID-TABLE;
        uses ALL-IID-TABLE;
      }

      container iid-mgr-standby {
        description "Standby RIB IID operational data";
        uses IID-MGR-INFO;
        uses IID-TABLE;
        uses ALL-IID-TABLE;
      }
    }
  }

  grouping RIB-NH-ID-SUMMARY-TABLE {
    description
      "Common node of rib, rib-stdby, ipv6-rib,
      ipv6-rib-stdby";

    container rib-nh-id-summaries {
      description "NHIds table";

      list rib-nh-id-summary {
        key "tableid";
        description "Table Id";

        container rib-nh-ids {
          description "nhids summary";

          list rib-nh-id {
            key "nh-id-entry-count";
            description "NH Id";
            leaf nh-id-entry-count {
              type Nhid-entry-count-range;
              description "NH Id entry count";
            }
            uses RIB-EDM-NHID-OBJ;
          }
        }
        leaf tableid {
          type xr:Hex-integer;
          description "Table ID";
        }
      }
    }
  }

  grouping RIB-UPDATE-GROUP-TABLE {
    description
      "Common node of rib, rib-stdby, ipv6-rib,
      ipv6-rib-stdby";

    container rib-update-groups {
      description "RIB UpdateGroup table";

      list rib-update-group {
        key "update-group-id";
        description "UpdateGroup id";

        container rib-update-group-info {
          description "Information of specific updategroup";
          uses RIB-EDM-UG;
        }
        leaf update-group-id {
          type uint32;
          description "UpdateGroup Id";
        }
      }
    }
  }

  grouping RIB-CLIENT-TABLE {
    description
      "Common node of rib, rib-stdby, ipv6-rib,
      ipv6-rib-stdby";

    container rib-clients {
      description "Client";

      list rib-client {
        key "clientid";
        description "Specific Client";

        container rib-client-redist-stats {
          description "Redist statistics of a specific client";
          uses RIB-EDM-STATS-REDIST;
        }

        container rib-client-stats-client {
          description "Client statistics of a specific client";
          uses RIB-EDM-CLIENT-STATS-SUMMARY;
        }

        container rib-client-stats {
          description "Statistics of table of a specific client";

          list rib-client-stat {
            key "table-id";
            description "Specific Table";

            container rib-client-stats-protos {
              description
                "Statistics of table of protocol of a
                specific client";

              list rib-client-stats-proto {
                key "proto-id";
                description "Specific proto id";
                leaf proto-id {
                  type uint32 {
                    range "0..96";
                  }
                  description "Proto ID";
                }
                uses RIB-EDM-CLIENT-PROTO-STATS-SUMMARY;
              }
            }
            leaf table-id {
              type xr:Cisco-ios-xr-string;
              description "Table Id";
            }
          }
        }

        container rib-client-stats-nexthops {
          description "Statistics of table of a specific client";

          list rib-client-stats-nexthop {
            key "table-id";
            description "Specific Table";
            leaf table-id {
              type Table-id-range;
              description "Table Id";
            }
            uses RIB-EDM-STATS-NEXTHOP;
          }
        }

        container rib-client-proto {
          description "Information of protocols of client";

          container rib-client-proto-table-ids {
            description "Client Protocol table";

            list rib-client-proto-table-id {
              key "tableid";
              description
                "Table ID for a given protocol under a given
                client";

              container rib-client-proto-ids {
                description
                  "Protocols list under a given table under a
                  given client";

                list rib-client-proto-id {
                  key "protoid";
                  description
                    "Information of protocols under a given
                    table under a given client";
                  leaf protoid {
                    type uint32 {
                      range "0..96";
                    }
                    description "Proto ID";
                  }
                  uses RIB-EDM-CLIENT-PROTO;
                }
              }

              container rib-client-proto-table-info {
                description
                  "Information of a specifc table under a
                  given protocol under a given client";
                uses RIB-EDM-CLIENT-PROTO-TABLE-INFO;
              }
              leaf tableid {
                type xr:Cisco-ios-xr-string;
                description "Table Id";
              }
            }
          }

          container rib-client-proto-info {
            description
              "Information of protocols of a specific client";
            uses RIB-EDM-CLIENT-PROTO-INFO;
          }
        }

        container rib-client-redist-history-opaque {
          description
            "Opaque History information of the table
            associated with a given redist under a
            specific client";
          uses RIB-EDM-CLIENT-REDIST-OPAQUE;
        }

        container rib-client-stats-redist-nexthops {
          description "Statistics of nexthop table distribution";

          list rib-client-stats-redist-nexthop {
            key "table-id";
            description "Specific Table";
            leaf table-id {
              type Table-id-range;
              description "Table Id";
            }
            uses RIB-EDM-STATS-REDIST-NH;
          }
        }

        container rib-client-info {
          description "Information for a specific client";
          uses RIB-EDM-CLIENT;
        }

        container rib-client-redist-history {
          description
            "History information of the table associated
            with a given redist under a specific client";
          uses RIB-EDM-CLIENT-REDIST;
        }

        container rib-client-redists {
          description "RIB client redistribution";

          list rib-client-redist {
            key "table-id";
            description "Id of RIB client redistribution Table";

            container rib-client-redist-protos {
              description "Client proto";

              list rib-client-redist-proto {
                key "proto-id channel-id";
                description
                  "Protocols information for a specific client
                  . Client may have optional Channel
                  Identifier";
                leaf proto-id {
                  type uint32 {
                    range "0..96";
                  }
                  description "Proto ID";
                }
                leaf channel-id {
                  type uint32 {
                    range "0..4294967295";
                  }
                  description "Optional Channel ID, default 0";
                }
                uses RIB-EDM-CLIENT-REDIST-PROTO;
              }
            }

            container rib-client-redist-info {
              description
                "Information for a specific redistribution
                table under a given client";
              uses RIB-EDM-CLIENT-REDIST-TABLE;
            }
            leaf table-id {
              type xr:Cisco-ios-xr-string;
              description "Table Id";
            }
          }
        }

        container rib-client-stats-redists {
          description "Statistics of table distribution";

          list rib-client-stats-redist {
            key "table-id";
            description "Specific Table";

            container rib-client-stats-redist-protos {
              description "Protocol under a given table";

              list rib-client-stats-redist-proto {
                key "proto-id";
                description "Specific protocol";
                leaf proto-id {
                  type uint32 {
                    range "0..96";
                  }
                  description "Proto ID";
                }
                uses RIB-EDM-STATS-REDIST;
              }
            }
            leaf table-id {
              type Table-id-range;
              description "Table Id";
            }
          }
        }
        leaf clientid {
          type uint32 {
            range "0..2501";
          }
          description "Client ID";
        }
      }
    }
  }

  grouping NON-AS {
    description
      "Common node of local, srv6-local, iid-local,
      connected, rip, static, subscriber, mobile, dagr,
      application, te-client";

    container non-as {
      description "Non Autonomous System of protocol";
      uses PROTOCOL-ROUTE-TABLE;
      uses INFORMATION;
    }
  }

  grouping PROTOCOL-ROUTE-TABLE {
    description "Common node of as, non-as, smiap, l2vpn, lspv";

    container protocol-routes {
      description "Protocol specific Route";

      list protocol-route {
        key "network";
        description
          " Route information of a specific Network
          Address ";
        leaf network {
          type inet:ip-prefix;
          description "Network address and Length";
        }
        uses RIB-EDM-ROUTE;
      }
    }
  }

  grouping IID-TABLE {
    description "Common node of iid-mgr-active, iid-mgr-standby";

    container iids {
      description "Container class for all active IIDs";

      list iid {
        key "iid-prefix";
        description "Operational container for a given IID";

        container iid-info {
          description "Operational data for a given IID";
          uses IIDMGR-IID-INFO;
        }
        leaf iid-prefix {
          type inet:ipv6-address-no-zone;
          description "IID Value as IPv6 prefix";
        }
      }
    }
  }

  grouping RIB-UPDATE-GROUP-PRUNED-NODES {
    description
      "Common node of rib, rib-stdby, ipv6-rib,
      ipv6-rib-stdby";

    container rib-update-group-pruned-nodes {
      description "Information of updategroup pruned nodes";

      container rib-update-group-pruned-nodes-info {
        description "Information of updategroup pruned nodes";
        uses RIB-EDM-UG-PRUNED-NODES;
      }
    }
  }

  container ipv6-rib {
    config false;
    status "deprecated";
    description
      "This model is deprecated and is replaced by
      Cisco-IOS-XR-ip-rib-oper.yang which will provide
      the compatible functionalities.  RIB operational
      data";
    uses RIB-NH-ID-HISTORY-TABLE;
    uses RIB-UPDATE-GROUP-TABLE;
    uses RIBNHG-TABLE;
    uses RIB-UPDATE-GROUP-PRUNED-NODES;
    uses VRF-TABLE;
    uses RIB-TABLE;
    uses RIB-RPF-LIST-TABLE;
    uses RIB-NH-ID-SUMMARY-TABLE;
    uses RIB-STATS;
    uses RIB-MAX-DEPTH;
    uses RIB-CLIENT-TABLE;
    uses RIB-IID-MGR;
  }

  container rib-stdby {
    config false;
    status "deprecated";
    description
      "This model is deprecated and is replaced by
      Cisco-IOS-XR-ip-rib-oper.yang which will provide
      the compatible functionalities.  RIB standby node
      operational data";
    uses RIB-NH-ID-HISTORY-TABLE;
    uses RIB-UPDATE-GROUP-TABLE;
    uses RIB-UPDATE-GROUP-PRUNED-NODES;
    uses VRF-TABLE;
    uses RIB-TABLE;
    uses RIB-RPF-LIST-TABLE;
    uses RIB-NH-ID-SUMMARY-TABLE;
    uses RIB-STATS;
    uses RIB-MAX-DEPTH;
    uses RIB-CLIENT-TABLE;
  }

  container rib {
    config false;
    status "deprecated";
    description
      "This model is deprecated and is replaced by
      Cisco-IOS-XR-ip-rib-oper.yang which will provide
      the compatible functionalities.  RIB operational
      data";
    uses RIB-NH-ID-HISTORY-TABLE;
    uses RIB-UPDATE-GROUP-TABLE;
    uses RIB-UPDATE-GROUP-PRUNED-NODES;
    uses VRF-TABLE;
    uses RIB-TABLE;
    uses RIB-RPF-LIST-TABLE;
    uses RIB-NH-ID-SUMMARY-TABLE;
    uses RIB-STATS;
    uses RIB-MAX-DEPTH;
    uses RIB-CLIENT-TABLE;
  }

  container ipv6-rib-stdby {
    config false;
    status "deprecated";
    description
      "This model is deprecated and is replaced by
      Cisco-IOS-XR-ip-rib-oper.yang which will provide
      the compatible functionalities.  RIB standby node
      IPv6 operational data";
    uses RIB-NH-ID-HISTORY-TABLE;
    uses RIB-UPDATE-GROUP-TABLE;
    uses RIBNHG-TABLE;
    uses RIB-UPDATE-GROUP-PRUNED-NODES;
    uses VRF-TABLE;
    uses RIB-TABLE;
    uses RIB-RPF-LIST-TABLE;
    uses RIB-NH-ID-SUMMARY-TABLE;
    uses RIB-STATS;
    uses RIB-MAX-DEPTH;
    uses RIB-CLIENT-TABLE;
    uses RIB-IID-MGR;
  }
}
