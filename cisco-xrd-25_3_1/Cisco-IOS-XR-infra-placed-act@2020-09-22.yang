module Cisco-IOS-XR-infra-placed-act {

  namespace "http://cisco.com/ns/yang/Cisco-IOS-XR-infra-placed-act";

  prefix "placed-act";

  import cisco-semver { prefix "semver"; }

  import Cisco-IOS-XR-types { prefix "csc"; }

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR action package configuration.

     Copyright (c) 2018-2020 by Cisco Systems, Inc.
     All rights reserved.";

  revision "2020-09-22" {
    description
      "Added root access for placement-reoptimize.";
  }
  revision "2020-03-09" {
    description
      "Changed cli command.";
  }
  revision "2019-04-05" {
    description
      "Establish semantic version baseline.";
    semver:module-version "1.0.0";
  }

  revision "2018-01-10" {
    description
      "IOS XR 6.4.1 revision.";
  }

  rpc placement-reoptimize {
    csc:xr-task "cisco-support | root-lr";
    csc:cli-command "placement reoptimize force";
    description
      "Migrate the processes, if placement is not optimal.
      ";
  }

}
