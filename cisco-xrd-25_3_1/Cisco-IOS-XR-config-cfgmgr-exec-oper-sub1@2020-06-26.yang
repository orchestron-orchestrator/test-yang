submodule Cisco-IOS-XR-config-cfgmgr-exec-oper-sub1 {

  belongs-to Cisco-IOS-XR-config-cfgmgr-exec-oper {
    prefix Cisco-IOS-XR-config-cfgmgr-exec-oper;
  }

  /*** LINKAGE (IMPORTS / INCLUDES) ***/

  import cisco-semver { prefix "semver"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR config-cfgmgr-exec package operational data.

     Copyright (c) 2013-2020 by Cisco Systems, Inc.
     All rights reserved.";

  revision "2020-06-26" {
    description
      "Updated schema to restrict user-access based on taskgroup.";
    semver:module-version "1.0.1";
  }

  revision "2019-04-05" {
    description
      "Establish semantic version baseline.";
    semver:module-version "1.0.1";
  }

  revision "2017-09-07" {
    description
      "Fixed type translation error.";
  }

  revision "2015-11-09" {
    description
      "IOS XR 6.0 revision.";
  }

  typedef Hist-record {
    type enumeration {
      enum cfghist-bag-record-all {
        description "All history";
      }
      enum cfghist-bag-record-alarm {
        description "Alarm history";
      }
      enum cfghist-bag-record-cfs-check {
        description "CfgCheck history";
      }
      enum cfghist-bag-record-commit {
        description "Commit history";
      }
      enum cfghist-bag-record-oir {
        description "OIR history";
      }
      enum cfghist-bag-record-shutdown {
        description "Shutdown history";
      }
      enum cfghist-bag-record-startup {
        description "Bootup history";
      }
      enum cfghist-bag-record-backup {
        description "Backup history";
      }
      enum cfghist-bag-record-rebase {
        description "Rebase history";
      }
      enum cfghist-bag-record-last {
        description "Last history";
      }
    }
    description "Possible types of history";
  }

  grouping CFGSESSION-D-ENTRY {
    description "Per Session Detail Information";
    leaf session-id {
      type string;
      description "Session Id";
    }
    leaf client-name {
      type string;
      description "Client Name";
    }
    leaf user-id {
      type string;
      description "UserId";
    }
    leaf tty-name {
      type string;
      description "TtyName";
    }
    leaf timestamp {
      type string;
      description "Timestamp";
    }
    leaf lock-flag {
      type string;
      description "Lock Flag";
    }
    leaf trial-flag {
      type string;
      description "Trial Flag";
    }
    leaf pid {
      type uint32;
      description "PID";
    }
    leaf process-name {
      type string;
      description "Process Name";
    }
    leaf node-name {
      type string;
      description "Node Name";
    }
    leaf elapsed-time {
      type string;
      description "Elapsed Time";
    }
  }

  grouping HIST-BACKUP {
    description "HIST BACKUP";
    leaf comment {
      type string;
      description "Comment";
    }
  }

  grouping HIST-STARTUP {
    description "HIST STARTUP";
    leaf how-booted {
      type string;
      description "How Booted";
    }
    leaf boot-path {
      type string;
      description "Boot Path";
    }
  }

  grouping HIST-SHUTDOWN {
    description "HIST SHUTDOWN";
    leaf comment {
      type string;
      description "Comment";
    }
  }

  grouping HIST-OIR {
    description "HIST OIR";
    leaf config-type {
      type string;
      description "Config Type";
    }
    leaf operation {
      type string;
      description "Operation";
    }
    leaf config-name {
      type string;
      description "Config Name";
    }
  }

  grouping HIST-COMMIT {
    description "HIST COMMIT";
    leaf commit-id {
      type string;
      description "CommitId";
    }
    leaf user-id {
      type string;
      description "UserId";
    }
    leaf line {
      type string;
      description "Line";
    }
    leaf client-name {
      type string;
      description "Client name";
    }
    leaf label {
      type string;
      description "Label";
    }
    leaf comment {
      type string;
      description "Comment";
    }
  }

  grouping HIST-CFSCHECK {
    description "HIST CFSCHECK";
    leaf user-id {
      type string;
      description "UserId";
    }
    leaf line {
      type string;
      description "Line";
    }
  }

  grouping HIST-ALARM {
    description "HIST ALARM";
    leaf state {
      type string;
      description "State";
    }
    leaf where {
      type string;
      description "Where";
    }
  }

  grouping HIST-INFO {
    description "Configuration history record information";

    container alarm-info {
      when "../type = 'cfghist-bag-record-alarm'" {
        description "../type = 'CFGHIST_BAG_RECORD_ALARM'";
      }
      description "alarm info";
      uses HIST-ALARM;
    }

    container cfscheck-info {
      when "../type = 'cfghist-bag-record-cfs-check'" {
        description "../type = 'CFGHIST_BAG_RECORD_CFSCHECK'";
      }
      description "cfscheck info";
      uses HIST-CFSCHECK;
    }

    container commit-info {
      when "../type = 'cfghist-bag-record-commit'" {
        description "../type = 'CFGHIST_BAG_RECORD_COMMIT'";
      }
      description "commit info";
      uses HIST-COMMIT;
    }

    container oir-info {
      when "../type = 'cfghist-bag-record-oir'" {
        description "../type = 'CFGHIST_BAG_RECORD_OIR'";
      }
      description "oir info";
      uses HIST-OIR;
    }

    container shutdown-info {
      when "../type = 'cfghist-bag-record-shutdown'" {
        description "../type = 'CFGHIST_BAG_RECORD_SHUTDOWN'";
      }
      description "shutdown info";
      uses HIST-SHUTDOWN;
    }

    container startup-info {
      when "../type = 'cfghist-bag-record-startup'" {
        description "../type = 'CFGHIST_BAG_RECORD_STARTUP'";
      }
      description "startup info";
      uses HIST-STARTUP;
    }

    container backup-info {
      when "../type = 'cfghist-bag-record-backup'" {
        description "../type = 'CFGHIST_BAG_RECORD_BACKUP'";
      }
      description "backup info";
      uses HIST-BACKUP;
    }
    leaf type {
      type Hist-record;
      description "type";
    }
    leaf a {
      when "../type != 'cfghist-bag-record-alarm' and ../type !="+
        " 'cfghist-bag-record-cfs-check' and ../type !="+
        " 'cfghist-bag-record-commit' and ../type !="+
        " 'cfghist-bag-record-oir' and ../type !="+
        " 'cfghist-bag-record-shutdown' and ../type !="+
        " 'cfghist-bag-record-startup' and ../type !="+
        " 'cfghist-bag-record-backup'" {
          description
            "../type != 'CFGHIST_BAG_RECORD_ALARM' and .
            ./type != 'CFGHIST_BAG_RECORD_CFSCHECK' and .
            ./type != 'CFGHIST_BAG_RECORD_COMMIT' and .
            ./type != 'CFGHIST_BAG_RECORD_OIR' and ../type
            != 'CFGHIST_BAG_RECORD_SHUTDOWN' and ../type 
            != 'CFGHIST_BAG_RECORD_STARTUP' and ../type !=
            'CFGHIST_BAG_RECORD_BACKUP'";
      }
      type uint32;
      description "B";
    }
  }

  grouping CONFIGURATIONHISTORY-ENTRY {
    description "Per History Information";

    container info {
      description "Content of the history";
      uses HIST-INFO;
    }
    leaf timestamp {
      type string;
      description "Timestamp";
    }
  }

  grouping CFGCOMMITLIST-D-ENTRY {
    description "Per Commit Information";
    leaf timestamp {
      type string;
      description "Timestamp";
    }
    leaf commit-id {
      type string;
      description "CommitId";
    }
    leaf user-id {
      type string;
      description "UserId";
    }
    leaf line {
      type string;
      description "Line";
    }
    leaf client-name {
      type string;
      description "Client name";
    }
    leaf label {
      type string;
      description "Label";
    }
    leaf comment {
      type string;
      description "Comment";
    }
  }
}
