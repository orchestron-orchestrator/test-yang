module Cisco-IOS-XR-ipv4-ma-cfg {

  /*** NAMESPACE / PREFIX DEFINITION ***/

  namespace "http://cisco.com/ns/yang/Cisco-IOS-XR-ipv4-ma-cfg";


  prefix "ipv4-ma-cfg";

  /*** LINKAGE (IMPORTS / INCLUDES) ***/

  import Cisco-IOS-XR-types { prefix "xr"; }

  import cisco-semver { prefix "semver"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ipv4-ma package configuration.

     This module contains definitions
     for the following management objects:
       ipv4-network-global: IPv4 network global configuration data
       subscriber-pta: PTA Subscriber configuration

     Copyright (c) 2013-2024 by Cisco Systems, Inc.
     All rights reserved.";

  revision "2024-09-01" {
    description
      "Removed unsupported global IPv4 QPPB leaf nodes.
       2024-08-29
         Modified data type for IPv4 unnumbered mpls traffic-eng interface name
       2021-10-25
         Enabled DHCP client support on physical interface.";
    semver:module-version "2.0.0";
  }

  revision "2019-04-05" {
    description
      "Establish semantic version baseline.";
    semver:module-version "1.0.0";
  }

  revision "2015-07-30" {
    description
      "Descriptions updated.";
  }

  revision "2015-01-07" {
    description
      "IOS XR 5.3.1 revision.";
  }

  container ipv4-network-global {
    description "IPv4 network global configuration data";

    container unnumbered {
      description
        "Enable IPv4 processing without an explicit
        address";

      container mpls {
        description "Configure MPLS routing protocol parameters";

        container te {
          description "IPv4 commands for MPLS Traffic Engineering";
          leaf interface {
            type xr:Interface-name;
            description
              "Enable IP processing without an explicit
              address on MPLS Traffic-Eng";
          }
        }
      }
    }
    leaf source-route {
      type boolean;
      default "true";
      description
        "The flag for enabling whether to process packets
        with source routing header options";
    }
    leaf reassemble-max-packets {
      type uint32 {
        range "1..50";
      }
      units "percentage";
      description
        "Percentage of total packets available in the
        system";
    }
    leaf reassemble-time-out {
      type uint32 {
        range "1..120";
      }
      units "second";
      description
        "Number of seconds a reassembly queue will hold
        before timeout";
    }
  }

  container subscriber-pta {
    description "PTA Subscriber configuration";
    leaf tcp-mss-adjust {
      type uint32 {
        range "1280..1536";
      }
      units "byte";
      description "TCP MSS Adjust (bytes)";
    }
  }
}
