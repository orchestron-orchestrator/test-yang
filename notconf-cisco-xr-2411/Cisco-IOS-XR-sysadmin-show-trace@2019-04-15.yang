module Cisco-IOS-XR-sysadmin-show-trace {
  namespace "http://www.cisco.com/ns/yang/Cisco-IOS-XR-sysadmin-show-trace";
  prefix show_trace;

  import cisco-semver {
    prefix semver;
  }

  organization
    "Cisco Systems Inc.";
  contact
    "Cisco Systems, Inc.
     Customer Service

     Postal: 170 West Tasman Drive
     San Jose, CA 95134

     Tel: +1 800 553-NETS

     E-mail: cs-yang@cisco.com";
  description
    "This module contains a collection of YANG
     definitions for Cisco IOS-XR SysAdmin configuration.

     Copyright (c) 2012-2020 by Cisco Systems, Inc.
     All rights reserved.";

  revision 2019-04-15 {
    semver:module-version "1.0.0";
    description
      "Establish semantic version baseline.";
  }
  revision 2017-04-12 {
    description
      "Changed namespace and module name";
  }
  revision 2016-05-11 {
    description
      "Initial version.";
  }

  grouping traceable {
    list trace {
      key "buffer";
      config false;
      description
        "show traceable processes";
      leaf buffer {
        type string;
      }
      list location {
        key "location_name";
        leaf location_name {
          type string;
        }
        list all-options {
          key "option";
          leaf option {
            type string;
          }
          list trace-blocks {
            leaf data {
              type string;
              description
                "Trace output block";
            }
          }
        }
      }
    }
  }

  grouping traceable_process {
    list instance {
      key "process_name";
      config false;
      description
        "show traceable process instance names";
      leaf process_name {
        type string;
      }
      list trace {
        key "buffer";
        config false;
        description
          "show traceable processes";
        leaf buffer {
          type string;
        }
        list location {
          key "location_name";
          leaf location_name {
            type string;
          }
          list all-options {
            key "option";
            leaf option {
              type string;
            }
            list trace-blocks {
              leaf data {
                type string;
                description
                  "Trace output block";
              }
            }
          }
        }
      }
    }
  }

  grouping traceable_with_keypath_location {
    list trace {
      key "buffer";
      config false;
      leaf buffer {
        type string;
      }
      list all-options {
        key "option";
        leaf option {
          type string;
        }
        list trace-blocks {
          leaf data {
            type string;
          }
        }
      }
    }
  }
}
