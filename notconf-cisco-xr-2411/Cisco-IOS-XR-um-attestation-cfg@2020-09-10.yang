module Cisco-IOS-XR-um-attestation-cfg {
  namespace "http://cisco.com/ns/yang/Cisco-IOS-XR-um-attestation-cfg";
  prefix um-attestation-cfg;

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR attestation package configuration.

     This YANG module augments the
     modules with configuration data.

     Copyright (c) 2020, 2022 by Cisco Systems, Inc.
     All rights reserved.";

  revision 2020-09-10 {
    semver:module-version "1.0.0";
    description
      "Initial release";
  }

  container attestation {
    description
      "Attestation Agent configuration";
    container runtime-integrity {
      description
        "IMA related configuration";
      container cache {
        description
          "IMA cache related configuration";
        container job {
          description
            "Cache CRON job related configuration";
          leaf interval {
            type uint32 {
              range "5..1440" {
                description
                  "Time interval in minutes (must be multiple or factor of 60)";
              }
            }
            description
              "Time interval for the CRON job";
          }
          container disable {
            presence "Indicates a disable node is configured.";
            description
              "Disable the IMA Cache CRON job";
          }
        }
      }
    }
  }
}
