submodule Cisco-IOS-XR-ethernet-loopback-oper-sub1 {
  belongs-to Cisco-IOS-XR-ethernet-loopback-oper {
    prefix Cisco-IOS-XR-ethernet-loopback-oper;
  }

  import ietf-yang-types {
    prefix yang;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR ethernet-loopback package operational data.

     Copyright (c) 2013-2021 by Cisco Systems, Inc.
     All rights reserved.";

  revision 2021-04-27 {
    semver:module-version "1.1.0";
    description
      "Add COS filter support flag to active sessions";
  }
  revision 2019-04-05 {
    semver:module-version "1.0.0";
    description
      "Establish semantic version baseline.";
  }
  revision 2015-11-09 {
    description
      "IOS XR 6.0 revision.";
  }

  typedef Edpl-bag-status {
    type enumeration {
      enum "invalid" {
        value 958450333;
        description
          "Invalid loopback session status";
      }
      enum "starting" {
        value 958450334;
        description
          "Loopback starting";
      }
      enum "active" {
        value 958450335;
        description
          "Loopback active";
      }
      enum "stopping" {
        value 958450336;
        description
          "Loopback stopping";
      }
    }
    description
      "Loopback status";
  }

  typedef Edpl-bag-session {
    type enumeration {
      enum "local" {
        value 0;
        description
          "Local Session";
      }
      enum "latching" {
        value 1;
        description
          "Remote-initiated session";
      }
    }
    description
      "EDPL session type";
  }

  typedef Edpl-bag-direction {
    type enumeration {
      enum "invalid" {
        value 0;
        description
          "Invalid direction";
      }
      enum "external" {
        value 1;
        description
          "External direction";
      }
      enum "internal" {
        value 2;
        description
          "Internal direction";
      }
    }
    description
      "EDPL direction";
  }

  typedef Edpl-bag-remote-session-status {
    type enumeration {
      enum "inactive" {
        value 0;
        description
          "Inactive remote session";
      }
      enum "active" {
        value 1;
        description
          "Active remote session";
      }
    }
    description
      "Remote session status";
  }

  typedef Edpl-bag-vlan {
    type enumeration {
      enum "unspecified" {
        value 0;
        description
          "Unspecified VLAN type";
      }
      enum "dot1q" {
        value 1;
        description
          "Dot1Q VLAN type";
      }
      enum "dot1ad" {
        value 2;
        description
          "Dot1ad VLAN type";
      }
    }
    description
      "EDPL VLAN type";
  }

  typedef Mac-address {
    type yang:mac-address;
    description
      "MAC address type";
  }

  typedef Cfm-bag-ll {
    type enumeration {
      enum "activate" {
        value 0;
        description
          "Loopback activate request";
      }
      enum "deactivate" {
        value 1;
        description
          "Loopback deactivate request";
      }
      enum "state-request" {
        value 2;
        description
          "Loopback state request";
      }
      enum "activate-response" {
        value 3;
        description
          "Loopback activate response";
      }
      enum "deactivate-response" {
        value 4;
        description
          "Loopback deactivate response";
      }
      enum "state-response" {
        value 5;
        description
          "Loopback state response";
      }
    }
    description
      "Cfm bag ll";
  }

  typedef Edpl-bag-message-dir {
    type enumeration {
      enum "incoming" {
        value 0;
        description
          "Incoming message";
      }
      enum "outgoing" {
        value 1;
        description
          "Outgoing message";
      }
    }
    description
      "Edpl bag message dir";
  }

  grouping EDPL-BAG-VLAN-RANGE {
    description
      "EDPL VLAN range";
    leaf min {
      type uint16;
      description
        "Lowest value";
    }
    leaf max {
      type uint16;
      description
        "Highest value";
    }
  }

  grouping EDPL-BAG-VLAN-RANGE-ARRAY {
    description
      "EDPL VLAN range array structure";
    list vlan-range {
      max-elements 10;
      description
        "VLAN range";
      uses EDPL-BAG-VLAN-RANGE;
    }
  }

  grouping EDPL-BAG-SESSION {
    description
      "EDPL session details";
    container outer-vlan-range {
      description
        "Outer VLAN range";
      uses EDPL-BAG-VLAN-RANGE-ARRAY;
    }
    container inner-vlan-range {
      description
        "Inner VLAN range";
      uses EDPL-BAG-VLAN-RANGE-ARRAY;
    }
    leaf session-id {
      type uint32;
      description
        "Session ID";
    }
    leaf direction {
      type Edpl-bag-direction;
      description
        "Loopback direction";
    }
    leaf session-type {
      type Edpl-bag-session;
      description
        "Loopback session type";
    }
    leaf meg-level {
      type uint16;
      description
        "MEG level";
    }
    leaf status {
      type Edpl-bag-status;
      description
        "Loopback status";
    }
    leaf outer-vlan-type {
      type Edpl-bag-vlan;
      description
        "Outer VLAN type";
    }
    leaf source-mac-address {
      type Mac-address;
      description
        "Source MAC address";
    }
    leaf destination-mac-address {
      type Mac-address;
      description
        "Destination MAC address";
    }
    leaf ether-type {
      type uint16;
      description
        "Ether type";
    }
    leaf cos {
      type uint8;
      description
        "Class of Service";
    }
    leaf llc-oui {
      type uint32;
      description
        "LLC OUI";
    }
    leaf timeout {
      type uint32;
      description
        "Timeout period (s)";
    }
    leaf time-left {
      type uint32;
      description
        "Time left (s)";
    }
    leaf cos-filter-supported {
      type boolean;
      description
        "Is filtering by COS supported?";
    }
  }

  grouping EDPL-ACTIVE-BAG {
    description
      "Details of active loopback sessions for an
       interface";
    list session {
      description
        "Session information";
      uses EDPL-BAG-SESSION;
    }
  }

  grouping EDPL-PERMITTED-BAG {
    description
      "Details of whether EDPL is permitted on an
       interface";
    leaf external {
      type boolean;
      description
        "TRUE if external loopback is permitted";
    }
    leaf internal {
      type boolean;
      description
        "TRUE if internal loopback is permitted";
    }
    leaf external-latching {
      type boolean;
      description
        "TRUE if external latching-loopback is permitted";
    }
    leaf internal-latching {
      type boolean;
      description
        "TRUE if internal latching-loopback is permitted";
    }
    leaf log-changes {
      type boolean;
      description
        "TRUE if log-changes are to be recorded";
    }
    leaf latching-loopback-controller {
      type boolean;
      description
        "TRUE if the latching loopback ctrlr is enabled";
    }
  }

  grouping EDPL-MESSAGE-BAG {
    description
      "Contents of a single loopback message";
    leaf message-id {
      type uint32;
      description
        "The message ID";
    }
    leaf time {
      type uint32;
      description
        "Time the message was sent";
    }
    leaf direction {
      type Edpl-bag-message-dir;
      description
        "Was the message sent or received?";
    }
    leaf type {
      type Cfm-bag-ll;
      description
        "Loopback message type";
    }
    leaf interface {
      type string;
      description
        "Interface name";
    }
    leaf mac {
      type Mac-address;
      description
        "target/source mac for outgoing/incoming messages";
    }
    leaf mep {
      type uint16;
      description
        "target/source mep for outgoing/incoming messages";
    }
    leaf mep-specified {
      type boolean;
      description
        "MEP ID is specified";
    }
    leaf domain {
      type string;
      description
        "CFM domain on which the message was sent";
    }
    leaf service {
      type string;
      description
        "CFM service on which the message was sent";
    }
    leaf oam-level {
      type uint16;
      description
        "Indicates level of CFM domain";
    }
    leaf outer-type {
      type Edpl-bag-vlan;
      description
        "type of outer VLAN tag (dot1ad or dot1Q)";
    }
    leaf outer-vlanid {
      type uint16;
      description
        "Outer VLAN ID";
    }
    leaf outer-vlan-specified {
      type boolean;
      description
        "Outer VLAN ID specified";
    }
    leaf inner-vlanid {
      type uint16;
      description
        "Inner VLAN ID";
    }
    leaf inner-vlan-specified {
      type boolean;
      description
        "Inner VLAN ID specified";
    }
    leaf multicast {
      type boolean;
      description
        "Was the message sent multicast?";
    }
    leaf capabilities {
      type uint8;
      description
        "Flags specifying capabilities of sender";
    }
    leaf all-vlans {
      type boolean;
      description
        "Was all_vlans flag specified?";
    }
    leaf response-code {
      type uint8;
      description
        "Error code specified";
    }
    leaf status {
      type Edpl-bag-remote-session-status;
      description
        "Status of the loopback session";
    }
    leaf session-direction {
      type Edpl-bag-direction;
      description
        "Direction of the loopback session";
    }
    leaf timer {
      type uint32;
      units "second";
      description
        "Length of the expiration timer, in seconds";
    }
  }

  grouping EDPL-MESSAGES-BAG {
    description
      "Bag containing loopback messages";
    list message {
      description
        "Loopback messages information";
      uses EDPL-MESSAGE-BAG;
    }
  }
}
