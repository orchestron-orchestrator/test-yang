module Cisco-IOS-XR-gil-ea-oper {
  namespace "http://cisco.com/ns/yang/Cisco-IOS-XR-gil-ea-oper";
  prefix gil-ea-oper;

  import Cisco-IOS-XR-types {
    prefix xr;
  }
  import cisco-semver {
    prefix semver;
  }

  include Cisco-IOS-XR-gil-ea-oper-sub1 {
    revision-date 2023-03-09;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR gil-ea package operational data.

     This module contains definitions
     for the following management objects:
       generic-interface-list-ea: GenericInterfaceList Execution
         Agent Operational Table

     Copyright (c) 2013-2023 by Cisco Systems, Inc.
     All rights reserved.";

  revision 2023-03-09 {
    semver:module-version "1.0.0";
    description
      "Initial GIL EA Support";
  }
  revision 2019-04-05 {
    description
      "Establish semantic version baseline.";
  }
  revision 2015-11-09 {
    description
      "IOS XR 6.0 revision.";
  }

  container generic-interface-list-ea {
    config false;
    description
      "GenericInterfaceList Execution Agent Operational
       Table";
    container nodes {
      description
        "Table of GenericInterfaceList Execution Agent
         operational data for a particular node";
      list node {
        key "node-id";
        description
          "GenericInterfaceList Execution Agent
           operational data for a particular node";
        container generic-interfaces {
          description
            "Generic interface list table";
          list generic-interface {
            key "interface-name";
            description
              "GenericInterfaceList Execution Agent
               Interface Database";
            leaf interface-name {
              type xr:Interface-name;
              description
                "Interface Name";
            }
            uses GIL-EA-IDB;
          }
        }
        leaf node-id {
          type xr:Node-id;
          description
            "Location";
        }
      }
    }
  }
}
