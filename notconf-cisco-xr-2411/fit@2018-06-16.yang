module fit {
  namespace "http://cisco.com/panini/calvados/fit";
  prefix fit;

  import tailf-common {
    prefix tailf;
  }
  import Cisco-IOS-XR-sysadmin-types {
    prefix calvados;
  }

  organization
    "Cisco Systems, Inc.";
  contact
    "Cisco Systems, Inc.
     Customer Service

     Postal: 170 West Tasman Drive
     San Jose, CA 95134

     Tel: +1 800 553-NETS

     E-mail: cs-yang@cisco.com";
  description
    "This module contains definitions
     for the Calvados model objects.

     Copyright (c) 2012-2020 by Cisco Systems, Inc.
     All rights reserved.";

  revision 2018-06-16 {
    description
      "Remove the duplicate entry of container set";
  }
  revision 2012-05-20 {
    description
      "Initial revision";
  }

  grouping fit-cmd-end-grp {
    list location {
      tailf:action "go";
      key "fit-location-name";
      leaf fit-location-name {
        type calvados:location-id;
      }
    }
  }

  grouping fit-rate-grp {
    container rate {
      list error-number {
        key "num-errs";
        leaf num-errs {
          type uint32;
        }
        list duration {
          key "num-seconds";
          leaf num-seconds {
            type uint32;
          }
          uses fit-cmd-end-grp;
        }
      }
    }
  }

  grouping fit-thresh-grp {
    list threshold {
      key "num-seconds";
      leaf num-seconds {
        type uint32;
        mandatory true;
      }
      uses fit-cmd-end-grp;
    }
  }

  grouping fit-block-grp {
    container all {
      uses fit-thresh-grp;
      uses fit-cmd-end-grp;
    }
    list block-name-lst {
      key "block-name";
      leaf block-name {
        type string;
      }
      container one {
        uses fit-rate-grp;
        uses fit-cmd-end-grp;
      }
      container continuous {
        uses fit-rate-grp;
        uses fit-cmd-end-grp;
      }
      container stop {
        uses fit-cmd-end-grp;
      }
    }
  }

  grouping fit-module-grp {
    list module {
      key "module-name";
      leaf module-name {
        type string;
      }
      container fault-type {
        container ecc {
          uses fit-block-grp;
        }
        container parity {
          uses fit-block-grp;
        }
        container other {
          uses fit-block-grp;
        }
      }
    }
  }

  grouping fit-grp {
    list asic {
      key "asic-name";
      config false;
      leaf asic-name {
        type string;
      }
      list instance {
        key "instance-ids";
        leaf instance-ids {
          type uint32;
        }
        container fault-injection {
          uses fit-module-grp;
        }
      }
    }
  }
}
