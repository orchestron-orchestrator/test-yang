module Cisco-IOS-XR-sysadmin-zapdisk {
  namespace "http://www.cisco.com/ns/yang/Cisco-IOS-XR-sysadmin-zapdisk";
  prefix zapdisk;

  import cisco-semver {
    prefix semver;
  }

  organization
    "Cisco Systems Inc.";
  contact
    "Cisco Systems, Inc.
     Customer Service

     Postal: 170 West Tasman Drive
     San Jose, CA 95134

     Tel: +1 800 553-NETS

     E-mail: cs-yang@cisco.com";
  description
    "This module contains a collection of YANG
     definitions for Cisco IOS-XR Zapdisk module.

     This module zapdisk is for factory card reset feature.

     Copyright (c) 2016-2020 by Cisco Systems, Inc.
     All rights reserved.";

  revision 2019-04-15 {
    semver:module-version "1.0.0";
    description
      "Establish semantic version baseline.";
  }
  revision 2017-05-23 {
    description
      "Changed namespace and module name";
  }
  revision 2017-03-25 {
    description
      "zapdisk [set|unset] [location L] support";
  }

  rpc zapdisk {
    input {
      choice zapdisk-input {
        mandatory true;
        case target-set {
          leaf set {
            type empty;
            mandatory false;
          }
        }
        case target-unset {
          container czapdisk-unset {
            leaf unset {
              type empty;
              mandatory false;
            }
          }
        }
      }
    }
    output {
      leaf result {
        type string;
        mandatory true;
      }
    }
  }
}
