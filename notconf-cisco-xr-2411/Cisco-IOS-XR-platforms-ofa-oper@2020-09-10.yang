module Cisco-IOS-XR-platforms-ofa-oper {
  namespace "http://cisco.com/ns/yang/Cisco-IOS-XR-platforms-ofa-oper";
  prefix platforms-ofa-oper;

  import Cisco-IOS-XR-types {
    prefix xr;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR platforms-ofa package operational data.

     This module contains definitions
     for the following management objects:
       ofa: OFA Data

     Copyright (c) 2013-2020 by Cisco Systems, Inc.
     All rights reserved.";

  revision 2020-09-10 {
    semver:module-version "1.0.1";
    description
      "Added task-id";
  }
  revision 2020-06-25 {
    semver:module-version "1.0.1";
    description
      "Updated task-name";
  }
  revision 2019-12-14 {
    semver:module-version "1.0.1";
    description
      "Updated date for ofa yang path";
  }
  revision 2019-04-05 {
    semver:module-version "1.0.0";
    description
      "Establish semantic version baseline.";
  }
  revision 2015-11-09 {
    description
      "IOS XR 6.0 revision.";
  }

  container ofa {
    config false;
    description
      "OFA Data";
    container stats {
      description
        "OFA Stats Data";
      container nodes {
        description
          "OFA data for available nodes";
        list node {
          key "node-name";
          description
            "OFA operational data for a particular node";
          leaf node-name {
            type xr:Node-id;
            description
              "Node ID";
          }
        }
      }
    }
  }
}
