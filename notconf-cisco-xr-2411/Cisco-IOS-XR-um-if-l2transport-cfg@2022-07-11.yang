module Cisco-IOS-XR-um-if-l2transport-cfg {
  namespace "http://cisco.com/ns/yang/Cisco-IOS-XR-um-if-l2transport-cfg";
  prefix um-if-l2transport-cfg;

  import Cisco-IOS-XR-um-interface-cfg {
    prefix a1;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR if-l2transport package configuration.

     This YANG module augments the
     modules with configuration data.

     Copyright (c) 2019-2022 by Cisco Systems, Inc.
     All rights reserved.";

  revision 2022-07-11 {
    semver:module-version "1.1.0";
    description
      "Added missing description statement to nodes";
  }
  revision 2020-02-10 {
    semver:module-version "1.0.0";
    description
      "Initial draft";
  }

  grouping IF-BODY {
    description
      "Grouping for interface";
    container l2transport {
      presence "Indicates a l2transport node is configured.";
      description
        "Enable Layer 2 transport and enter its configuration submode";
    }
  }

  augment "/a1:interfaces/a1:interface" {
    description
      "This augment extends active nodes configuration";
    uses IF-BODY;
  }
  augment "/a1:interfaces/a1:interface-preconfigure" {
    description
      "This augment extends preconfigured nodes
       configuration";
    uses IF-BODY;
  }
}
