module Cisco-IOS-XR-ethernet-cfm-sat-cfg {
  namespace "http://cisco.com/ns/yang/Cisco-IOS-XR-ethernet-cfm-sat-cfg";
  prefix ethernet-cfm-sat-cfg;

  import cisco-semver {
    prefix semver;
  }
  import Cisco-IOS-XR-ethernet-cfm-datatypes {
    prefix dt1;
  }
  import Cisco-IOS-XR-ifmgr-cfg {
    prefix a1;
  }
  import Cisco-IOS-XR-icpe-infra-cfg {
    prefix a2;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ethernet-cfm-sat package configuration.

     This YANG module augments the
       Cisco-IOS-XR-ifmgr-cfg,
       Cisco-IOS-XR-icpe-infra-cfg
     modules with configuration data.

     Copyright (c) 2013-2019 by Cisco Systems, Inc.
     All rights reserved.";

  revision 2019-04-05 {
    semver:module-version "2.0.0";
    description
      "Establish semantic version baseline.";
  }
  revision 2015-11-09 {
    description
      "IOS XR 6.0 revision.";
  }

  augment "/a1:interface-configurations/a1:interface-configuration/a2:nv-satellite-fabric-link" {
    description
      "This augment extends the configuration data of
       'Cisco-IOS-XR-icpe-infra-cfg'";
    container ethernet-features {
      description
        "Ethernet Satellite configuration";
      container cfm {
        description
          "CFM Satellite configuration";
        leaf continuity-check-interval {
          type dt1:Cfm-ccm-interval;
          description
            "Continuity-Check Interval";
        }
        leaf level {
          type dt1:Cfm-level;
          description
            "Maintenance Domain Level";
        }
        leaf enable {
          type empty;
          description
            "Enable CFM on Satellite";
        }
      }
    }
  }
}
