module Cisco-IOS-XR-adt-oper {
  namespace "http://cisco.com/ns/yang/Cisco-IOS-XR-adt-oper";
  prefix adt-oper;

  import cisco-semver {
    prefix semver;
  }

  include Cisco-IOS-XR-adt-oper-sub2 {
    revision-date 2020-05-05;
  }
  include Cisco-IOS-XR-adt-oper-sub1 {
    revision-date 2020-05-05;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR adt package operational data.

     This module contains definitions
     for the following management objects:
       adt: ADT operational data

     Copyright (c) 2013-2020 by Cisco Systems, Inc.
     All rights reserved.";

  revision 2020-05-05 {
    semver:module-version "1.0.0";
    description
      "IOS XR 7.3.1 Initial version.";
  }
  revision 2019-04-05 {
    description
      "Establish semantic version baseline.";
  }
  revision 2015-11-09 {
    description
      "IOS XR 6.0 revision.";
  }

  container adt {
    config false;
    description
      "ADT operational data";
    container statistics {
      description
        "ADT statistics";
      uses ADT-STATISTICS;
    }
    container adt-output {
      description
        "Data associated with the event triggered from
         adt";
      uses ADT-EVENTS;
    }
    container subscription-info {
      description
        "ADT subscription details";
      uses ADT-SUBSCRIPTION-INFO;
    }
  }
}
