module Cisco-IOS-XR-um-session-redundancy-cfg {
  namespace "http://cisco.com/ns/yang/Cisco-IOS-XR-um-session-redundancy-cfg";
  prefix um-session-redundancy-cfg;

  import Cisco-IOS-XR-types {
    prefix xr;
  }
  import ietf-inet-types {
    prefix inet;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR session-redundancy package configuration.

     This YANG module augments the
     modules with configuration data.

     Copyright (c) 2021-2022 by Cisco Systems, Inc.
     All rights reserved.";

  revision 2021-06-29 {
    semver:module-version "1.0.0";
    description
      "Initial release";
  }

  container session-redundancy {
    presence "Indicates a session-redundancy node is configured.";
    description
      "Session Redundancy configuration";
    container disable {
      presence "Indicates a disable node is configured.";
      description
        "Disable Session Redundancy for all Groups";
    }
    container preferred-role {
      description
        "Preferred Role for all Groups";
      container primary {
        must "not(../subordinate)";
        presence "Indicates a primary node is configured.";
        description
          "Primary Role";
      }
      container subordinate {
        must "not(../primary)";
        presence "Indicates a subordinate node is configured.";
        description
          "Subordinate Role";
      }
    }
    leaf source-interface {
      type xr:Interface-name;
      description
        "Source Interface for Redundancy Peer Communication";
    }
    leaf hold-timer {
      type uint32 {
        range "1..65535" {
          description
            "Value of hold time in minutes";
        }
      }
      description
        "Hold Timer for all Groups";
    }
    leaf revertive-timer {
      type uint32 {
        range "1..65535" {
          description
            "Value of revertive time in minutes";
        }
      }
      must "../maximum";
      description
        "Revertive Timer for all groups";
    }
    leaf maximum {
      type uint32 {
        range "1..65535" {
          description
            "Value of MAX Revertive Timer";
        }
      }
      must "../revertive-timer";
      description
        "Max Revertive Timer for all group";
    }
    container groups {
      description
        "Redundancy Group configuration";
      list group {
        key "group-id";
        description
          "Redundancy Group configuration";
        leaf group-id {
          type uint32 {
            range "1..500" {
              description
                "Group ID";
            }
          }
          description
            "Redundancy Group configuration";
        }
        container interface-list {
          presence "Indicates a interface-list node is configured.";
          description
            "List of Interfaces for this Group";
          container interfaces {
            description
              "Interface for this Group";
            list interface {
              key "interface-name";
              description
                "Interface for this Group";
              leaf interface-name {
                type xr:Interface-name;
                description
                  "Interface for this Group";
              }
              leaf id {
                type uint32 {
                  range "1..65535" {
                    description
                      "ID for the interface to be mapped on to subordinate";
                  }
                }
                mandatory true;
                description
                  "Map Identifier";
              }
            }
          }
          container interface-sub-if-ranges {
            description
              "Interface with sub-interface range for this Group";
            list interface {
              must "sub-if-range";
              key "interface-name";
              description
                "Interface for this Group";
              leaf interface-name {
                type xr:Interface-name;
                description
                  "Interface for this Group";
              }
              list sub-if-range {
                key "start-range end-range";
                description
                  "Sub Interface Range";
                leaf start-range {
                  type uint32 {
                    range "0..2147483647" {
                      description
                        "Sub Interface Start Range";
                    }
                  }
                  description
                    "Sub Interface Range";
                }
                leaf end-range {
                  type uint32 {
                    range "0..2147483647" {
                      description
                        "Sub Interface End Range";
                    }
                  }
                  description
                    "Sub Interface End Range";
                }
                leaf id-range {
                  type uint32 {
                    range "1..65535" {
                      description
                        "Starting Map Identifier for the Sub Interface Range";
                    }
                  }
                  must "../end-id-range";
                  mandatory true;
                  description
                    "Identifier";
                }
                leaf end-id-range {
                  type uint32 {
                    range "1..65535" {
                      description
                        "Ending Map Identifier for the Sub Interface Range";
                    }
                  }
                  must "../id-range";
                  mandatory true;
                  description
                    "Ending Map Identifier for the Sub Interface Range";
                }
              }
            }
          }
        }
        container disable {
          presence "Indicates a disable node is configured.";
          description
            "Disable this Group";
        }
        container preferred-role {
          description
            "Preferred Role for this Group";
          container primary {
            must "not(../subordinate)";
            presence "Indicates a primary node is configured.";
            description
              "Primary Role";
          }
          container subordinate {
            must "not(../primary)";
            presence "Indicates a subordinate node is configured.";
            description
              "Subordinate Role";
          }
        }
        leaf peer {
          type inet:ip-address-no-zone;
          description
            "Peer config for this Group";
        }
        leaf hold-timer {
          type uint32 {
            range "1..65535" {
              description
                "Value of hold time in minutes";
            }
          }
          description
            "Hold Timer for this Group";
        }
        leaf description {
          type string {
            length "1..800" {
              description
                "Description for this Group";
            }
          }
          description
            "Description for this Group";
        }
        leaf core-tracking {
          type xr:Cisco-ios-xr-string {
            length "1..800" {
              description
                "Tracking Object Name";
            }
          }
          description
            "Core Tracking Object for this Group";
        }
        leaf access-tracking {
          type xr:Cisco-ios-xr-string {
            length "1..800" {
              description
                "Tracking Object Name";
            }
          }
          description
            "Access Tracking Object for this Group";
        }
        container tracking-disable {
          presence "Indicates a tracking-disable node is configured.";
          description
            "Disable Tracking Object for this Group";
        }
        leaf revertive-timer {
          type uint32 {
            range "1..65535" {
              description
                "Value of revertive time in minutes";
            }
          }
          must "../maximum";
          description
            "Revertive Timer for this group";
        }
        leaf maximum {
          type uint32 {
            range "1..65535" {
              description
                "Value of MAX Revertive Timer";
            }
          }
          must "../revertive-timer";
          description
            "Max Revertive Timer for this group";
        }
        container mode {
          description
            "Mode of operation for current group";
          container active-active {
            presence "Indicates a active-active node is configured.";
            description
              "Active-Active mode";
          }
        }
        container pool-list {
          presence "Indicates a pool-list node is configured.";
          description
            "List of Pool-names for this Group";
          list pool {
            key "pool-name";
            description
              "Address Pool Name";
            leaf pool-name {
              type xr:Cisco-ios-xr-string {
                length "1..800" {
                  description
                    "Pool name";
                }
              }
              description
                "Address Pool Name";
            }
          }
        }
      }
    }
  }
}
