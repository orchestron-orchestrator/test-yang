module Cisco-IOS-XR-config-valid-ccv-cfg {
  namespace "http://cisco.com/ns/yang/Cisco-IOS-XR-config-valid-ccv-cfg";
  prefix config-valid-ccv-cfg;

  import cisco-semver {
    prefix semver;
  }
  import Cisco-IOS-XR-infra-script-mgmt-cfg {
    prefix a1;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR config-valid-ccv package configuration.

     This module contains definitions
     for the following management objects:
       configurationvalidation: Configuration for the Configuration
         Validation feature

     This YANG module augments the
       Cisco-IOS-XR-infra-script-mgmt-cfg
     module with configuration data.

     Copyright (c) 2013-2021 by Cisco Systems, Inc.
     All rights reserved.";

  revision 2021-06-16 {
    semver:module-version "2.1.0";
    description
      "Deprecate nodes specific to commit check.";
  }
  revision 2020-07-06 {
    semver:module-version "2.0.0";
    description
      "Added Config Scripts support.";
  }
  revision 2019-04-05 {
    semver:module-version "1.0.0";
    description
      "Establish semantic version baseline.";
  }
  revision 2015-11-09 {
    description
      "IOS XR 6.0 revision.";
  }

  typedef Failure-action {
    type enumeration {
      enum "report" {
        value 1;
        description
          "Report this failure type";
      }
    }
    description
      "Failure action";
  }

  typedef Failure {
    type enumeration {
      enum "unsupported" {
        value 0;
        description
          "Unsupported failure type";
      }
    }
    description
      "Failure";
  }

  typedef Enable {
    type enumeration {
      enum "nonblocking" {
        value 1;
        description
          "Non-blocking enable type";
      }
      enum "blocking" {
        value 2;
        description
          "Blocking enable type";
      }
    }
    description
      "Enable";
  }

  typedef Checksum {
    type enumeration {
      enum "sha256" {
        value 0;
        description
          "SHA256";
      }
    }
    description
      "Checksum";
  }

  container configurationvalidation {
    description
      "Configuration for the Configuration Validation
       feature";
    container failure-type-actions {
      status deprecated;
      description
        "DEPRECATED: not to be used in new deployments";
      list failure-type-action {
        key "failure";
        description
          "Failure type action configuration";
        leaf action {
          type Failure-action;
          description
            "Action configuration for this failure type";
        }
        leaf failure {
          type Failure;
          description
            "Failure type";
        }
      }
    }
    leaf enable {
      type Enable;
      status deprecated;
      description
        "DEPRECATED: not to be used in new deployments.
         Incompatible with use of ScriptsEnable.";
    }
    leaf scripts-enable {
      type boolean;
      description
        "Enable configuration validation via scripts";
    }
  }

  augment "/a1:scripts" {
    description
      "This augment extends the configuration data of
       'Cisco-IOS-XR-infra-script-mgmt-cfg'";
    container config {
      description
        "Config script activation configuration";
      container scripts {
        description
          "Config script list";
        list script {
          key "name";
          description
            "Config script activation item";
          leaf name {
            type string;
            description
              "Script name";
          }
          leaf checksum-type {
            type Checksum;
            mandatory true;
            description
              "Checksum type";
          }
          leaf checksum {
            type string {
              length "64";
            }
            mandatory true;
            description
              "Checksum value";
          }
          leaf priority {
            type uint32;
            default "500";
            description
              "Script priority";
          }
        }
      }
    }
  }
}
