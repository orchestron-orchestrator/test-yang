submodule Cisco-IOS-XR-olc-oper-sub1 {
  belongs-to Cisco-IOS-XR-olc-oper {
    prefix Cisco-IOS-XR-olc-oper;
  }

  import ietf-inet-types {
    prefix inet;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR olc package operational data.

     Copyright (c) 2013-2023 by Cisco Systems, Inc.
     All rights reserved.";

  revision 2023-10-01 {
    semver:module-version "1.0.0";
    description
      "Otdr autoscan status and reason fields modification.";
  }
  revision 2023-08-21 {
    description
      "ALC status and baseline CLI addition";
  }
  revision 2023-05-24 {
    description
      "Otdr autoscan CLI addition";
  }
  revision 2023-04-18 {
    description
      "Link-status CLI addition";
  }
  revision 2022-12-20 {
    description
      "Comments added for all the fields in bag";
  }
  revision 2022-10-10 {
    description
      "raman tune status details CLI addition";
  }
  revision 2022-10-06 {
    description
      "Enhanced APC domain CLI for partial topology support";
  }
  revision 2022-06-30 {
    description
      "C+L band status CLI addition";
  }
  revision 2022-06-03 {
    description
      "L Band Path Loss information.";
  }
  revision 2022-04-18 {
    description
      "Link tuner bag modification include PSD index.";
  }
  revision 2021-12-07 {
    description
      "Link tuner CLI modification.";
  }
  revision 2021-03-26 {
    description
      "Span-loss CLI modification.";
  }
  revision 2021-01-19 {
    description
      "APC oper CLI addition.";
  }
  revision 2020-11-05 {
    description
      "Initial Revision.";
  }
  revision 2019-04-05 {
    description
      "Establish semantic version baseline.";
  }
  revision 2015-11-09 {
    description
      "IOS XR 6.0 revision.";
  }

  typedef Olc-otdr-raman-eval-enum {
    type enumeration {
      enum "olc-otdr-raman-eval-na" {
        value 0;
        description
          "Raman not evaluated";
      }
      enum "olc-otdr-raman-eval-go" {
        value 1;
        description
          "Raman evaluated result is GO";
      }
      enum "olc-otdr-raman-eval-nogo" {
        value 2;
        description
          "Raman evaluated result is NO GO";
      }
      enum "olc-otdr-raman-eval-forced" {
        value 3;
        description
          "Raman is Forced GO";
      }
    }
    description
      "Olc otdr raman eval enum";
  }

  typedef Olc-otdr-trigger-event {
    type enumeration {
      enum "olc-otdr-trigger-undef" {
        value 0;
        description
          "OTDR scan trigger in unknown";
      }
      enum "olc-otdr-trigger-manual" {
        value 1;
        description
          "OTDR scan trigger is manual";
      }
      enum "olc-otdr-trigger-span-up" {
        value 2;
        description
          "OTDR scan trigger is generated from Span Up";
      }
      enum "olc-otdr-trigger-span-down" {
        value 3;
        description
          "OTDR scan trigger is generated from Span Down";
      }
    }
    description
      "Olc otdr trigger event";
  }

  typedef Olc-otdr-link-status-enum {
    type enumeration {
      enum "olc-otdr-span-st-undef" {
        description
          "Span status undefined";
      }
      enum "olc-otdr-span-st-up" {
        description
          "Span is up";
      }
      enum "olc-otdr-span-st-down" {
        description
          "Span is down";
      }
    }
    description
      "Olc otdr link status enum";
  }

  typedef Apc-status {
    type enumeration {
      enum "disabled" {
        value 0;
        description
          "APC current state is Disabled";
      }
      enum "idle" {
        value 1;
        description
          "APC current state is Idle";
      }
      enum "blocked" {
        value 2;
        description
          "APC current state is Blocked";
      }
      enum "working" {
        value 3;
        description
          "APC current state is Working";
      }
      enum "enable" {
        value 4;
        description
          "APC current state is Enabled";
      }
      enum "paused" {
        value 5;
        description
          "APC current state is Paused";
      }
      enum "span-mode" {
        value 6;
        description
          "APC current state is Span-Mode";
      }
      enum "manual" {
        value 7;
        description
          "APC in Manual mode";
      }
    }
    description
      "Apc status";
  }

  typedef Apc-target-psd-source {
    type enumeration {
      enum "link-tuner" {
        value 0;
        description
          "Target PSD Source is Link Tuner";
      }
      enum "configuration" {
        value 1;
        description
          "Target PSD Source is Configuration";
      }
    }
    description
      "Apc target psd source";
  }

  typedef Apc-agent-mode {
    type enumeration {
      enum "apc-centralized-mode" {
        value 0;
        description
          "APC operating in Centralized mode";
      }
      enum "apc-span-mode" {
        value 1;
        description
          "APC operating in Span-mode";
      }
    }
    description
      "Apc agent mode";
  }

  typedef Apc-agent-source-port {
    type enumeration {
      enum "ase" {
        value 0;
        description
          "Source static noise loaded channel";
      }
      enum "och" {
        value 1;
        description
          "Source optical channel";
      }
      enum "na" {
        value 2;
        description
          "Source port information not applicable -
           applicable in span-mode APC";
      }
    }
    description
      "Apc agent source port";
  }

  typedef Apc-block-reason {
    type enumeration {
      enum "hw-fail" {
        value 1;
        description
          "Node reporting HW failure";
      }
      enum "edfa-shutdown" {
        value 2;
        description
          "EDFA is shutdown on node";
      }
      enum "apr-enabled" {
        value 4;
        description
          "APR is enabled on node";
      }
      enum "user-disabled" {
        value 8;
        description
          "APC disabled by user on node";
      }
      enum "edfa-apr" {
        value 16;
        description
          "EDFA is in APR on node";
      }
      enum "gain-estimation-in-progress" {
        value 32;
        description
          "Gain estimation in progress on node";
      }
      enum "band-failure" {
        value 64;
        description
          "Band Failure";
      }
      enum "partial-topology" {
        value 128;
        description
          "Partial topology";
      }
      enum "node-blocked" {
        value 256;
        description
          "Node blocked in the domain";
      }
      enum "prev-span-down" {
        value 512;
        description
          "Previous span neighbor is down";
      }
    }
    description
      "Apc block reason";
  }

  typedef Apc-internal-state {
    type enumeration {
      enum "blocked" {
        value 0;
        description
          "APC node is Blocked";
      }
      enum "idle" {
        value 1;
        description
          "APC node in Idle state";
      }
      enum "oor" {
        value 2;
        description
          "APC node in Out Of Range state";
      }
      enum "discrepancy" {
        value 3;
        description
          "APC node reporting Discrepancy ";
      }
      enum "correcting" {
        value 4;
        description
          "APC node in Correcting state";
      }
      enum "chan-startup" {
        value 5;
        description
          "APC node in starting up channel";
      }
      enum "paused" {
        value 6;
        description
          "APC node in Paused state (only applicable in
           span mode)";
      }
    }
    description
      "Apc internal state";
  }

  typedef Apc-agent-direction {
    type enumeration {
      enum "tx" {
        value 0;
        description
          "APC agent in TX direction";
      }
      enum "rx" {
        value 1;
        description
          "APC agent in RX direction";
      }
    }
    description
      "Apc agent direction";
  }

  typedef Olc-bs-status {
    type enumeration {
      enum "status-unknown" {
        value 0;
        description
          "BFR Agent Status is Unknown";
      }
      enum "status-running" {
        value 1;
        description
          "BFR Agent Status is Running";
      }
      enum "status-paused" {
        value 2;
        description
          "BFR Agent Status is Paused";
      }
      enum "status-initializing" {
        value 3;
        description
          "BFR Agent Status is Initializing";
      }
    }
    description
      "Olc bs status";
  }

  typedef Olc-bs-parter-band-conn-state {
    type enumeration {
      enum "conn-unknown" {
        value 0;
        description
          "Unknown partner band connection state";
      }
      enum "conn-up" {
        value 1;
        description
          "Partner band connection UP";
      }
      enum "conn-down" {
        value 2;
        description
          "Partner band connection DOWN";
      }
    }
    description
      "Olc bs parter band conn state";
  }

  typedef Olc-bs-psd {
    type enumeration {
      enum "unknown" {
        value 0;
        description
          "Unknown Configured PSD for Single Band";
      }
      enum "single-band" {
        value 1;
        description
          "Configured PSD for Single Band";
      }
      enum "dual-band" {
        value 2;
        description
          "Configured PSD for Dual Band";
      }
    }
    description
      "Olc bs psd";
  }

  typedef Olc-bs-band-status {
    type enumeration {
      enum "unknown" {
        value 0;
        description
          "Band in Unknown status";
      }
      enum "active" {
        value 1;
        description
          "Band in Active status";
      }
      enum "failed" {
        value 2;
        description
          "Band in Failed status";
      }
      enum "recovering" {
        value 3;
        description
          "Band in Recovering status";
      }
    }
    description
      "Olc bs band status";
  }

  typedef Olc-bs-band {
    type enumeration {
      enum "none" {
        value 0;
        description
          "None Band type defined";
      }
      enum "c-band" {
        value 1;
        description
          "C-Band type";
      }
      enum "l-band" {
        value 2;
        description
          "L-Band type";
      }
    }
    description
      "Olc bs band";
  }

  typedef Gain-estimator-status {
    type enumeration {
      enum "blocked" {
        value 0;
        description
          "Gain Estimator current state is Blocked";
      }
      enum "disabled" {
        value 1;
        description
          "Gain Estimator current state is Disabled";
      }
      enum "operational" {
        value 2;
        description
          "Gain Estimator current state is Operational";
      }
      enum "idle" {
        value 3;
        description
          "Gain Estimator current state is Idle";
      }
      enum "unknown" {
        value 4;
        description
          "Gain Estimator current state is Unknown";
      }
      enum "manual" {
        value 5;
        description
          "Gain Estimator current state in Manual";
      }
    }
    description
      "Gain estimator status";
  }

  typedef Link-tuner-status {
    type enumeration {
      enum "blocked" {
        value 0;
        description
          "Link Tuner current state is Blocked";
      }
      enum "disabled" {
        value 1;
        description
          "Link Tuner current state is Disabled";
      }
      enum "operational" {
        value 2;
        description
          "Link Tuner current state is Operational";
      }
      enum "unknown" {
        value 3;
        description
          "Link Tuner current state is Unknown";
      }
      enum "manual" {
        value 4;
        description
          "Link Tuner currnet state is Manual";
      }
    }
    description
      "Link tuner status";
  }

  typedef Olc-ls-status {
    type enumeration {
      enum "disabled" {
        value 0;
        description
          "Link Manager Status is Disabled";
      }
      enum "blocked" {
        value 1;
        description
          "Link Manager Status is Blocked (no PCE
           container available)";
      }
      enum "operational" {
        value 2;
        description
          "Link Manager Status is Operational (waiting for
           requests)";
      }
      enum "running" {
        value 3;
        description
          "Link Manager Status is Running (updating
           setpoint's)";
      }
    }
    description
      "Olc ls status";
  }

  typedef Raman-tuning-fail-reason {
    type enumeration {
      enum "measurement-failed" {
        value 0;
        description
          "Raman-Tuning has failed because of failure in
           measurement collection";
      }
      enum "calculation-failed" {
        value 1;
        description
          "Raman-Tuning has failed because of failure in
           calculation";
      }
      enum "optimization-failed" {
        value 2;
        description
          "Raman-Tuning has failed because of failure in
           optimization";
      }
    }
    description
      "Raman tuning fail reason";
  }

  typedef Raman-tuning-block-reason {
    type enumeration {
      enum "fibre-cut-present" {
        value 0;
        description
          "Raman-Tuning is blocked due to fibre cut
           presence";
      }
      enum "peer-node-comm-down" {
        value 1;
        description
          "Raman-Tuning is blocked due to no communication
           with peer node";
      }
      enum "can-not-enable-raman-pumps" {
        value 2;
        description
          "Raman-Tuning is blocked because cannot enable
           Raman pumps";
      }
      enum "blocked-due-to-multi-cond-itions" {
        value 3;
        description
          "Raman-Tuning is blocked due to multiple
           conditions";
      }
    }
    description
      "Raman tuning block reason";
  }

  typedef Raman-tuning-status {
    type enumeration {
      enum "startup" {
        value 0;
        description
          "Raman-Tuning current state is in startup";
      }
      enum "disabled" {
        value 1;
        description
          "Raman-Tuning current state is Disabled";
      }
      enum "blocked" {
        value 2;
        description
          "Raman-Tuning current state is Blocked";
      }
      enum "failed" {
        value 3;
        description
          "Raman-Tuning current state is Failed";
      }
      enum "measurement-in-prog" {
        value 4;
        description
          "Raman-Tuning current state is measurement in
           progress";
      }
      enum "calculation-in-prog" {
        value 5;
        description
          "Raman-Tuning current state is calculation in
           progress";
      }
      enum "optimization-in-prog" {
        value 6;
        description
          "Raman-Tuning current state is optimization in
           progress";
      }
      enum "tuned" {
        value 7;
        description
          "Raman-Tuning current state is Tuned";
      }
    }
    description
      "Raman tuning status";
  }

  typedef Olc-alc-agt-state {
    type enumeration {
      enum "idle" {
        value 1;
        description
          "ALC Local node Status is Operational (waiting
           for requests)";
      }
      enum "in-progress" {
        value 2;
        description
          "ALC Local node Status is Running (updating
           setpoint's)";
      }
      enum "pre-check-failed" {
        value 3;
        description
          "ALC Status is Running (updating setpoint's)";
      }
      enum "failed" {
        value 4;
        description
          "ALC procedure failed on local node";
      }
      enum "complete" {
        value 5;
        description
          "ALC procedure completed on local node";
      }
      enum "blocked" {
        value 6;
        description
          "ALC procedure blocked on local node";
      }
      enum "ter-min-ated" {
        value 7;
        description
          "ALC procedure Terminated on local node";
      }
      enum "unreachable" {
        value 8;
        description
          "ALC procedure failed due to node being
           unreachable";
      }
    }
    description
      "Olc alc agt state";
  }

  typedef String1 {
    type string;
    description
      "String1";
  }

  typedef Olc-alc-fail-reason {
    type enumeration {
      enum "partial-topology" {
        value 1;
        description
          "ALC procedure failed due to partial OLT-OLT
           topology";
      }
      enum "change-in-topology" {
        value 2;
        description
          "ALC procedure failed due to change in topology
           during procedure";
      }
      enum "config-change" {
        value 3;
        description
          "ALC procedure failed dur to changed
           configuration during procedure";
      }
      enum "incorrect-config" {
        value 4;
        description
          "ALC procedure failed dur to
           incorrect/incompatible configuration";
      }
      enum "parallel-run" {
        value 5;
        description
          "ALC procedure failed due to an ongoing
           procedure on far-end-OLT";
      }
      enum "control-loop-blocked" {
        value 6;
        description
          "ALC procedure failed due to one-or-more control
           loops blocked";
      }
      enum "control-loop-failed" {
        value 7;
        description
          "ALC procedure failed due to one-or-more control
           loop failed";
      }
      enum "failed-regulation" {
        value 8;
        description
          "ALC procedure failed regulation";
      }
    }
    description
      "Olc alc fail reason";
  }

  typedef Olc-alc-status {
    type enumeration {
      enum "idle" {
        value 1;
        description
          "ALC in Idle state";
      }
      enum "in-progress" {
        value 2;
        description
          "ALC procedure in progress";
      }
      enum "failed" {
        value 3;
        description
          "ALC procedure has failed";
      }
      enum "blocked" {
        value 4;
        description
          "ALC procedure is blocked";
      }
      enum "complete" {
        value 5;
        description
          "ALC procedure is complete";
      }
    }
    description
      "Olc alc status";
  }

  grouping OLC-LINK-TUNER-STATUS-DETAIL {
    description
      "OLC LINK TUNER STATUS DETAIL";
    container link-tuner-info {
      description
        "Link tuner summary information";
      uses OLC-LINK-TUNER-STATUS-SUMMARY;
    }
    leaf computed-total-noise {
      type string {
        length "0..16";
      }
      description
        "Total computed noise by Link Tuner (dB)";
    }
    leaf-list block-descr {
      type String1;
      description
        "Blocked reason description";
    }
  }

  grouping OLC-OTDR-EVENT-LIST-BAG {
    description
      "OLC OTDR EVENT LIST BAG";
    leaf event-number {
      type uint32;
      description
        "Event Number";
    }
    leaf detected-event {
      type uint32;
      description
        "Event Detected [Non-Reflective | Reflective |
         Fiber-End | Excess-Reflection]";
    }
    leaf location {
      type int64;
      description
        "Location (in unit of 0.01m)";
    }
    leaf accuracy {
      type int64;
      description
        "Accuracy (in unit of 0.01m)";
    }
    leaf magnitude {
      type int64;
      description
        "Magnitude (in unit of 0.01db)";
    }
    leaf magnitude-max {
      type int64;
      description
        "Max Acceptable Magnitude (in unit of 0.01db)";
    }
    leaf min-relaxation-factor {
      type uint32;
      units "percentage";
      description
        "Min Acceptable Relaxation factor (in percentage)";
    }
    leaf go-value {
      type uint32;
      description
        "Go Condition";
    }
  }

  grouping OLC-OTDR-PREVIOUS-STATUS {
    description
      "OLC OTDR PREVIOUS STATUS";
    leaf trigger-event {
      type Olc-otdr-trigger-event;
      description
        "Previous OTDR scan start trigger event";
    }
    leaf-list otdr-start-timestamp {
      type String1;
      description
        "Timestamp of OTDR scan start ";
    }
    leaf-list otdr-end-timestamp {
      type String1;
      description
        "Timestamp of OTDR scan end ";
    }
    leaf-list go-nogo-eval {
      type Olc-otdr-raman-eval-enum;
      description
        "Previous Evaluation of raman turn up algorithm";
    }
  }

  grouping OLC-OTDR-STATUS {
    description
      "OLC OTDR STATUS";
    leaf optical-link-status {
      type Olc-otdr-link-status-enum;
      description
        "Status of span analyzed by OTDR (span up/down)";
    }
    leaf trigger-event {
      type Olc-otdr-trigger-event;
      description
        "Type of event that started current OTDR scan";
    }
    leaf critical-distance {
      type int64;
      description
        "Critical Distance Location (in unit of 0.01m)";
    }
    leaf relaxation-factor {
      type int32;
      units "percentage";
      description
        "Relaxation Factor (in percentage)";
    }
    leaf-list otdr-start-timestamp {
      type String1;
      description
        "Timestamp of OTDR scan start ";
    }
    leaf-list otdr-end-timestamp {
      type String1;
      description
        "Timestamp of OTDR scan end ";
    }
    leaf-list status {
      type String1;
      description
        "OTDR Controller Status";
    }
    leaf-list reason {
      type String1;
      description
        "Reason description for current OTDR
         (Started/Completed)";
    }
    leaf-list go-nogo-eval {
      type Olc-otdr-raman-eval-enum;
      description
        "Result of raman turn up evaluation algorithm";
    }
    list last-otdr-status {
      description
        "Previous otdr state";
      uses OLC-OTDR-PREVIOUS-STATUS;
    }
    list event {
      description
        "Variable List of detected OTDR events ";
      uses OLC-OTDR-EVENT-LIST-BAG;
    }
  }

  grouping OLC-CONTROLLER-PARTNERBAND {
    description
      "OLC CONTROLLER PARTNERBAND";
    leaf partner-controller {
      type string {
        length "0..80";
      }
      description
        "Partner Controller name (OTS)";
    }
    leaf-list partner-ip {
      type inet:ipv4-address;
      description
        "Partner Controller IP address";
    }
    leaf-list cl-patch-loss {
      type String1;
      description
        "L-Band-Tx Patchcord Loss (dB)";
    }
    leaf-list cl-path-loss {
      type String1;
      description
        "L-Band-Tx Path Loss (dB)";
    }
    leaf-list cl-patch-loss-rx {
      type String1;
      description
        "L-Band-Rx Patchcord Loss (dB)";
    }
    leaf-list cl-path-loss-rx {
      type String1;
      description
        "L-Band-Rx Path Loss (dB)";
    }
    leaf-list ts-loss {
      type String1;
      description
        "Timestamp of Path and Patchord losses
         calculation";
    }
  }

  grouping OLC-APC-AGENT-STATUS {
    description
      "OLC APC AGENT STATUS";
    leaf tx-status {
      type Apc-status;
      description
        "TxStatus";
    }
    leaf-list rx-status {
      type Apc-status;
      description
        "rx status";
    }
  }

  grouping APC-NODE-STATUS-B {
    description
      "APC NODE STATUS B";
    leaf node-id {
      type inet:ipv4-address;
      description
        "RID of the agent node";
    }
    leaf-list internal-state {
      type Apc-internal-state;
      description
        "Internal status of the agent node";
    }
    leaf-list block-reason {
      type Apc-block-reason;
      description
        "Blocked reason of the agent node (if any)";
    }
  }

  grouping OLC-APC-STATUS {
    description
      "OLC APC STATUS";
    leaf status {
      type Apc-status;
      description
        "Current APC domain status";
    }
    leaf-list corr-node {
      type inet:ipv4-address;
      description
        "RID of current correcting node";
    }
    leaf-list block-reason {
      type Apc-block-reason;
      description
        "APC Blocked reason (if any)";
    }
    list node-status {
      description
        "Status of event node in the APC domain";
      uses APC-NODE-STATUS-B;
    }
  }

  grouping OLC-BASELINE-SPECTRUM-INFO {
    description
      "OLC BASELINE SPECTRUM INFO";
    leaf slice-count {
      type string {
        length "0..10";
      }
      description
        "Total number of slices in Spectrum";
    }
    leaf slice-spacing {
      type string {
        length "0..10";
      }
      description
        "Spacing between spectrum slices (in unit of GHz)";
    }
    leaf slice-start-wavelength {
      type string {
        length "0..10";
      }
      description
        "Wavelength of first slice (in unit of nm)";
    }
    leaf slice-start-freq {
      type string {
        length "0..10";
      }
      description
        "Frequency of first Slice Frequency (in unit of
         GHz)";
    }
    leaf slice-num {
      type uint32;
      description
        "spectrum slice number";
    }
    leaf-list rx-power {
      type String1;
      description
        "Received Power in dBm";
    }
    leaf-list tx-power {
      type String1;
      description
        "Transmit Power in dBm";
    }
  }

  grouping OLC-BASELINE-MEASUREMENTS-INFO {
    description
      "OLC BASELINE MEASUREMENTS INFO";
    container spectrum-info {
      description
        "Spectrum Info";
      uses OLC-BASELINE-SPECTRUM-INFO;
    }
    list cband-span-loss {
      description
        "C-Band Span Loss Info";
      uses OLC-C-BAND-SPAN-LOSS;
    }
  }

  grouping OLC-BASELINE-MEASUREMENTS-TXRX-INFO {
    description
      "OLC BASELINE MEASUREMENTS TXRX INFO";
    list measurements-tx {
      description
        "Measurements Info Tx";
      uses OLC-BASELINE-MEASUREMENTS-INFO;
    }
    list measurements-rx {
      description
        "Measurements Info Rx";
      uses OLC-BASELINE-MEASUREMENTS-INFO;
    }
  }

  grouping OLC-APC-AGENT-TARGET-PSD-SET-POINTS {
    description
      "target psd profile set_points information";
    leaf-list set-point {
      type uint32;
      description
        "Set Point in value between 1 to 33";
    }
    leaf-list target-psd {
      type String1;
      description
        "Target PSD in units of dBm/12 GHz";
    }
    leaf-list frequency {
      type String1;
      description
        "frequency in the units of THz";
    }
  }

  grouping OLC-APC-AGENT-TARGET-PSD-PROFILE {
    description
      "target psd profile information";
    leaf source {
      type Apc-target-psd-source;
      description
        "Target PSD Source as either Link Tuner or User
         Config";
    }
    list psd-info {
      description
        "Value of target psd, frequency, setpoint";
      uses OLC-APC-AGENT-TARGET-PSD-SET-POINTS;
    }
  }

  grouping APC-DISCRPANCY {
    description
      "APC DISCRPANCY";
    leaf cent-freq {
      type string {
        length "0..12";
      }
      description
        "Channel center frequency (THz)";
    }
    leaf width {
      type string {
        length "0..10";
      }
      description
        "Channel width (GHz)";
    }
    leaf channel-id {
      type string {
        length "0..5";
      }
      description
        "Channel ID";
    }
    leaf channel-source {
      type Apc-agent-source-port;
      description
        "Channel source (OCH/ASE/NA)";
    }
    leaf spectrum-slice-num {
      type uint32;
      description
        "Channel slice index";
    }
    leaf ampli-input-psd {
      type string {
        length "0..10";
      }
      description
        "Channel input PSD in units of 0.1 dBm/12.5 GHz";
    }
    leaf tgt-psd {
      type string {
        length "0..10";
      }
      description
        "Channel target PSD in units of 0.1 dBm/12.5 GHz";
    }
    leaf cur-psd {
      type string {
        length "0..10";
      }
      description
        "Channel current PSD in units of 0.1 dBm/12.5 GHz";
    }
    leaf chnl-slice-attn-cfg {
      type string {
        length "0..10";
      }
      description
        "Channel slice attenuation config (dB)";
    }
    leaf discrepancy {
      type string {
        length "0..10";
      }
      description
        "Channel discrepancy in units of 0.1 dBm";
    }
  }

  grouping APC-AMPLIFIER-STATUS {
    description
      "APC AMPLIFIER STATUS";
    leaf edfa-gain {
      type string {
        length "0..8";
      }
      description
        "Amplifier gain (dB)";
    }
    leaf edfa-out-pwr {
      type string {
        length "0..8";
      }
      description
        "Amplifier output power (dB)";
    }
    leaf edfa-tilt {
      type string {
        length "0..8";
      }
      description
        "Amplifier tilt (dB)";
    }
    leaf dge-attn-max {
      type string {
        length "0..8";
      }
      description
        "DGE/WSS attenuation (dB)";
    }
    leaf voa-attn {
      type string {
        length "0..8";
      }
      description
        "VOA attenuation (dB)";
    }
  }

  grouping APC-AMPLIFIER-CAPAB {
    description
      "APC AMPLIFIER CAPAB";
    leaf ampli-range-min {
      type string {
        length "0..8";
      }
      description
        "Minimum amplifier gain for given range mode (dB)";
    }
    leaf ampli-range-max {
      type string {
        length "0..8";
      }
      description
        "Maximum amplifier gain for given range mode (dB)";
    }
    leaf ampli-power-min {
      type string {
        length "0..8";
      }
      description
        "Minimum amplifier power for given range mode
         (dB)";
    }
    leaf ampli-power-max {
      type string {
        length "0..8";
      }
      description
        "Maximum amplifier power for given range mode
         (dB)";
    }
    leaf ampli-tilt-min {
      type string {
        length "0..8";
      }
      description
        "Minimum amplifier tilt for given range mode (dB)";
    }
    leaf ampli-tilt-max {
      type string {
        length "0..8";
      }
      description
        "Maximum amplifier tilt for given range mode (dB)";
    }
    leaf dge-attn-min {
      type string {
        length "0..8";
      }
      description
        "Minimum DGE/WSS attenuation (dB)";
    }
    leaf dge-attn-max {
      type string {
        length "0..8";
      }
      description
        "Maximum DGE/WSS attenuation (dB)";
    }
    leaf voa-attn-min {
      type string {
        length "0..8";
      }
      description
        "Minimum VOA attenuation (dB)";
    }
    leaf voa-attn-max {
      type string {
        length "0..8";
      }
      description
        "Maximum VOA attenuation (dB)";
    }
  }

  grouping OLC-APC-AGENT-REG-INFO {
    description
      "OLC APC AGENT REG INFO";
    container capab {
      description
        "Capability information";
      uses APC-AMPLIFIER-CAPAB;
    }
    container configuration {
      description
        "APC configured values";
      uses APC-AMPLIFIER-STATUS;
    }
    container operational-data {
      description
        "Operational data after regulation cycle";
      uses APC-AMPLIFIER-STATUS;
    }
    leaf controller {
      type string {
        length "0..80";
      }
      description
        "Controller name (OTS)";
    }
    leaf domain-apc-manager {
      type inet:ipv4-address;
      description
        "APC Domain manager Router ID";
    }
    leaf direction-xr {
      type Apc-agent-direction;
      description
        "Regulation info direction (TX/RX)";
    }
    leaf internal-state {
      type Apc-internal-state;
      description
        "APC agent internal state";
    }
    leaf psd-minimum {
      type string {
        length "0..8";
      }
      description
        "PSD minimum (dBm/12.5 GHz)";
    }
    leaf last-correction-timestamp {
      type string {
        length "0..40";
      }
      description
        "Timestamp for last correction by APC";
    }
    leaf gain-range {
      type string {
        length "0..10";
      }
      description
        "Gain range configured";
    }
    leaf-list block-reason {
      type Apc-block-reason;
      description
        "APC agent blocked reason";
    }
    leaf-list mode {
      type Apc-agent-mode;
      description
        "APC mode";
    }
    leaf-list last-span-loss-input {
      type String1;
      description
        "Last Span Loss input (dB)";
    }
    leaf-list last-span-loss-correction-timestamp {
      type String1;
      description
        "Timestamp for last span loss change correction
         by APC";
    }
    leaf-list residual-disc-prev-node {
      type String1;
      description
        "Residual discrepancy from  previous node (dB)";
    }
    leaf-list residual-discrepancy-timestamp {
      type String1;
      description
        "Timestamp when residual discrepancy was last
         received from the previous node (dB)";
    }
    leaf-list span-loss-correction-threshold {
      type String1;
      description
        "Span loss correction threshold (dB)";
    }
    leaf-list correction-tolerance {
      type String1;
      description
        "APC correction tolerance (dB)";
    }
    leaf-list domain-manager {
      type String1;
      description
        "APC domain manager RID (will be NA in span-mode)";
    }
    list channel-info {
      description
        "Every channel information with respect to
         regulation";
      uses APC-DISCRPANCY;
    }
  }

  grouping OLC-BASELINE-APC-REG-INFO {
    description
      "OLC BASELINE APC REG INFO";
    container reg-info {
      description
        "Regulation Info";
      uses OLC-APC-AGENT-REG-INFO;
    }
    leaf config-mode {
      type string {
        length "0..20";
      }
      description
        "Config mode Manual/Disabled/Centralized";
    }
    list psd-profile {
      description
        "PSD PRofile";
      uses OLC-APC-AGENT-TARGET-PSD-PROFILE;
    }
  }

  grouping OLC-BASELINE-APC-TXRX-INFO {
    description
      "OLC BASELINE APC TXRX INFO";
    list apc-regulation-tx {
      description
        "APC Regulation Info Tx";
      uses OLC-BASELINE-APC-REG-INFO;
    }
    list apc-regulation-rx {
      description
        "APC Regulation Info Rx";
      uses OLC-BASELINE-APC-REG-INFO;
    }
  }

  grouping OLC-LINK-TUNER-STATUS-SUMMARY {
    description
      "OLC LINK TUNER STATUS SUMMARY";
    leaf status {
      type Link-tuner-status;
      description
        "Link Tuner current status";
    }
    leaf last-psd-cmpt-time-stamp {
      type string {
        length "0..40";
      }
      description
        "Timestamp for last PSD computation by Link Tuner";
    }
    list psd-info {
      description
        "Single band PSD information of Link Tuner";
      uses OLC-LINK-TUNER-PSD-INFO;
    }
    list dual-band-psd-info {
      description
        "Dual band PSD information of Link Tuner";
      uses OLC-LINK-TUNER-PSD-INFO;
    }
  }

  grouping OLC-BASELINE-LINK-TUNER-INFO {
    description
      "OLC BASELINE LINK TUNER INFO";
    container link-tuner-status {
      description
        "Link Tuner Status info";
      uses OLC-LINK-TUNER-STATUS-SUMMARY;
    }
    leaf config-mode {
      type string {
        length "0..20";
      }
      description
        "Config mode Manual/Disabled";
    }
  }

  grouping OLC-C-BAND-SPAN-LOSS {
    description
      "OLC C BAND SPAN LOSS";
    leaf tx-controller {
      type string {
        length "0..80";
      }
      description
        "Controller name (OTS)";
    }
    leaf rx-controller {
      type string {
        length "0..80";
      }
      description
        "Controller name (OTS)";
    }
    leaf osc-tx-controller {
      type string {
        length "0..80";
      }
      description
        "Controller name (OTS)";
    }
    leaf osc-rx-controller {
      type string {
        length "0..80";
      }
      description
        "Controller name (OTS)";
    }
    leaf-list cband-apparent-sl {
      type String1;
      description
        "C-Band Apparent Span Loss in unit of 0.1 dB";
    }
    leaf-list ts-c-band-apparent-sl {
      type String1;
      description
        "Timestamp when C-Band Apparent Span Loss was
         measured";
    }
    leaf-list cband-total-rx-power {
      type String1;
      description
        "C-Band Total RX Power in unit of dBm";
    }
    leaf-list cband-total-tx-power {
      type String1;
      description
        "C-Band Total TX Power in unit of dBm";
    }
    leaf-list osc-total-rx-power {
      type String1;
      description
        "OSC Total RX Poweri in unit of dBm";
    }
    leaf-list osc-total-tx-power {
      type String1;
      description
        "OSC Total TX Power in unit of dBm";
    }
    leaf-list ts-total-power {
      type String1;
      description
        "Timestamp when Total Powers were measured";
    }
  }

  grouping OLC-CONTROLLER-SPAN-LOSS {
    description
      "OLC CONTROLLER SPAN LOSS";
    leaf-list neighbour-rid {
      type inet:ipv4-address;
      description
        "RID of the neighboring node";
    }
    leaf-list rx-span-loss {
      type String1;
      description
        "RX span loss (dB)";
    }
    leaf-list apparent-rx-span-loss {
      type String1;
      description
        "Apparent RX span loss (dB)";
    }
    leaf-list tx-span-loss {
      type String1;
      description
        "TX span loss (dB)";
    }
    leaf-list apparent-tx-span-loss {
      type String1;
      description
        "Apparent TX span loss (dB)";
    }
    leaf-list dfb-rx-span-loss-with-pumps-off {
      type String1;
      description
        "DFB RX span loss (dB)";
    }
    leaf-list ts-dfb-rx-span-loss-with-pumps-off {
      type String1;
      description
        "Timestamp for when DFB RX span loss was computed
         previously";
    }
    leaf-list dfb-tx-span-loss-with-pumps-off {
      type String1;
      description
        "DFB TX span loss (dB)";
    }
    leaf-list ts-dfb-tx-span-loss-with-pumps-off {
      type String1;
      description
        "Timestamp for when DFB TX span loss was computed
         previously";
    }
    leaf-list est-rx-span-loss {
      type String1;
      description
        "Estimated RX span loss (dB)";
    }
    leaf-list est-tx-span-loss {
      type String1;
      description
        "Estimated TX span loss (dB)";
    }
    leaf-list neighbour-intf-index {
      type uint32;
      description
        "Interface Index of neighboring node";
    }
    leaf-list signal-rx-span-loss {
      type String1;
      description
        "Signal RX span loss (dB)";
    }
    leaf-list apparent-signal-rx-span-loss {
      type String1;
      description
        "Apparent Signal RX span loss (dB)";
    }
    leaf-list signal-tx-span-loss {
      type String1;
      description
        "Signal TX span loss (dB)";
    }
    leaf-list apparent-signal-tx-span-loss {
      type String1;
      description
        "Apparent Signal TX span loss (dB)";
    }
    leaf-list osc-rx-span-loss {
      type String1;
      description
        "OSC RX span loss (dB)";
    }
    leaf-list apparent-osc-rx-span-loss {
      type String1;
      description
        "Apparent OSC RX span loss (dB)";
    }
    leaf-list osc-tx-span-loss {
      type String1;
      description
        "OSC TX span loss (dB)";
    }
    leaf-list apparent-osc-tx-span-loss {
      type String1;
      description
        "Apparent OSC TX span loss (dB)";
    }
  }

  grouping OLC-BASELINE-SPAN-LOSS-INFO {
    description
      "OLC BASELINE SPAN LOSS INFO";
    container controller-span-loss {
      description
        "Controller RX/TX Span Loss Info";
      uses OLC-CONTROLLER-SPAN-LOSS;
    }
    container cband-span-loss {
      description
        "C-Band Span Loss Info";
      uses OLC-C-BAND-SPAN-LOSS;
    }
  }

  grouping OLC-AMPLI-GAIN-ESTIMATOR-STATUS {
    description
      "OLC AMPLI GAIN ESTIMATOR STATUS";
    leaf status {
      type Gain-estimator-status;
      description
        "Gain estimator current status";
    }
    leaf computed-gain {
      type string {
        length "0..10";
      }
      description
        "Gain computed by gain estimator (dB)";
    }
    leaf computed-gain-mode {
      type string {
        length "0..10";
      }
      description
        "Gain mode configured by gain estimator
         (Normal/Extended)";
    }
    leaf-list last-gain-cmpt-time-stamp {
      type String1;
      description
        "Timestamp when that gain was computed by gain
         estimator the last time";
    }
    leaf-list block-descr {
      type String1;
      description
        "Blocked reason description";
    }
  }

  grouping OLC-GAIN-ESTIMATOR-STATUS {
    description
      "OLC GAIN ESTIMATOR STATUS";
    list egress-status {
      description
        "Gain estimator status in egress direction";
      uses OLC-AMPLI-GAIN-ESTIMATOR-STATUS;
    }
    list ingress-status {
      description
        "Gain estimator status in ingress direction";
      uses OLC-AMPLI-GAIN-ESTIMATOR-STATUS;
    }
  }

  grouping OLC-BASELINE-GAIN-ESTM-INFO {
    description
      "OLC BASELINE GAIN ESTM INFO";
    container gain-estm-info {
      description
        "Gain estimation details";
      uses OLC-GAIN-ESTIMATOR-STATUS;
    }
    leaf config-mode {
      type string {
        length "0..20";
      }
      description
        "Config mode Manual/Disabled";
    }
  }

  grouping OLC-BASELINE-OTDR-INFO {
    description
      "OLC BASELINE OTDR INFO";
    leaf-list otdr-sor-rx {
      type String1;
      description
        "OTDR SOR file Info Rx";
    }
    leaf-list otdr-sor-tx {
      type String1;
      description
        "OTDR SOR file Info Tx";
    }
  }

  grouping OLC-ALC-BASELINE-INFO {
    description
      "OLC ALC BASELINE INFO";
    container otdr {
      description
        "OTDR SOR file Info";
      uses OLC-BASELINE-OTDR-INFO;
    }
    container gain-estimator {
      description
        "Gain Estimation Info";
      uses OLC-BASELINE-GAIN-ESTM-INFO;
    }
    container span-loss {
      description
        "Span Loss Info";
      uses OLC-BASELINE-SPAN-LOSS-INFO;
    }
    container link-tuner {
      description
        "Link Tuner Info";
      uses OLC-BASELINE-LINK-TUNER-INFO;
    }
    container apc-regulation {
      description
        "APC Regulation Info Tx and Rx";
      uses OLC-BASELINE-APC-TXRX-INFO;
    }
    container measurements-info {
      description
        "Spectrum Info Tx and Rx";
      uses OLC-BASELINE-MEASUREMENTS-TXRX-INFO;
    }
  }

  grouping OLC-BS-BAND-INFO {
    description
      "OLC BS BAND INFO";
    leaf-list band-type {
      type Olc-bs-band;
      description
        "Band Type";
    }
    leaf-list band-status {
      type Olc-bs-band-status;
      description
        "Band status";
    }
    leaf-list psd-type {
      type Olc-bs-psd;
      description
        "Psd Type";
    }
  }

  grouping OLC-BS-BAND-NODE-INFO {
    description
      "OLC BS BAND NODE INFO";
    leaf partner-controller {
      type string {
        length "0..80";
      }
      description
        "Partner Controller name (OTS)";
    }
    leaf self-controller {
      type string {
        length "0..80";
      }
      description
        "Self Controller name (OTS)";
    }
    leaf-list node-rid {
      type inet:ipv4-address;
      description
        "OSPF RID IP address";
    }
    leaf-list partner-ip {
      type inet:ipv4-address;
      description
        "Partner Controller IP address";
    }
    leaf-list partner-band-conn-state {
      type Olc-bs-parter-band-conn-state;
      description
        "Partner band connection state";
    }
    leaf-list self-ip {
      type inet:ipv4-address;
      description
        "Self Controller IP address";
    }
    list band-info {
      max-elements 2;
      description
        "C and L Band Status Information";
      uses OLC-BS-BAND-INFO;
    }
  }

  grouping OLC-CONTROLLER-BAND-STATUS {
    description
      "Band Status information";
    leaf self-band {
      type Olc-bs-band;
      description
        "Local Band type";
    }
    leaf bfr-status {
      type Olc-bs-status;
      description
        "BFR Manager Status";
    }
    list band-node-info {
      description
        "Node's Bands Status list";
      uses OLC-BS-BAND-NODE-INFO;
    }
  }

  grouping OLC-LINK-TUNER-PSD-INFO {
    description
      "OLC LINK TUNER PSD INFO";
    leaf setpoint {
      type uint32;
      description
        "PSD setpoint (1-33)";
    }
    leaf computed-optimum-psd {
      type string {
        length "0..10";
      }
      description
        "Optimum PSD computed for given setpoint (dB)";
    }
  }

  grouping OLC-LS-NODE-PSD-INFO {
    description
      "OLC LS NODE PSD INFO";
    leaf psd-avg {
      type string {
        length "0..10";
      }
      description
        "Average PSD configured by Link Tuner (dBm)";
    }
    list psd-setpoint {
      description
        "PSD information of Link Tuner";
      uses OLC-LINK-TUNER-PSD-INFO;
    }
  }

  grouping OLC-LS-BAND-INFO {
    description
      "OLC LS BAND INFO";
    leaf managed-controller {
      type string {
        length "0..80";
      }
      description
        "Managed Controller name (OTS)";
    }
    leaf-list link-tuner-status {
      type Link-tuner-status;
      description
        "Link Tuner current status";
    }
    leaf-list gain-estimator-status {
      type Gain-estimator-status;
      description
        "Gain estimator current status";
    }
    leaf-list rx-ampli-gain-mode {
      type String1;
      description
        "Ingress Amplifier Gain mode configured by gain
         estimator (Normal/Extended)";
    }
    leaf-list rx-ampli-gain {
      type String1;
      description
        "Ingress Amplifier Gain value configured by gain
         estimator (dB)";
    }
    leaf-list tx-ampli-gain-mode {
      type String1;
      description
        "Egress Amplifier Gain mode configured by gain
         estimator (Normal/Extended)";
    }
    leaf-list tx-ampli-gain {
      type String1;
      description
        "Egress Amplifier Gain value configured by gain
         estimator (dB)";
    }
    leaf-list tx-ampli-output-power {
      type String1;
      description
        "Egress Amplifier output power set by Link-Tuner
         (dBm)";
    }
    list single-band-psd {
      description
        "Single Band PSD configured by Link Tuner (dBm)";
      uses OLC-LS-NODE-PSD-INFO;
    }
    list dual-band-psd {
      description
        "Dual Band PSD configured by Link Tuner (dBm)";
      uses OLC-LS-NODE-PSD-INFO;
    }
  }

  grouping OLC-LS-NODE-INFO {
    description
      "OLC LS NODE INFO";
    container cband {
      description
        "C Band GE and LT data";
      uses OLC-LS-BAND-INFO;
    }
    leaf-list node-rid {
      type inet:ipv4-address;
      description
        "OSPF RID IP address";
    }
    list lband {
      description
        "L Band GE and LT data";
      uses OLC-LS-BAND-INFO;
    }
  }

  grouping OLC-CONTROLLER-LINK-STATUS {
    description
      "Link Status information";
    leaf manager-status {
      type Olc-ls-status;
      description
        "Link Simulator global status";
    }
    leaf last-cmpt-time-stamp {
      type string {
        length "0..40";
      }
      description
        "Timestamp of last computation by Link Simulator";
    }
    leaf global-osnr {
      type string {
        length "0..10";
      }
      description
        "Global OSNR as computed by Link Tuner";
    }
    leaf global-osnr-std-dev {
      type string {
        length "0..10";
      }
      description
        "Global OSNR standard deviation as computed by
         Link Tuner";
    }
    leaf last-error {
      type string {
        length "0..150";
      }
      description
        "Last Error reported by Link Tuner";
    }
    list node-info {
      description
        "Node's Link Tuner and Gain Estimator Status list";
      uses OLC-LS-NODE-INFO;
    }
  }

  grouping RAMAN-TUNING-STATE-REASON {
    description
      "RAMAN TUNING STATE REASON";
    leaf-list block-reason {
      type Raman-tuning-block-reason;
      description
        "Block reason for Raman Tuning";
    }
    leaf-list fail-reason {
      type Raman-tuning-fail-reason;
      description
        "Failure reason for Raman Tuning";
    }
    leaf-list block-descr {
      type String1;
      description
        "Block reason description for Raman Tuning";
    }
    leaf-list last-fail-descr {
      type String1;
      description
        "Failure reason description for Raman Tuning";
    }
  }

  grouping OLC-RAMAN-STATUS {
    description
      "OLC RAMAN STATUS";
    leaf status {
      type Raman-tuning-status;
      description
        "Raman Tuning current status";
    }
    leaf-list tuning-complete-timestamp {
      type String1;
      description
        "Timestamp for the last Raman Tuning completion";
    }
    leaf-list target-gain {
      type String1;
      description
        "Target gain for Raman Tuning (dB)";
    }
    leaf-list max-gain {
      type String1;
      description
        "Maximum gain possible by Raman Tuning (dB)";
    }
    leaf-list tuning-complete-gain {
      type String1;
      description
        "Gain achieved at the completion of Raman Tuning
         (dB)";
    }
    leaf-list last-fail-timestamp {
      type String1;
      description
        "Timestamp for the last Raman Tuning failure";
    }
    leaf-list last-tuned-gain {
      type String1;
      description
        "Last tuned gain by Raman Tuning (dB)";
    }
    leaf-list last-tuned-timestamp {
      type String1;
      description
        "Timestamp for last tuning by Raman Tuning";
    }
    list reason {
      description
        "Reason description for current Raman Tuning
         status (Blocked/Failed)";
      uses RAMAN-TUNING-STATE-REASON;
    }
  }

  grouping OLC-ALC-FAILED-REASON-DETAIL {
    description
      "OLC ALC FAILED REASON DETAIL";
    leaf fail-reason {
      type string;
      description
        "Description of failure reason";
    }
    leaf fail-desc {
      type string;
      description
        "Detailed reason for the failure";
    }
  }

  grouping OLC-ALC-NODE-INFO {
    description
      "OLC ALC NODE INFO";
    leaf node-rid {
      type inet:ipv4-address;
      description
        "Remote NodeID of ALC agent";
    }
    leaf alc-state {
      type Olc-alc-agt-state;
      description
        "ALC agent state";
    }
    list failure-detail {
      description
        "ALC failed reason details if applicable";
      uses OLC-ALC-FAILED-REASON-DETAIL;
    }
  }

  grouping OLC-CONTROLLER-ALC-STATUS {
    description
      "OLC CONTROLLER ALC STATUS";
    leaf manager-status {
      type Olc-alc-status;
      description
        "Router ID corresponding to ALC manager";
    }
    leaf-list failure-detail {
      type Olc-alc-fail-reason;
      description
        "ALC procedure failure state if applicable";
    }
    leaf-list alc-start-timestamp {
      type String1;
      description
        "ALC procedure start time";
    }
    leaf-list alc-baseline-timestamp {
      type String1;
      description
        "ALC procedure baseline time";
    }
    list node-info {
      description
        "List of agent nodes with the current state";
      uses OLC-ALC-NODE-INFO;
    }
  }
}
