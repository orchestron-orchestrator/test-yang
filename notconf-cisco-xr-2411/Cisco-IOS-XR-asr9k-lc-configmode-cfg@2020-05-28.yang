module Cisco-IOS-XR-asr9k-lc-configmode-cfg {
  namespace "http://cisco.com/ns/yang/Cisco-IOS-XR-asr9k-lc-configmode-cfg";
  prefix asr9k-lc-configmode-cfg;

  import Cisco-IOS-XR-types {
    prefix xr;
  }
  import cisco-semver {
    prefix semver;
  }
  import Cisco-IOS-XR-config-mda-cfg {
    prefix a1;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR asr9k-lc-configmode package configuration.

     This YANG module augments the
       Cisco-IOS-XR-config-mda-cfg
     module with configuration data.

     Copyright (c) 2013-2020 by Cisco Systems, Inc.
     All rights reserved.";

  revision 2020-05-28 {
    semver:module-version "1.0.0";
    description
      "Added/modified to support port mode config through yang model.";
  }
  revision 2019-04-05 {
    description
      "Establish semantic version baseline.";
  }
  revision 2015-11-09 {
    description
      "IOS XR 6.0 revision.";
  }

  grouping HARDWARE-MODULE-CONFIG-MODE {
    description
      "Common node of active-node, preconfigured-node";
    container hardware-module-config-mode {
      description
        "HW module config-mode config";
      container slices {
        description
          "slice configuration";
        list slice {
          key "slice-number";
          description
            "Slice number";
          leaf if-config-mode {
            type string;
            description
              "Linecard interface config-mode";
          }
          leaf slice-number {
            type xr:Cisco-ios-xr-string;
            description
              "Slice number";
          }
        }
      }
    }
  }

  augment "/a1:preconfigured-nodes/a1:preconfigured-node" {
    description
      "This augment extends the configuration data of
       'Cisco-IOS-XR-config-mda-cfg'";
    uses HARDWARE-MODULE-CONFIG-MODE;
  }
  augment "/a1:active-nodes/a1:active-node" {
    description
      "This augment extends the configuration data of
       'Cisco-IOS-XR-config-mda-cfg'";
    uses HARDWARE-MODULE-CONFIG-MODE;
  }
}
