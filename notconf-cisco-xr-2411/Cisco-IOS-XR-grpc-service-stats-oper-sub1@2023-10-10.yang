submodule Cisco-IOS-XR-grpc-service-stats-oper-sub1 {
  belongs-to Cisco-IOS-XR-grpc-service-stats-oper {
    prefix Cisco-IOS-XR-grpc-service-stats-oper;
  }

  import ietf-inet-types {
    prefix inet;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR grpc-service-stats package operational data.

     Copyright (c) 2013-2023 by Cisco Systems, Inc.
     All rights reserved.";

  revision 2023-10-10 {
    semver:module-version "1.0.0";
    description
      "Added support for leaf set-union-replace-paths";
  }
  revision 2022-11-04 {
    description
      "Added support for SRTE gRPC stats";
  }
  revision 2022-09-26 {
    description
      "Added new service stats oper model";
  }
  revision 2019-04-05 {
    description
      "Establish semantic version baseline.";
  }
  revision 2015-11-09 {
    description
      "IOS XR 6.0 revision.";
  }

  typedef Service-rpc-type-enum {
    type enumeration {
      enum "gnmi-get" {
        description
          "GNMI Get stats";
      }
      enum "gnmi-set" {
        description
          "GNMI Set stats";
      }
      enum "gnmi-capability" {
        description
          "GNMI Capability stats";
      }
      enum "srte-add" {
        description
          "SRTE policy add stats";
      }
      enum "srte-delete" {
        description
          "SRTE policy delete stats";
      }
    }
    description
      "Service RPC types";
  }

  typedef Ems-in6-addr {
    type inet:ipv6-address;
    description
      "Ems in6 addr";
  }

  typedef Ip-type-enum {
    type enumeration {
      enum "ipv4" {
        description
          "IPV4";
      }
      enum "ipv6" {
        description
          "IPV6";
      }
    }
    description
      "IP types";
  }

  grouping SRTE-HEALTH-STATS {
    description
      "SRTE service stats";
    leaf enabled {
      type boolean;
      description
        "TRUE if service is enabled, FALSE otherwise";
    }
  }

  grouping GNMI-SET-STATS {
    description
      "gNMI set statistics information";
    leaf set-update-paths {
      type uint64;
      description
        "Number of update paths request in Set";
    }
    leaf set-delete-paths {
      type uint64;
      description
        "Number of delete paths request in Set";
    }
    leaf set-replace-paths {
      type uint64;
      description
        "Number of replace paths request in Set";
    }
    leaf set-union-replace-paths {
      type uint64;
      description
        "Number of union_replace paths request in Set";
    }
  }

  grouping GNMI-GET-STATS {
    description
      "gNMI get statistics information";
    leaf config-requests {
      type uint64;
      description
        "Number of config requests";
    }
    leaf operational-requests {
      type uint64;
      description
        "Number of opereational requests";
    }
    leaf state-requests {
      type uint64;
      description
        "Number of state requests";
    }
    leaf config-responses {
      type uint64;
      description
        "Number of config responses";
    }
    leaf operational-responses {
      type uint64;
      description
        "Number of opereational responses";
    }
    leaf state-responses {
      type uint64;
      description
        "Number of state responses";
    }
  }

  grouping HEALTH-STATS {
    description
      "HEALTH STATS";
    container gnmi-get-stats {
      when "../service-rpc-type = 'gnmi-get'" {
        description
          "../service_rpc_type = 'GNMIGet'";
      }
      description
        "gnmi get stats";
      uses GNMI-GET-STATS;
    }
    container gnmi-set-stats {
      when "../service-rpc-type = 'gnmi-set'" {
        description
          "../service_rpc_type = 'GNMISet'";
      }
      description
        "gnmi set stats";
      uses GNMI-SET-STATS;
    }
    container srte-add-stats {
      when "../service-rpc-type = 'srte-add'" {
        description
          "../service_rpc_type = 'SRTEAdd'";
      }
      description
        "srte add stats";
      uses SRTE-HEALTH-STATS;
    }
    container srte-delete-stats {
      when "../service-rpc-type = 'srte-delete'" {
        description
          "../service_rpc_type = 'SRTEDelete'";
      }
      description
        "srte delete stats";
      uses SRTE-HEALTH-STATS;
    }
    leaf service-rpc-type {
      type Service-rpc-type-enum;
      description
        "service rpc type";
    }
  }

  grouping USER-IP-ADDRESS {
    description
      "USER IP ADDRESS";
    leaf ip-type {
      type Ip-type-enum;
      description
        "ip type";
    }
    leaf ipv4-address {
      when "../ip-type = 'ipv4'" {
        description
          "../ip_type = 'IPV4'";
      }
      type inet:ipv4-address;
      description
        "IPv4 Address";
    }
    leaf ipv6-address {
      when "../ip-type = 'ipv6'" {
        description
          "../ip_type = 'IPV6'";
      }
      type Ems-in6-addr;
      description
        "IPv6 Address";
    }
  }

  grouping USER-INFO {
    description
      "User detail statistics information";
    container client-ip-address {
      description
        "Client IP Address";
      uses USER-IP-ADDRESS;
    }
    leaf username {
      type string;
      description
        "RPC for each service";
    }
    leaf port-number {
      type int32;
      description
        "Port number for client";
    }
    leaf authenticated {
      type boolean;
      description
        "User is authenticated";
    }
  }

  grouping AUDIT-STATS {
    description
      "Audit statistics information";
    list user-info {
      description
        "User list";
      uses USER-INFO;
    }
  }

  grouping COMMON-STATS {
    description
      "common statistics information";
    leaf requests {
      type uint64;
      description
        "Number of general requests";
    }
    leaf responses {
      type uint64;
      description
        "Number of responses";
    }
    leaf unauthenticated {
      type uint64;
      description
        "Number of status code unauthenticated";
    }
    leaf permission-denied {
      type uint64;
      description
        "Number of status code permission-denied";
    }
    leaf resource-exhausted {
      type uint64;
      description
        "Number of status code resource-exhausted";
    }
    leaf unavailable {
      type uint64;
      description
        "Number of status code unavailable";
    }
    leaf unimplemented {
      type uint64;
      description
        "Number of status code unimplemented";
    }
    leaf invalid-argument {
      type uint64;
      description
        "Number of status code invalid-argument";
    }
    leaf internal {
      type uint64;
      description
        "Number of status code internal";
    }
    leaf aborted {
      type uint64;
      description
        "Number of status code aborted";
    }
    leaf cancelled {
      type uint64;
      description
        "Number of status code cancelled";
    }
    leaf unknown {
      type uint64;
      description
        "Number of status code unknown";
    }
    leaf not-found {
      type uint64;
      description
        "Number of status code not found";
    }
    leaf already-exists {
      type uint64;
      description
        "Number of status code already exists";
    }
    leaf failed-precondition {
      type uint64;
      description
        "Number of status code falied precondition";
    }
    leaf data-loss {
      type uint64;
      description
        "Number of status code data loss";
    }
    leaf out-of-range {
      type uint64;
      description
        "Number of status code out of range";
    }
    leaf deadline-exceeded {
      type uint64;
      description
        "Number of status code deadline exceeded";
    }
  }

  grouping STATISTICS {
    description
      "Per RPC for Service information";
    container common-stats {
      description
        "Common Stats";
      uses COMMON-STATS;
    }
    container audit-stats {
      description
        "Audit Stats";
      uses AUDIT-STATS;
    }
    container health-stats {
      description
        "Health Stats";
      uses HEALTH-STATS;
    }
  }
}
