submodule Cisco-IOS-XR-8000-platforms-npu-memory-oper-sub1 {
  belongs-to Cisco-IOS-XR-8000-platforms-npu-memory-oper {
    prefix Cisco-IOS-XR-8000-platforms-npu-memory-oper;
  }

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR 8000-platforms-npu-memory package operational data.

     Copyright (c) 2013-2019 by Cisco Systems, Inc.
     All rights reserved.";

  revision 2019-04-05 {
    semver:module-version "1.0.0";
    description
      "Establish semantic version baseline.";
  }
  revision 2015-11-09 {
    description
      "IOS XR 6.0 revision.";
  }

  grouping OFA-SYSDB-PKT-MEMORY-USAGE {
    description
      "Per NPU structure for a pkt memory usage";
    leaf timestamp {
      type uint64;
      description
        "timestamp";
    }
    leaf device {
      type uint8;
      description
        "device";
    }
    leaf buff-int-usage {
      type uint32;
      description
        "buff int usage";
    }
    leaf buff-int-max-wm {
      type uint32;
      description
        "buff int max wm";
    }
    leaf buff-ext-usage {
      type uint32;
      description
        "buff ext usage";
    }
    leaf buff-ext-max-wm {
      type uint32;
      description
        "buff ext max wm";
    }
    leaf buff-int-free-min-wm {
      type uint64;
      description
        "buff int free min wm";
    }
    leaf buff-ext-free-min-wm {
      type uint64;
      description
        "buff ext free min wm";
    }
  }

  grouping OFA-SYSDB-PKT-MEMORY-USAGE-ARRAY-ST {
    description
      "Resource level information";
    list entry {
      description
        "entry";
      uses OFA-SYSDB-PKT-MEMORY-USAGE;
    }
  }

  grouping OFA-SYSDB-PKT-MEMORY-CONGESTION {
    description
      "Per NPU structure for a pkt memory congestion";
    leaf timestamp {
      type uint64;
      description
        "timestamp";
    }
    leaf event-type {
      type uint8;
      description
        "event type";
    }
    leaf device {
      type uint8;
      description
        "device";
    }
    leaf slice {
      type uint32;
      description
        "slice";
    }
    leaf voq {
      type uint32;
      description
        "voq";
    }
    leaf voq-buff-int-wm {
      type uint32;
      description
        "voq buff int wm";
    }
    leaf evicted-buff-int-wm {
      type uint32;
      description
        "evicted buff int wm";
    }
    leaf buff-int-uc-wm {
      type uint32;
      description
        "buff int uc wm";
    }
    leaf buff-int-usage {
      type uint32;
      description
        "buff int usage";
    }
    leaf buff-int-max-wm {
      type uint32;
      description
        "buff int max wm";
    }
    leaf buff-ext-usage {
      type uint32;
      description
        "buff ext usage";
    }
    leaf buff-ext-max-wm {
      type uint32;
      description
        "buff ext max wm";
    }
  }

  grouping OFA-SYSDB-PKT-MEMORY-CONGESTION-ARRAY-ST {
    description
      "Resource level information";
    list entry {
      description
        "entry";
      uses OFA-SYSDB-PKT-MEMORY-CONGESTION;
    }
  }
}
