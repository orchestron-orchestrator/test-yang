module Cisco-IOS-XR-um-mibs-ifmib-cfg {
  namespace "http://cisco.com/ns/yang/Cisco-IOS-XR-um-mibs-ifmib-cfg";
  prefix um-mibs-ifmib-cfg;

  import Cisco-IOS-XR-types {
    prefix xr;
  }
  import Cisco-IOS-XR-um-snmp-server-cfg {
    prefix a1;
  }
  import tailf-common {
    prefix tailf;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR mibs-ifmib package configuration.

     This YANG module augments the
     modules with configuration data.

     Copyright (c) 2021-2022 by Cisco Systems, Inc.
     All rights reserved.";

  revision 2022-07-11 {
    semver:module-version "1.0.0";
    description
      "Added missing description statement to nodes";
  }
  revision 2021-02-25 {
    semver:module-version "1.0.0";
    description
      "Initial release";
  }

  augment "/a1:snmp-server-mibs" {
    description
      "This augment extends snmp-server-mibs nodes
       configuration";
    container ifindex {
      description
        "Enable ifindex persistence";
      container persist {
        presence "Indicates a persist node is configured.";
        description
          "Persist interface indices";
      }
    }
    container interfaces {
      description
        "Enter the SNMP interface configuration commands";
      list interface {
        key "interface-name";
        description
          "Interface to configure";
        leaf interface-name {
          type xr:Interface-name;
          description
            "Interface to configure";
        }
        container notification {
          description
            "Allow an SNMP notification type";
          container linkupdown {
            description
              "SNMP linkUp and linkDown notifications";
            container enable {
              when "../../../interface-name[contains(text(),'.')] or ../../../interface-name[starts-with(text(),'Serial')] or ../../../interface-name[starts-with(text(),'ATM')] or ../../../interface-name[starts-with(text(),'IMA')]" {
                tailf:dependency "../../../interface-name";
              }
              presence "Indicates a enable node is configured.";
              description
                "Disable linkUp and linkDown notification";
            }
            container disable {
              when "../../../interface-name[not(contains(text(),'.'))] and ../../../interface-name[not(starts-with(text(),'Serial'))] and ../../../interface-name[not(starts-with(text(),'ATM'))] and ../../../interface-name[not(starts-with(text(),'IMA'))]" {
                tailf:dependency "../../../interface-name";
              }
              presence "Indicates a disable node is configured.";
              description
                "Disable linkUp and linkDown notification";
            }
          }
        }
        container index {
          description
            "Configure ifIndex attributes";
          container persistence {
            presence "Indicates a persistence node is configured.";
            description
              "Persistency across system reloads";
          }
        }
      }
      container subsets {
        description
          "Add configuration for an interface subset";
        list subset {
          must "notification/linkupdown";
          key "subset-number";
          description
            "Add configuration for an interface subset";
          leaf subset-number {
            type uint32 {
              range "1..255" {
                description
                  "The interface subset number";
              }
            }
            description
              "Add configuration for an interface subset";
          }
          leaf regular-expression {
            type xr:Cisco-ios-xr-string {
              length "1..130" {
                description
                  "Regular expression to match ifName";
              }
            }
            mandatory true;
            description
              "Interfaces matching regular expression";
          }
          container notification {
            description
              "Allow an SNMP notification type";
            container linkupdown {
              presence "Indicates a linkupdown node is configured.";
              description
                "SNMP linkUp and linkDown notifications";
              container disable {
                presence "Indicates a disable node is configured.";
                description
                  "Disable linkUp and linkDown notification";
              }
            }
          }
        }
      }
    }
    container trap {
      description
        "MIB trap configurations";
      container link {
        description
          "Link up/down trap configuration";
        container ietf {
          presence "Indicates a ietf node is configured.";
          description
            "Set the varbind of linkupdown trap to the RFC specified varbinds (default cisco)";
        }
      }
    }
    container ifmib {
      description
        "IF-MIB configuration commands";
      container ifalias {
        description
          "Modify parameters for ifAlias object";
        container long {
          presence "Indicates a long node is configured.";
          description
            "Enable support for ifAlias values longer than 64 characters";
        }
      }
      container stats {
        description
          "Modify IF-MIB statistics parameters";
        container cache {
          presence "Indicates a cache node is configured.";
          description
            "Get cached interface statistics";
        }
      }
      container ipsubscriber {
        presence "Indicates a ipsubscriber node is configured.";
        description
          "Enable ipsubscriber interfaces in IFMIB";
      }
      container internal {
        description
          "IFMIB internal lookahead cache";
        container cache {
          description
            "Cached data";
          leaf max-duration {
            type uint32 {
              range "0..60" {
                description
                  "Cache timeout";
              }
            }
            description
              "Change the max duration";
          }
        }
      }
    }
  }
}
