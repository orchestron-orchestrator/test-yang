module Cisco-IOS-XR-bundlemgr-oper {
  namespace "http://cisco.com/ns/yang/Cisco-IOS-XR-bundlemgr-oper";
  prefix bundlemgr-oper;

  import Cisco-IOS-XR-types {
    prefix xr;
  }
  import cisco-semver {
    prefix semver;
  }

  include Cisco-IOS-XR-bundlemgr-oper-sub2 {
    revision-date 2023-03-13;
  }
  include Cisco-IOS-XR-bundlemgr-oper-sub1 {
    revision-date 2023-03-13;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR bundlemgr package operational data.

     This module contains definitions
     for the following management objects:
       lacp-bundles: LACP bundle data
       bundle-information: Bundle information
       lacp-data: LACP data
       bundles: Bundle operational data
       lacp-bundle-members: LACP Bundle Member operational data
       bundles-adjacency: Bundle operational data from the adjacency
         processes

     Copyright (c) 2013-2023 by Cisco Systems, Inc.
     All rights reserved.";

  revision 2023-03-13 {
    semver:module-version "4.0.0";
    description
      "Updated member state reason to aggregable.
       2022-12-06
         Support added for new bundle state reason.
       2022-09-05
         Support added for new member state reason.
       2022-07-29
         Support added for forwarding-viable in member state reason.
       2022-02-16
         Support added for lacp timeout transitions and last lacp timeout leaves.";
  }
  revision 2020-10-01 {
    semver:module-version "3.0.0";
    description
      "64 bit bandwidth support";
  }
  revision 2019-05-30 {
    semver:module-version "2.0.0";
    description
      "64 bit bandwidth changes.";
  }
  revision 2019-04-05 {
    semver:module-version "1.0.0";
    description
      "Establish semantic version baseline.";
  }
  revision 2018-08-18 {
    description
      "Added a new leaf";
  }
  revision 2018-07-25 {
    description
      "Added a new leaf";
  }
  revision 2018-04-30 {
    description
      "Description updated.";
  }
  revision 2017-05-01 {
    description
      "Fixing backward compatibility error in module.";
  }
  revision 2016-02-22 {
    description
      "Description updated.";
  }
  revision 2015-11-09 {
    description
      "IOS XR 6.0 revision.";
  }

  container lacp-bundles {
    config false;
    description
      "LACP bundle data";
    container bundles {
      description
        "LACP bundle data";
      list bundle {
        key "bundle-interface";
        description
          "LACP Bundle interface";
        container data {
          description
            "Data for each Bundle";
          uses LACP-BUNDLE-DATA;
        }
        container members {
          description
            "LACP Member interface";
          list member {
            key "member-interface";
            description
              "Member information";
            leaf member-interface {
              type xr:Interface-name;
              description
                "Member interface";
            }
            uses BM-MEMBER-DATA;
          }
        }
        leaf bundle-interface {
          type xr:Interface-name;
          description
            "LACP Bundle interface";
        }
      }
    }
  }
  container bundle-information {
    config false;
    description
      "Bundle information";
    container bfd-counters {
      description
        "BFD counters information for bundles and members";
      container bfd-counters-bundles {
        description
          "Bundle interfaces with BFD counters information";
        list bfd-counters-bundle {
          key "bundle-interface";
          description
            "Bundle interface";
          container bfd-counters-bundle-descendant {
            description
              "Data for this item and all its members";
            uses BMD-BFD-COUNTER-BAG-MULTIPLE;
          }
          container bfd-counters-bundle-children-members {
            description
              "Children of bundle with BFD counters
               information";
            list bfd-counters-bundle-children-member {
              key "member-interface";
              description
                "Bundle member item with BFD counters
                 information";
              leaf member-interface {
                type string;
                description
                  "Member interface";
              }
              uses BMD-BFD-COUNTER-BAG;
            }
          }
          container bfd-counters-bundle-item {
            description
              "Data for this item";
            uses BM-NAME-BAG;
          }
          leaf bundle-interface {
            type xr:Interface-name;
            description
              "Bundle interface";
          }
        }
      }
      container bfd-counters-members {
        description
          "Member interfaces with BFD counters information";
        list bfd-counters-member {
          key "member-interface";
          description
            "Member interface";
          container bfd-counters-member-item {
            description
              "Data for this item";
            uses BMD-BFD-COUNTER-BAG;
          }
          leaf member-interface {
            type string;
            description
              "Member interface";
          }
        }
      }
    }
    container scheduled-actions {
      description
        "Scheduled actions on a bundle";
      container scheduled-actions-bundles {
        description
          "Bundles with actions scheduled";
        list scheduled-actions-bundle {
          key "bundle-interface";
          description
            "Bundle interface";
          container scheduled-actions-bundle-item {
            description
              "Data for this item";
            uses BMD-SCH-ACTION-BAG;
          }
          leaf bundle-interface {
            type xr:Interface-name;
            description
              "Bundle interface";
          }
        }
      }
    }
    container bundle {
      description
        "Generic information for bundles and members";
      container bundle-bundles {
        description
          "Bundle interfaces with common bundle
           information";
        list bundle-bundle {
          key "bundle-interface";
          description
            "Bundle interface";
          container bundle-bundle-descendant {
            description
              "Data for this item and all its members";
            uses BM-BUNDLE-COMBINED-DATA;
          }
          container bundle-bundle-children-members {
            description
              "Children of bundle with common bundle
               information";
            list bundle-bundle-children-member {
              key "member-interface";
              description
                "Bundle member item with common bundle
                 information";
              leaf member-interface {
                type string;
                description
                  "Member interface";
              }
              uses BM-MEMBER-DATA;
            }
          }
          container bundle-bundle-item {
            description
              "Data for this item";
            uses BM-BUNDLE-DATA;
          }
          leaf bundle-interface {
            type xr:Interface-name;
            description
              "Bundle interface";
          }
        }
      }
      container bundle-members {
        description
          "Member interfaces with common bundle
           information";
        list bundle-member {
          key "member-interface";
          description
            "Member interface";
          container bundle-member-ancestor {
            description
              "Data for this item and its parent bundle";
            uses BM-BUNDLE-COMBINED-DATA;
          }
          container bundle-member-item {
            description
              "Data for this item";
            uses BM-MEMBER-DATA;
          }
          leaf member-interface {
            type string;
            description
              "Member interface";
          }
        }
      }
    }
    container events-rg {
      description
        "Bundle ICCP events information for bundles and
         members";
      container events-rg-members {
        description
          "Bundle Member interfaces with ICCP events
           information";
        list events-rg-member {
          key "member-interface";
          description
            "Member interface";
          container events-rg-member-ancestor {
            description
              "Data for this item and its parent bundle";
            uses BMD-EVENT-BAG;
          }
          leaf member-interface {
            type string;
            description
              "Member interface";
          }
        }
      }
      container events-rg-iccp-groups {
        description
          "ICCP events for all ICCP Groups";
        list events-rg-iccp-group {
          key "iccp-group";
          description
            "ICCP Group ID";
          container events-rg-bundle-item-iccp-group {
            description
              "Data for this item";
            uses BMD-EVENT-BAG;
          }
          leaf iccp-group {
            type uint32 {
              range "1..4294967295";
            }
            description
              "ICCP Group ID";
          }
        }
      }
      container events-rg-bundles {
        description
          "Bundle interfaces with ICCP events information";
        list events-rg-bundle {
          key "bundle-interface";
          description
            "Bundle interface";
          container events-rg-bundle-ancestor {
            description
              "Data for this item and its parent bundle";
            uses BMD-EVENT-BAG;
          }
          leaf bundle-interface {
            type xr:Interface-name;
            description
              "Bundle interface";
          }
        }
      }
    }
    container lacp {
      description
        "LACP information for bundles and members";
      container lacp-bundles {
        description
          "Bundle interfaces with LACP information";
        list lacp-bundle {
          key "bundle-interface";
          description
            "Bundle interface";
          container lacp-bundle-item {
            description
              "Data for this item";
            uses LACP-BUNDLE-DATA;
          }
          container lacp-bundle-descendant {
            description
              "Data for this item and all its members";
            uses LACP-COMBINED-DATA;
          }
          container lacp-bundle-children-members {
            description
              "Children of bundle with LACP information";
            list lacp-bundle-children-member {
              key "member-interface";
              description
                "Bundle member item with LACP information";
              leaf member-interface {
                type string;
                description
                  "Member interface";
              }
              uses LACP-MBR-DATA;
            }
          }
          leaf bundle-interface {
            type xr:Interface-name;
            description
              "Bundle interface";
          }
        }
      }
      container lacp-members {
        description
          "Member interfaces with LACP information";
        list lacp-member {
          key "member-interface";
          description
            "Member interface";
          container lacp-member-ancestor {
            description
              "Data for this item and its parent bundle";
            uses LACP-COMBINED-DATA;
          }
          container lacp-member-item {
            description
              "Data for this item";
            uses LACP-MBR-DATA;
          }
          leaf member-interface {
            type string;
            description
              "Member interface";
          }
        }
      }
    }
    container mlacp-bundle-counters {
      description
        "Bundle specific counters of mLACP events";
      container iccp-groups {
        description
          "ICCP Groups with counters of their bundle's
           mLACP events";
        list iccp-group {
          key "iccp-group";
          description
            "ICCP Group ID";
          container iccp-group-item {
            description
              "Data for this item";
            uses BMD-BAG-BDL-INFO-MLACP-COUNTERS-RG;
          }
          leaf iccp-group {
            type uint32 {
              range "1..4294967295";
            }
            description
              "ICCP Group ID";
          }
        }
      }
      container bundles {
        description
          "Bundle interfaces with counters of mLACP events";
        list bundle {
          key "bundle-interface";
          description
            "Bundle interface";
          container bundle-item {
            description
              "Data for this item";
            uses BMD-BAG-BDL-INFO-MLACP-COUNTERS-RG-MULTIPLE;
          }
          leaf bundle-interface {
            type xr:Interface-name;
            description
              "Bundle interface";
          }
        }
      }
      container nodes {
        description
          "Devices with counters of their bundle's mLACP
           events";
        list node {
          key "node";
          description
            "Node ID";
          container node-item {
            description
              "Data for this item";
            uses BMD-BAG-BDL-INFO-MLACP-COUNTERS-RG;
          }
          leaf node {
            type string;
            description
              "For a local device the Node ID e.g.
               '0_0_CPU0', for a peer device the LDP ID
               followed by the ICCP Group ID e.g. '5.4.3.2
               ,4'";
          }
        }
      }
    }
    container protect {
      description
        "Information for bundles and members that are in
         the protect database";
      container protect-bundles {
        description
          "Bundle interfaces with information in the
           protect database";
        list protect-bundle {
          key "bundle-interface";
          description
            "Bundle interface";
          container protect-bundle-item {
            description
              "Data for this item";
            uses BMD-BAG-PROT-BDL-INFO;
          }
          leaf bundle-interface {
            type xr:Interface-name;
            description
              "Bundle interface";
          }
        }
      }
    }
    container mlacp-brief {
      description
        "mLACP Information for Interchassis Groups and
         bundles";
      container mlacp-bundle-briefs {
        description
          "Bundle interfaces with brief mLACP information";
        list mlacp-bundle-brief {
          key "bundle-interface";
          description
            "Bundle interface";
          container mlacp-bundle-item-brief {
            description
              "Data for this item";
            uses BMD-BAG-MLACP-DATA-MULTIPLE;
          }
          leaf bundle-interface {
            type xr:Interface-name;
            description
              "Bundle interface";
          }
        }
      }
      container mlacp-brief-iccp-groups {
        description
          "ICCP Groups with brief mLACP information";
        list mlacp-brief-iccp-group {
          key "iccp-group";
          description
            "ICCP Group ID";
          container mlacp-brief-iccp-group-item {
            description
              "Data for this item";
            uses BMD-BAG-MLACP-DATA;
          }
          leaf iccp-group {
            type uint32 {
              range "1..4294967295";
            }
            description
              "ICCP Group ID";
          }
        }
      }
    }
    container mlacp {
      description
        "mLACP Information for Interchassis Groups and
         bundles";
      container mlacp-bundles {
        description
          "Bundle interfaces with mLACP information";
        list mlacp-bundle {
          key "bundle-interface";
          description
            "Bundle interface";
          container mlacp-bundle-item {
            description
              "Data for this item";
            uses BMD-BAG-MLACP-DATA-MULTIPLE;
          }
          leaf bundle-interface {
            type xr:Interface-name;
            description
              "Bundle interface";
          }
        }
      }
      container mlacp-iccp-groups {
        description
          "ICCP Groups with mLACP information";
        list mlacp-iccp-group {
          key "iccp-group";
          description
            "ICCP Group ID";
          container mlacp-iccp-group-item {
            description
              "Data for this item";
            uses BMD-BAG-MLACP-DATA;
          }
          leaf iccp-group {
            type uint32 {
              range "1..4294967295";
            }
            description
              "ICCP Group ID";
          }
        }
      }
    }
    container mac-allocation {
      description
        "Information about allocated MAC addresses that
         are not in use";
      container mac-allocation-global {
        description
          "All MAC addresses that are allocated but
           currently not in use";
        container mac-allocation-global-item {
          description
            "Data for this item";
          uses BM-MAC-ALLOC;
        }
      }
    }
    container events {
      description
        "Events information for bundles and members";
      container events-members {
        description
          "Member interfaces with events information";
        list events-member {
          key "member-interface";
          description
            "Member interface";
          container events-member-item {
            description
              "Data for this item";
            uses BMD-EVENT-BAG;
          }
          container events-member-ancestor {
            description
              "Data for this item and its parent bundle";
            uses BMD-EVENT-BAG;
          }
          leaf member-interface {
            type string;
            description
              "Member interface";
          }
        }
      }
      container events-bundles {
        description
          "Bundle interfaces with events information";
        list events-bundle {
          key "bundle-interface";
          description
            "Bundle interface";
          container events-bundle-ancestor {
            description
              "Data for this item and its parent bundle";
            uses BMD-EVENT-BAG;
          }
          container events-bundle-item {
            description
              "Data for this item";
            uses BMD-EVENT-BAG;
          }
          container events-bundle-descendant {
            description
              "Data for this item and all its members";
            uses BMD-EVENT-BAG-MULTIPLE;
          }
          container events-bundle-children-members {
            description
              "Children of bundle with events information";
            list events-bundle-children-member {
              key "member-interface";
              description
                "Bundle member item with events information";
              leaf member-interface {
                type string;
                description
                  "Member interface";
              }
              uses BMD-EVENT-BAG;
            }
          }
          leaf bundle-interface {
            type xr:Interface-name;
            description
              "Bundle interface";
          }
        }
      }
    }
    container events-bdl {
      description
        "Bundle events information for bundles and
         members";
      container events-bdl-members {
        description
          "Member interfaces with bundle events
           information";
        list events-bdl-member {
          key "member-interface";
          description
            "Member interface";
          container events-bdl-member-ancestor {
            description
              "Data for this item and its parent bundle";
            uses BMD-EVENT-BAG;
          }
          leaf member-interface {
            type string;
            description
              "Member interface";
          }
        }
      }
      container events-bdl-bundles {
        description
          "Bundle interfaces with bundle events
           information";
        list events-bdl-bundle {
          key "bundle-interface";
          description
            "Bundle interface";
          container events-bdl-bundle-item {
            description
              "Data for this item";
            uses BMD-EVENT-BAG;
          }
          leaf bundle-interface {
            type xr:Interface-name;
            description
              "Bundle interface";
          }
        }
      }
      container events-bdl-iccp-groups {
        description
          "Bundle events for all ICCP Groups";
        list events-bdl-iccp-group {
          key "iccp-group";
          description
            "ICCP Group ID";
          container events-bdl-bundle-descendant-iccp-group {
            description
              "Data for this item and all its members";
            uses BMD-EVENT-BAG-MULTIPLE;
          }
          leaf iccp-group {
            type uint32 {
              range "1..4294967295";
            }
            description
              "ICCP Group ID";
          }
        }
      }
    }
    container bundle-briefs {
      description
        "Bundle interfaces with common bundle information";
      list bundle-brief {
        key "bundle-interface";
        description
          "Bundle interface";
        container bundle-brief-item {
          description
            "Data for this item";
          uses BM-BUNDLE-DATA;
        }
        leaf bundle-interface {
          type xr:Interface-name;
          description
            "Bundle interface";
        }
      }
    }
    container events-mbr {
      description
        "Bundle member events information for bundles and
         members";
      container events-mbr-bundles {
        description
          "Bundle interfaces with member events
           information";
        list events-mbr-bundle {
          key "bundle-interface";
          description
            "Bundle interface";
          container events-mbr-bundle-children-members {
            description
              "Children of bundle with member events
               information";
            list events-mbr-bundle-children-member {
              key "member-interface";
              description
                "Bundle member item with member events
                 information";
              leaf member-interface {
                type string;
                description
                  "Member interface";
              }
              uses BMD-EVENT-BAG;
            }
          }
          container events-mbr-bundle-descendant {
            description
              "Data for this item and all its members";
            uses BMD-EVENT-BAG-MULTIPLE;
          }
          leaf bundle-interface {
            type xr:Interface-name;
            description
              "Bundle interface";
          }
        }
      }
      container events-mbr-members {
        description
          "Member interfaces with bundle member events
           information";
        list events-mbr-member {
          key "member-interface";
          description
            "Member interface";
          container events-mbr-member-item {
            description
              "Data for this item";
            uses BMD-EVENT-BAG;
          }
          leaf member-interface {
            type string;
            description
              "Member interface";
          }
        }
      }
      container events-mbr-iccp-groups {
        description
          "Member events for all ICCP Groups";
        list events-mbr-iccp-group {
          key "iccp-group";
          description
            "ICCP Group ID";
          container events-mbr-bundle-children-member-iccp-groups {
            description
              "Children of bundle with member events
               information";
            list events-mbr-bundle-children-member-iccp-group {
              key "member-interface";
              description
                "Bundle member item with ICCP events
                 information";
              leaf member-interface {
                type string;
                description
                  "Member interface";
              }
              uses BMD-EVENT-BAG;
            }
          }
          container events-mbr-bundle-descendant-iccp-group {
            description
              "Data for this item and all its members";
            uses BMD-EVENT-BAG-MULTIPLE;
          }
          leaf iccp-group {
            type uint32 {
              range "1..4294967295";
            }
            description
              "ICCP Group ID";
          }
        }
      }
    }
    container mlacp-iccp-group-counters {
      description
        "ICCP Group specific counters of mLACP events";
      container iccp-groups {
        description
          "ICCP Groups with counters of mLACP events";
        list iccp-group {
          key "iccp-group";
          description
            "ICCP Group ID";
          container iccp-group-ancestor-bundle {
            description
              "Data for this item and its parent RG";
            uses BMD-BAG-RG-INFO-MLACP-COUNTERS-RG;
          }
          container iccp-group-ancestor-member {
            description
              "Data for this item and its parent RG";
            uses BMD-BAG-RG-INFO-MLACP-COUNTERS-RG;
          }
          container iccp-group-ancestor-node {
            description
              "Data for this item and its parent RG";
            uses BMD-BAG-RG-INFO-MLACP-COUNTERS-RG;
          }
          container iccp-group-item {
            description
              "Data for this item";
            uses BMD-BAG-RG-INFO-MLACP-COUNTERS-RG;
          }
          leaf iccp-group {
            type uint32 {
              range "1..4294967295";
            }
            description
              "ICCP Group ID";
          }
        }
      }
    }
    container system-id {
      description
        "System Identifiers for the local system and all
         ICCP Groups";
      container system-id-global {
        description
          "System Identifier for the local system";
        container system-id-global-item {
          description
            "Data for this item";
          uses LACP-SYSTEM-ID;
        }
      }
      container system-id-iccp-groups {
        description
          "System Identifiers for all ICCP Groups";
        list system-id-iccp-group {
          key "iccp-group";
          description
            "ICCP Group ID";
          container system-id-iccp-group-item {
            description
              "Data for this item";
            uses LACP-SYSTEM-ID;
          }
          leaf iccp-group {
            type uint32 {
              range "1..4294967295";
            }
            description
              "ICCP Group ID";
          }
        }
      }
    }
    container mlacp-member-counters {
      description
        "Member specific counters of mLACP events";
      container iccp-groups {
        description
          "ICCP Groups with counters of their member's
           mLACP events";
        list iccp-group {
          key "iccp-group";
          description
            "ICCP Group ID";
          container iccp-group-item {
            description
              "Data for this item and all its members";
            uses BMD-BAG-MBR-INFO-MLACP-COUNTERS-RG;
          }
          leaf iccp-group {
            type uint32 {
              range "1..4294967295";
            }
            description
              "ICCP Group ID";
          }
        }
      }
      container members {
        description
          "Member interfaces with counters of mLACP events";
        list member {
          key "member-interface";
          description
            "Member interface";
          container member-item {
            description
              "Data for this item";
            uses BMD-BAG-MBR-INFO-MLACP-COUNTERS-RG;
          }
          leaf member-interface {
            type string;
            description
              "Member interface";
          }
        }
      }
      container bundles {
        description
          "Bundle interfaces with counters of their
           member's mLACP events";
        list bundle {
          key "bundle-interface";
          description
            "Bundle interface";
          container bundle-item {
            description
              "Data for this item";
            uses BMD-BAG-MBR-INFO-MLACP-COUNTERS-BDL;
          }
          leaf bundle-interface {
            type xr:Interface-name;
            description
              "Bundle interface";
          }
        }
      }
      container nodes {
        description
          "Devices with counters of their member's mLACP
           events";
        list node {
          key "node";
          description
            "Node ID";
          container node-item {
            description
              "Data for this item";
            uses BMD-BAG-MBR-INFO-MLACP-COUNTERS-RG;
          }
          leaf node {
            type string;
            description
              "For a local device the Node ID e.g.
               '0_0_CPU0', for a peer device the LDP ID
               followed by the ICCP Group ID e.g. '5.4.3.2
               ,4'";
          }
        }
      }
    }
  }
  container lacp-data {
    config false;
    description
      "LACP data";
    container global {
      description
        "Global LACP data";
      container system-id {
        description
          "LACP System ID";
        uses LACP-SYSTEM-ID;
      }
    }
  }
  container bundles {
    config false;
    description
      "Bundle operational data";
    container bundles {
      description
        "Per bundle operational data";
      list bundle {
        key "bundle-interface";
        description
          "Bundle interface";
        container applied-lacp-mode {
          description
            "Applied LACP Mode for each Bundle";
          uses BM-BUNDLE-APPLIED-LACP-MODE;
        }
        container data {
          description
            "Data for each Bundle";
          uses BM-BUNDLE-DATA;
        }
        container members {
          description
            "Member interface";
          list member {
            key "member-interface";
            description
              "Member information";
            leaf member-interface {
              type xr:Interface-name;
              description
                "Member interface";
            }
            uses BM-MEMBER-DATA;
          }
        }
        leaf bundle-interface {
          type xr:Interface-name;
          description
            "Bundle interface";
        }
      }
    }
  }
  container lacp-bundle-members {
    config false;
    description
      "LACP Bundle Member operational data";
    container nodes {
      description
        "Table of devices with their LACP bundle member
         interfaces";
      list node {
        key "node";
        description
          "Node ID";
        container counters {
          description
            "Link counters for LACP bundle members per node";
          uses LACP-DROPS;
        }
        leaf node {
          type string;
          description
            "For a local device the Node ID e.g. '0_0_CPU0'
             , for a peer device the LDP ID followed by the
             ICCP Group ID e.g. '5.4.3.2,4'";
        }
      }
    }
    container members {
      description
        "Table of LACP bundle member interfaces";
      list member {
        key "member-interface";
        description
          "LACP bundle member interface data";
        container data {
          description
            "Link data for LACP bundle members";
          uses LACP-LINK-DATA;
        }
        container counters {
          description
            "Link counters for LACP bundle members";
          uses LACP-COUNTERS;
        }
        leaf member-interface {
          type xr:Interface-name;
          description
            "Member interface";
        }
      }
    }
  }
  container bundles-adjacency {
    config false;
    description
      "Bundle operational data from the adjacency
       processes";
    container nodes {
      description
        "Per bundle operational data";
      list node {
        key "node-name";
        description
          "Location";
        container brief {
          description
            "Brief load-balance information for the node";
          uses BMA-BRIEF-DATA;
        }
        container bundles {
          description
            "Per bundle operational data";
          list bundle {
            key "bundle-name";
            description
              "Bundle information";
            container bundle-info {
              description
                "Data for each Bundle";
              uses BMA-BUNDLE-DATA;
            }
            leaf bundle-name {
              type xr:Interface-name;
              description
                "Bundle interface";
            }
          }
        }
        leaf node-name {
          type xr:Node-id;
          description
            "Node ID";
        }
      }
    }
  }
}
