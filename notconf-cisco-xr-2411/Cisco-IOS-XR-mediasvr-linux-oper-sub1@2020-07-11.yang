submodule Cisco-IOS-XR-mediasvr-linux-oper-sub1 {
  belongs-to Cisco-IOS-XR-mediasvr-linux-oper {
    prefix Cisco-IOS-XR-mediasvr-linux-oper;
  }

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR mediasvr-linux package operational data.

     Copyright (c) 2013-2020 by Cisco Systems, Inc.
     All rights reserved.";

  revision 2020-07-11 {
    semver:module-version "2.0.0";
    description
      "Breaking show media result string into fields";
  }
  revision 2019-04-05 {
    description
      "Establish semantic version baseline.";
  }
  revision 2015-11-09 {
    description
      "IOS XR 6.0 revision.";
  }

  grouping SHOW-MEDIA-EDM-PARTITION {
    description
      "SHOW MEDIA EDM PARTITION";
    leaf name-xr {
      type string {
        length "0..32";
      }
      description
        "string name";
    }
    leaf size {
      type string {
        length "0..16";
      }
      description
        "string size";
    }
    leaf used {
      type string {
        length "0..16";
      }
      description
        "string used";
    }
    leaf percent {
      type string {
        length "0..16";
      }
      units "percentage";
      description
        "string percent";
    }
    leaf avail {
      type string {
        length "0..16";
      }
      description
        "string avail";
    }
  }
}
