module Cisco-IOS-XR-infra-alarm-logger-cfg {
  namespace "http://cisco.com/ns/yang/Cisco-IOS-XR-infra-alarm-logger-cfg";
  prefix infra-alarm-logger-cfg;

  import Cisco-IOS-XR-types {
    prefix xr;
  }
  import cisco-semver {
    prefix semver;
  }
  import Cisco-IOS-XR-infra-alarm-logger-datatypes {
    prefix dt1;
  }
  import Cisco-IOS-XR-infra-syslog-cfg {
    prefix a1;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR infra-alarm-logger package configuration.

     This YANG module augments the
       Cisco-IOS-XR-infra-syslog-cfg
     module with configuration data.

     Copyright (c) 2013-2019 by Cisco Systems, Inc.
     All rights reserved.";

  revision 2019-04-05 {
    semver:module-version "1.0.1";
    description
      "Establish semantic version baseline.";
  }
  revision 2017-02-23 {
    description
      "Added pre-config suppression feature";
  }
  revision 2015-01-07 {
    description
      "IOS XR 5.3.1 revision.";
  }

  augment "/a1:syslog" {
    description
      "This augment extends the configuration data of
       'Cisco-IOS-XR-infra-syslog-cfg'";
    container alarm-logger {
      description
        "Alarm Logger Properties";
      container alarm-filter-strings {
        description
          "List of filter strings";
        list alarm-filter-string {
          key "filter-string";
          description
            "Match string to filter alarms";
          leaf filter-string {
            type xr:Cisco-ios-xr-string;
            description
              "Filter String";
          }
        }
      }
      leaf pre-config-suppression {
        type empty;
        description
          "Suppress events from a card/VM till its
           configuration is complete";
      }
      leaf severity-level {
        type dt1:Alarm-logger-severity-level;
        description
          "Log all events with equal or higher (lower
           level) severity than this";
      }
      leaf pre-config-suppression-timeout {
        type uint32 {
          range "1..60";
        }
        units "minute";
        default "15";
        description
          "Timeout (in minutes) for pre-config events
           suppression (default 15)";
      }
      leaf buffer-size {
        type uint32 {
          range "1024..1024000";
        }
        description
          "Set size of the local event buffer";
      }
      leaf source-location {
        type empty;
        description
          "Enable alarm source location in message text";
      }
      leaf threshold {
        type uint32 {
          range "10..100";
        }
        default "90";
        description
          "Configure threshold (%) for capacity alarm";
      }
    }
  }
}
