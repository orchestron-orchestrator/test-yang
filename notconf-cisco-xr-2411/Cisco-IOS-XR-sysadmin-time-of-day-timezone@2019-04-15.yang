module Cisco-IOS-XR-sysadmin-time-of-day-timezone {
  namespace "http://cisco.com/calvados/Cisco-IOS-XR-sysadmin-time-of-day-timezone";
  prefix timezone;

  import Cisco-IOS-XR-sysadmin-show-trace {
    prefix show_trace;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR syadmin TOD configuration and cli.

     This module contains definitions
     for the following management objects:
     Time of the Day(TOD) Cli and configuration data

     Copyright (c) 2013-2020 by Cisco Systems, Inc.
     All rights reserved.";

  revision 2019-04-15 {
    semver:module-version "1.0.0";
    description
      "Establish semantic version baseline.";
  }
  revision 2016-07-04 {
    description
      "Remove refine stmt";
  }
  revision 2016-05-12 {
    description
      "Initial version";
  }

  container clock {
    container timezone {
      leaf tzname {
        type string;
      }
      leaf area {
        type string;
      }
    }
  }
  container trace {
    config false;
    container timezone_config {
      uses show_trace:traceable;
    }
    container timezone_notify {
      uses show_trace:traceable;
    }
  }
}
