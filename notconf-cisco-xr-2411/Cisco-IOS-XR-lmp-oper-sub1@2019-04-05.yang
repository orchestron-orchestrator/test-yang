submodule Cisco-IOS-XR-lmp-oper-sub1 {
  belongs-to Cisco-IOS-XR-lmp-oper {
    prefix Cisco-IOS-XR-lmp-oper;
  }

  import ietf-inet-types {
    prefix inet;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR lmp package operational data.

     Copyright (c) 2013-2019 by Cisco Systems, Inc.
     All rights reserved.";

  revision 2019-04-05 {
    semver:module-version "1.0.1";
    description
      "Establish semantic version baseline.";
  }
  revision 2015-11-09 {
    description
      "IOS XR 6.0 revision.";
  }

  typedef Olmipcc-state {
    type enumeration {
      enum "ipcc-state-oir-removed" {
        description
          "OIR Removed";
      }
      enum "ipcc-state-admin-down" {
        description
          "OOS";
      }
      enum "ipcc-state-down" {
        description
          "Down";
      }
      enum "ipcc-state-cfg-send" {
        description
          "ConfigSend";
      }
      enum "ipcc-state-cfg-rcv" {
        description
          "ConfigReceive";
      }
      enum "ipcc-state-active" {
        description
          "Active";
      }
      enum "ipcc-state-up" {
        description
          "Up";
      }
      enum "ipcc-state-going-down" {
        description
          "Going Down";
      }
      enum "ipcc-state-unknown" {
        description
          "Unknown/Invalid";
      }
    }
    description
      "The OLM IPCC state";
  }

  typedef Olm-comp-link-lmp-status {
    type enumeration {
      enum "comp-link-lmp-status-if-id-mismatch" {
        description
          "Component link IF ID mismatch";
      }
      enum "comp-link-lmp-status-switch-cap-mismatch" {
        description
          "Component link switching capability ID mismatch";
      }
    }
    description
      "The component link LMP status";
  }

  typedef Olm-link-encoding {
    type enumeration {
      enum "none" {
        description
          "None";
      }
      enum "packet" {
        description
          "Packet";
      }
      enum "ethernet" {
        description
          "Ethernet";
      }
      enum "ansi-etsi-pdh" {
        description
          "ANSI/ETSI PDH";
      }
      enum "reserved1" {
        description
          "Reserved";
      }
      enum "sdh-sonet" {
        description
          "SDH ITU-T G.707 / SONET ANSI T1.105";
      }
      enum "reserved2" {
        description
          "Reserved";
      }
      enum "digital-wrapper" {
        description
          "Digital Wrapper";
      }
      enum "lambda" {
        description
          "Lambda (photonic)";
      }
      enum "fiber" {
        description
          "Fiber";
      }
      enum "reserved3" {
        description
          "Reserved";
      }
      enum "fiber-channel" {
        description
          "FiberChannel";
      }
      enum "lencode-unknown" {
        description
          "Unknown";
      }
      enum "ethernet2" {
        description
          "Ethernet Type-2";
      }
    }
    description
      "LMP link encoding type as defined in [RFC3471]";
  }

  typedef Olmte-link-lmp-state {
    type enumeration {
      enum "te-link-lmp-state-down" {
        description
          "Down";
      }
      enum "te-link-lmp-state-init" {
        description
          "Init";
      }
      enum "te-link-lmp-state-up" {
        description
          "Up";
      }
      enum "te-link-lmp-state-degraded" {
        description
          "Degraded";
      }
      enum "te-link-lmp-state-unknown" {
        description
          "Unknown/Invalid";
      }
    }
    description
      "The OLM TE link LMP state";
  }

  typedef Olm-comp-link-lmp-state {
    type enumeration {
      enum "comp-link-lmp-state-down" {
        description
          "Down";
      }
      enum "comp-link-lmp-state-test" {
        description
          "Test";
      }
      enum "comp-link-lmp-state-passive-test" {
        description
          "Pasv Test";
      }
      enum "comp-link-lmp-state-up-free" {
        description
          "Up Free";
      }
      enum "comp-link-lmp-state-up-allocated" {
        description
          "Up Allocated";
      }
      enum "comp-link-lmp-state-unknown" {
        description
          "Unknown/Invalid";
      }
    }
    description
      "The OLM Component link LMP state";
  }

  typedef Olm-comp-link-im-state {
    type enumeration {
      enum "comp-link-im-state-oir" {
        description
          "OIR removed";
      }
      enum "comp-link-im-state-down" {
        description
          "Down";
      }
      enum "comp-link-im-state-admin-down" {
        description
          "Admin Down";
      }
      enum "comp-link-im-state-up" {
        description
          "Up";
      }
      enum "comp-link-im-state-unknown" {
        description
          "Unknown";
      }
    }
    description
      "The OLM Component link IM state";
  }

  typedef Olm-mux-cap {
    type enumeration {
      enum "psc1" {
        description
          "PSC 1";
      }
      enum "psc2" {
        description
          "PSC 2";
      }
      enum "psc3" {
        description
          "PSC 3";
      }
      enum "psc4" {
        description
          "PSC 4";
      }
      enum "l2sc" {
        description
          "L2SC";
      }
      enum "tdm" {
        description
          "TDM";
      }
      enum "lsc" {
        description
          "LSC";
      }
      enum "fsc" {
        description
          "FSC";
      }
      enum "dcsc" {
        description
          "DCSC";
      }
      enum "unknown-mux-cap" {
        description
          "Unknown Mux Cap";
      }
    }
    description
      "Multiplexing capability";
  }

  typedef Olmipcc {
    type enumeration {
      enum "ipcc-type-global-routed" {
        description
          "Global routed IPCC";
      }
      enum "ipcc-type-global-if-bound" {
        description
          "Global I/F bound IPCC";
      }
      enum "ipcc-type-ldcc-sdcc" {
        description
          "SDCC/LDCC in fiber in band type IPCC";
      }
      enum "ipcc-type-unknown" {
        description
          "Unknown IPCC type";
      }
    }
    description
      "The OLM IPCC type";
  }

  typedef Olm-object-owner {
    type enumeration {
      enum "unknown" {
        description
          "Unknown owner";
      }
      enum "ouni" {
        description
          "OIF OUNI";
      }
      enum "gmpls-nni" {
        description
          "GMPLS NNI";
      }
      enum "gmpls-uni" {
        description
          "GMPLS UNI";
      }
    }
    description
      "The OLM object owner";
  }

  typedef Olm-router-id {
    type enumeration {
      enum "not-configured" {
        description
          "No router ID configured";
      }
      enum "global" {
        description
          "Global router ID";
      }
      enum "protocol-based-address" {
        description
          "Protocol based CLIrouter ID configured";
      }
      enum "interface" {
        description
          "Protocol based CLI I/Frouter ID configured";
      }
      enum "network-element" {
        description
          "Protocol based CLI I/F routerID configured on
           I/F that is not known to the system";
      }
      enum "unknown-type" {
        description
          "Unknown";
      }
    }
    description
      "The OLM router ID type";
  }

  typedef Ipv6-address {
    type inet:ipv6-address;
    description
      "Ipv6 address";
  }

  typedef Olm-addr-type-id {
    type enumeration {
      enum "unknown-address" {
        value 0;
        description
          "Unknown address type";
      }
      enum "ipv4" {
        value 101;
        description
          "IPv4 address type";
      }
      enum "ipv6" {
        value 102;
        description
          "IPv6 address type";
      }
      enum "unnumbered" {
        value 103;
        description
          "Unnumberedaddress type";
      }
    }
    description
      "OLM Link Address Type";
  }

  grouping OLM-COMPONENT-LINK-ID-INFO {
    description
      "OLM component link ID information";
    leaf component-interface-id {
      type uint32;
      description
        "LMP component link ID for an I/F";
    }
  }

  grouping OLM-IPCC-INFO {
    description
      "OLM information for a particular IPCC";
    container remote-ipcc-address {
      description
        "The remote node'sIPCC address";
      uses OLM-ADDR;
    }
    container source-ip-cc-address {
      description
        "The local IPCC address";
      uses OLM-ADDR;
    }
    leaf ipcc-id {
      type uint32;
      description
        "Global active IPCCfor this neighbor";
    }
    leaf ipc-ctype {
      type Olmipcc;
      description
        "OLM IPCC type";
    }
    leaf interface-name {
      type string;
      description
        "The interface name forI/F IPCCs";
    }
    leaf neighbor-name {
      type string;
      description
        "Neighbor name of theIPCCs neighbor";
    }
    leaf ipcc-state {
      type Olmipcc-state;
      description
        "OLM IPCC master state";
    }
    leaf lmp-hello-interval {
      type uint32;
      description
        "LMP hello send interval in msec [DEPRECATED]";
    }
    leaf lmp-hello-interval-minimum {
      type uint32;
      description
        "LMP minimum acceptable hello send interval
         [DEPRECATED]";
    }
    leaf lmp-hello-interval-maximum {
      type uint32;
      description
        "LMP maximum acceptable hello send interval
         [DEPRECATED]";
    }
    leaf lmp-hello-dead-interval {
      type uint32;
      description
        "LMP hello dead interval [DEPRECATED]";
    }
    leaf lmp-hello-dead-interval-minimum {
      type uint32;
      description
        "LMP minimum acceptable hello dead interval
         [DEPRECATED]";
    }
    leaf lmp-hello-dead-interval-maximum {
      type uint32;
      description
        "LMP maximum acceptable hello dead interval
         [DEPRECATED]";
    }
    leaf lmp-hello-transmit-packets {
      type uint32;
      description
        "LMP hello transmit packet count[DEPRECATED]";
    }
    leaf lmp-hello-receive-packets {
      type uint32;
      description
        "LMP hello receive packet count [DEPRECATED]";
    }
    leaf lmp-hello-transmit-packet-sequence-number {
      type uint32;
      description
        "LMP hello transmit packet sequence number
         [DEPRECATED]";
    }
    leaf lmp-hello-receive-packet-sequence-number {
      type uint32;
      description
        "LMP hello receive packet sequence
         number[DEPRECATED]";
    }
    leaf lmp-transmit-msg-id {
      type uint32;
      description
        "LMP transmit message ID[DEPRECATED]";
    }
    leaf lmp-receive-msg-id {
      type uint32;
      description
        "LMP receive message ID[DEPRECATED]";
    }
    leaf lmp-link-sum-transmit-packets {
      type uint32;
      description
        "LMP link summary transmit packet count
         [DEPRECATED]";
    }
    leaf lmp-link-sum-receive-packets {
      type uint32;
      description
        "LMP link summary receive packet count
         [DEPRECATED]";
    }
  }

  grouping OLM-NEIGHBOR-INFO {
    description
      "OLM information for a particular neighbor";
    container neighbor-address {
      description
        "The remote node ID of the neighbor";
      uses OLM-ADDR;
    }
    leaf protocol-owner {
      type Olm-object-owner;
      description
        "Protocol owningthis neighbor";
    }
    leaf ipcc-id {
      type uint32;
      description
        "The global active IPCCfor this neighbor";
    }
    leaf is-lmp-enabled {
      type boolean;
      description
        "Is LMP enabled on this neighbor [DEPRECATED]";
    }
    leaf is-lmp-config-disabled {
      type boolean;
      description
        "Are LMP hellos disabled through configuration
         for this neighbor [DEPRECATED]";
    }
    leaf lmp-transmit-msg-id {
      type uint32;
      description
        "LMP transmit message ID [DEPRECATED]";
    }
    leaf lmp-receive-msg-id {
      type uint32;
      description
        "LMP receive message ID [DEPRECATED]";
    }
    leaf lmp-link-sum-transmit-packets {
      type uint32;
      description
        "LMP link summary transmit packet count
         [DEPRECATED]";
    }
    leaf lmp-link-sum-receive-packets {
      type uint32;
      description
        "LMP link summary receive packet
         count[DEPRECATED]";
    }
    list te-link {
      description
        "A list of TE Links connected to this neighbor";
      uses OLM-TE-LINK-INFO;
    }
    list ipcc {
      description
        "A list of IPCCs connected to this neighbor";
      uses OLM-IPCC-INFO;
    }
  }

  grouping OLM-TE-LINK-INFO {
    description
      "OLM information for a particular TE Link";
    container local-link-id {
      description
        "The local datalink ID";
      uses OLM-ADDR;
    }
    container remote-link-id {
      description
        "The remote datalink ID";
      uses OLM-ADDR;
    }
    container local-te-link-id {
      description
        "Local TE-Link ID/ TNA address";
      uses OLM-ADDR;
    }
    container remote-te-link-id {
      description
        "Remote TE-Link ID/ TNA address";
      uses OLM-ADDR;
    }
    container neighbor-address {
      description
        "The address of the neighbor";
      uses OLM-ADDR;
    }
    container remote-ipcc-address {
      description
        "The remote node's IPCC address";
      uses OLM-ADDR;
    }
    leaf interface-name {
      type string;
      description
        "Interface forOLM info";
    }
    leaf protocol-owner {
      type Olm-object-owner;
      description
        "Protocol owningthis te-link";
    }
    leaf neighbor-name {
      type string;
      description
        "The name of the neighbor";
    }
    leaf ipcc-id {
      type uint32;
      description
        "The IPCC ID";
    }
    leaf ipc-ctype {
      type Olmipcc;
      description
        "OLM IPCC type";
    }
    leaf ipcc-name {
      type string;
      description
        "The name ofthe IPCC associated with the TE Link";
    }
    leaf local-mux-cap {
      type Olm-mux-cap;
      description
        "The local mux capability";
    }
    leaf remote-mux-cap {
      type Olm-mux-cap;
      description
        "The remote mux capability";
    }
    leaf im-state {
      type Olm-comp-link-im-state;
      description
        "data link IM state";
    }
    leaf lmp-state {
      type Olm-comp-link-lmp-state;
      description
        "data link LMP state";
    }
    leaf te-link-lmp-state {
      type Olmte-link-lmp-state;
      description
        "TE LinkLMP state";
    }
    leaf gmpls-te-link-local-minimum-bandwidth {
      type uint64;
      units "byte/s";
      description
        "GMPLS localminimum B/W in bytes/sec";
    }
    leaf gmpls-te-link-local-maximum-bandwidth {
      type uint64;
      units "byte/s";
      description
        "GMPLS localmaximum B/W in bytes/sec";
    }
    leaf gmpls-te-link-neighbor-minimum-bandwidth {
      type uint64;
      units "byte/s";
      description
        "GMPLSneighbor minimum B/W in bytes/sec";
    }
    leaf gmpls-te-link-neighbor-maximum-bandwidth {
      type uint64;
      units "byte/s";
      description
        "GMPLSneighbor maximum B/W in bytes/sec";
    }
    leaf gmpls-te-link-local-encoding-type {
      type Olm-link-encoding;
      description
        "GMPLS locallink encoding type";
    }
    leaf gmpls-te-link-neighbor-encoding-type {
      type Olm-link-encoding;
      description
        "GMPLS neighborlink encoding type";
    }
    leaf is-lmp-enabled {
      type boolean;
      description
        "Is LMP enabledon this TE link";
    }
    leaf lmp-transmit-msg-id {
      type uint32;
      description
        "LMP transmitmessage ID";
    }
    leaf lmp-receive-msg-id {
      type uint32;
      description
        "LMP receivemessage ID";
    }
    leaf-list lmp-comp-link-status {
      type Olm-comp-link-lmp-status;
      description
        "Component link LMP status indicators";
    }
  }

  grouping OLM-TIME {
    description
      "OLM Time Stamp";
    leaf time-connected {
      type uint32;
      description
        "The time the clientconnected in sec";
    }
  }

  grouping OLM-CLIENT-INFO {
    description
      "OLM information for a particular OLM client";
    container connected-time {
      description
        "The time the clientconnected in sec";
      uses OLM-TIME;
    }
    leaf node-name {
      type string;
      description
        "The RP name that the clientprocess is running on";
    }
  }

  grouping OLM-ADDR-U {
    description
      "OLM ADDR U";
    leaf address-type {
      type Olm-addr-type-id;
      description
        "AddressType";
    }
    leaf ipv4-address {
      when "../address-type = 'ipv4'" {
        description
          "../AddressType = 'IPv4'";
      }
      type inet:ipv4-address;
      description
        "IPv4 address";
    }
    leaf ipv6-address {
      when "../address-type = 'ipv6'" {
        description
          "../AddressType = 'IPv6'";
      }
      type Ipv6-address;
      description
        "IPv6 address";
    }
    leaf unnumbered-address {
      when "../address-type = 'unnumbered'" {
        description
          "../AddressType = 'Unnumbered'";
      }
      type uint32;
      description
        "Unnumberedaddress";
    }
  }

  grouping OLM-ADDR {
    description
      "TE Link or component link address";
    container address {
      description
        "Address Union";
      uses OLM-ADDR-U;
    }
  }

  grouping OLM-GLOBAL-INFO {
    description
      "OLM general information";
    container local-ouni-lmp-node-id {
      description
        "Local OUNI LMP Node ID";
      uses OLM-ADDR;
    }
    container local-mpls-te-lmp-node-id {
      description
        "MPLS TE LMP Node ID";
      uses OLM-ADDR;
    }
    container local-gmpls-uni-lmp-node-id {
      description
        "GMPLS UNI LMP Node ID";
      uses OLM-ADDR;
    }
    leaf local-ouni-lmp-node-id-interface {
      type string;
      description
        "Local OUNI LMP Node ID I/F";
    }
    leaf local-ouni-lmp-node-id-type {
      type Olm-router-id;
      description
        "Local OUNI LMP Node ID type";
    }
    leaf is-ouni-config-exist {
      type boolean;
      description
        "TRUE if any OLM OUNI config exists";
    }
    leaf is-gmpls-nni-config-exist {
      type boolean;
      description
        "TRUE if any OLM/LNP GMPLS NNI config exists";
    }
    leaf is-gmpls-uni-config-exist {
      type boolean;
      description
        "TRUE if any OLM/LMP GMPLS UNI config exists";
    }
  }
}
