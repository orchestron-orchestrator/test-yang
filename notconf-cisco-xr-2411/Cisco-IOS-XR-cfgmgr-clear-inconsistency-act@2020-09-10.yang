module Cisco-IOS-XR-cfgmgr-clear-inconsistency-act {
  namespace "http://cisco.com/ns/yang/Cisco-IOS-XR-cfgmgr-clear-inconsistency-act";
  prefix cfgmgr-clear-inconsistency-act;

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR action package configuration.

     Copyright (c) 2020 by Cisco Systems, Inc.
     All rights reserved.";

  revision 2020-09-10 {
    semver:module-version "1.0.0";
    description
      "IOS XR initial revision.";
    reference
      "RFC VVVV: NETCONF Server and RESTCONF Server Operational
       Models";
  }

  rpc clear-config-inconsistency {
    description
      "Clear configuration inconsistency";

    input {
      leaf inconsistency {
        type empty;
        mandatory true;
        description
          "Configuration inconsistencies";
      }
    }
  }
}
