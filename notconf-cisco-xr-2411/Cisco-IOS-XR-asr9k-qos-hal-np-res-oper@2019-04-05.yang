module Cisco-IOS-XR-asr9k-qos-hal-np-res-oper {
  namespace "http://cisco.com/ns/yang/Cisco-IOS-XR-asr9k-qos-hal-np-res-oper";
  prefix asr9k-qos-hal-np-res-oper;

  import Cisco-IOS-XR-types {
    prefix xr;
  }
  import cisco-semver {
    prefix semver;
  }

  include Cisco-IOS-XR-asr9k-qos-hal-np-res-oper-sub1 {
    revision-date 2019-04-05;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR asr9k-qos-hal-np-res package operational data.

     This module contains definitions
     for the following management objects:
       hardware-module-np: Hardware NP Counters

     Copyright (c) 2013-2019 by Cisco Systems, Inc.
     All rights reserved.";

  revision 2019-04-05 {
    semver:module-version "1.0.0";
    description
      "Establish semantic version baseline.";
  }
  revision 2015-11-09 {
    description
      "IOS XR 6.0 revision.";
  }

  typedef Np {
    type string {
      pattern "(np0)|(np1)|(np2)|(np3)|(np4)|(np5)|(np6)|(np7)|(np8)";
    }
    description
      "np0:NP0, np1:NP1, np2:NP2, np3:NP3, np4:NP4, np5
       :NP5, np6:NP6, np7:NP7, np8:NP8";
  }

  container hardware-module-np {
    config false;
    description
      "Hardware NP Counters";
    container nodes {
      description
        "Table of nodes";
      list node {
        key "node-name";
        description
          "Details for a specific node";
        container nps {
          description
            "List of all NP";
          list np {
            key "np-name";
            description
              "Details for a specific NPU";
            leaf np-name {
              type Np;
              description
                "NP name";
            }
            uses NPHAL-RESOURCE-COUNTERS;
          }
        }
        leaf node-name {
          type xr:Node-id;
          description
            "node number";
        }
      }
    }
  }
}
