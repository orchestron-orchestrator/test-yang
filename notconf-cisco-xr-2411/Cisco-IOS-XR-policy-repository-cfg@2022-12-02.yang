module Cisco-IOS-XR-policy-repository-cfg {
  namespace "http://cisco.com/ns/yang/Cisco-IOS-XR-policy-repository-cfg";
  prefix policy-repository-cfg;

  import Cisco-IOS-XR-types {
    prefix xr;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR policy-repository package configuration.

     This module contains definitions
     for the following management objects:
       routing-policy: Routing policy configuration

     Copyright (c) 2013-2022 by Cisco Systems, Inc.
     All rights reserved.";

  revision 2022-12-02 {
    semver:module-version "1.1.0";
    description
      "Updated RPL knob operations to include extcomm evpn-link-bandwidth.
       2022-06-22
         Updating RPL knob for set nexthop with allocate-vpn-label";
  }
  revision 2019-04-05 {
    semver:module-version "1.0.1";
    description
      "Establish semantic version baseline.";
  }
  revision 2017-09-07 {
    description
      "Fixing prepend/append/remove containers.";
  }
  revision 2017-09-07 {
    description
      "Fixed type translation error.";
  }
  revision 2015-08-27 {
    description
      "IOS XR 5.3.2 revision.";
  }

  container routing-policy {
    description
      "Routing policy configuration";
    container route-policies {
      description
        "All configured policies";
      list route-policy {
        key "route-policy-name";
        description
          "Information about an individual policy";
        leaf route-policy-name {
          type xr:Cisco-ios-xr-string;
          description
            "Route policy name";
        }
        leaf rpl-route-policy {
          type xr:Rpl-policy;
          mandatory true;
          description
            "policy statements";
        }
      }
    }
    container sets {
      description
        "All configured sets";
      container prefix-sets {
        description
          "Information about Prefix sets";
        list prefix-set {
          key "set-name";
          description
            "Information about an individual set";
          leaf set-name {
            type xr:Cisco-ios-xr-string;
            description
              "Set name";
          }
          leaf rpl-prefix-set {
            type xr:Rpl-set;
            mandatory true;
            description
              "prefix statements";
          }
        }
      }
      container large-community-sets {
        description
          "Information about Large Community sets";
        list large-community-set {
          key "set-name";
          description
            "Information about an individual set";
          leaf set-name {
            type xr:Cisco-ios-xr-string;
            description
              "Set name";
          }
          leaf large-community-set-as-text {
            type xr:Rpl-set;
            mandatory true;
            description
              "Large Community Set";
          }
        }
      }
      container extended-community-evpn-bandwidth-sets {
        description
          "Information about EVPN Link Bandwidth sets";
        list extended-community-evpn-bandwidth-set {
          key "set-name";
          description
            "Information about an individual set";
          leaf set-name {
            type xr:Cisco-ios-xr-string;
            description
              "Set name";
          }
          leaf extended-community-evpn-bandwidth-set-as-text {
            type xr:Rpl-set;
            mandatory true;
            description
              "Extended Community EVPN Link Bandwidth Set";
          }
        }
      }
      container mac-sets {
        description
          "Information about Mac sets";
        list mac-set {
          key "set-name";
          description
            "Information about an individual set";
          leaf set-name {
            type xr:Cisco-ios-xr-string;
            description
              "Set name";
          }
          leaf mac-set-as-text {
            type xr:Rpl-set;
            mandatory true;
            description
              "Mac Set";
          }
        }
      }
      container extended-community-opaque-sets {
        description
          "Information about Opaque sets";
        list extended-community-opaque-set {
          key "set-name";
          description
            "Information about an individual set";
          leaf set-name {
            type xr:Cisco-ios-xr-string;
            description
              "Set name";
          }
          leaf rpl-extended-community-opaque-set {
            type xr:Rpl-set;
            mandatory true;
            description
              "Extended Community Opaque Set";
          }
        }
      }
      container ospf-area-sets {
        description
          "Information about OSPF Area sets";
        list ospf-area-set {
          key "set-name";
          description
            "Information about an individual OSPF area set.
             Usage: OSPF area set allows to define named
             set of area numbers        which can be
             referenced in the route-policy. Area sets
             may be used during redistribution of the ospf
             protocol.  Example: ospf-area-set EXAMPLE
             1,
             192.168.1.255
             end-set
             Syntax: OSPF area number can be entered as 32
             bit number or in          the ip address
             format. See example.
             Semantic: Area numbers listed in the set will
             be searched for             a match. In the
             example these are areas 1 and
             192.168.1.255.                                ";
          leaf set-name {
            type xr:Cisco-ios-xr-string;
            description
              "Set name";
          }
          leaf rplospf-area-set {
            type xr:Rpl-set;
            mandatory true;
            description
              "OSPF Area Set";
          }
        }
      }
      container extended-community-cost-sets {
        description
          "Information about Cost sets";
        list extended-community-cost-set {
          key "set-name";
          description
            "Information about an individual set";
          leaf set-name {
            type xr:Cisco-ios-xr-string;
            description
              "Set name";
          }
          leaf rpl-extended-community-cost-set {
            type xr:Rpl-set;
            mandatory true;
            description
              "Extended Community Cost Set";
          }
        }
      }
      container extended-community-soo-sets {
        description
          "Information about SOO sets";
        list extended-community-soo-set {
          key "set-name";
          description
            "Information about an individual set";
          leaf set-name {
            type xr:Cisco-ios-xr-string;
            description
              "Set name";
          }
          leaf rpl-extended-community-soo-set {
            type xr:Rpl-set;
            mandatory true;
            description
              "Extended Community SOO Set";
          }
        }
      }
      container esi-sets {
        description
          "Information about Esi sets";
        list esi-set {
          key "set-name";
          description
            "Information about an individual set";
          leaf set-name {
            type xr:Cisco-ios-xr-string;
            description
              "Set name";
          }
          leaf esi-set-as-text {
            type xr:Rpl-set;
            mandatory true;
            description
              "Esi Set";
          }
        }
      }
      container append-extended-community-evpn-bandwidth-sets {
        description
          "Information about EVPN Link Bandwidth sets";
        list append-extended-community-evpn-bandwidth-set {
          key "set-name";
          description
            "Append the entries to the existing set";
          leaf set-name {
            type xr:Cisco-ios-xr-string;
            description
              "Set name";
          }
          leaf extended-community-evpn-bandwidth-set-as-text {
            type xr:Rpl-set;
            mandatory true;
            description
              "Extended Community EVPN Link Bandwidth Set";
          }
        }
      }
      container extended-community-seg-nh-sets {
        description
          "Information about SegNH sets";
        list extended-community-seg-nh-set {
          key "set-name";
          description
            "Information about an individual set";
          leaf set-name {
            type xr:Cisco-ios-xr-string;
            description
              "Set name";
          }
          leaf rpl-extended-community-seg-nh-set {
            type xr:Rpl-set;
            mandatory true;
            description
              "Extended Community SegNH Set";
          }
        }
      }
      container rd-sets {
        description
          "Information about RD sets";
        list rd-set {
          key "set-name";
          description
            "Information about an individual set";
          leaf set-name {
            type xr:Cisco-ios-xr-string;
            description
              "Set name";
          }
          leaf rplrd-set {
            type xr:Rpl-set;
            mandatory true;
            description
              "RD Set";
          }
        }
      }
      container policy-global-set-table {
        description
          "Information about PolicyGlobal sets";
        leaf policy-global-set {
          type xr:Rpl-set;
          description
            "Information about an individual set";
        }
      }
      container remove-extended-community-evpn-bandwidth-sets {
        description
          "Information about EVPN Link Bandwidth sets";
        list remove-extended-community-evpn-bandwidth-set {
          key "set-name";
          description
            "Remove the entries from the existing set";
          leaf set-name {
            type xr:Cisco-ios-xr-string;
            description
              "Set name";
          }
          leaf extended-community-evpn-bandwidth-set-as-text {
            type xr:Rpl-set;
            mandatory true;
            description
              "Extended Community EVPN Link Bandwidth Set";
          }
        }
      }
      container prepend-extended-community-evpn-bandwidth-sets {
        description
          "Information about EVPN Link Bandwidth sets";
        list prepend-extended-community-evpn-bandwidth-set {
          key "set-name";
          description
            "Prepend the entries to the existing set";
          leaf set-name {
            type xr:Cisco-ios-xr-string;
            description
              "Set name";
          }
          leaf extended-community-evpn-bandwidth-set-as-text {
            type xr:Rpl-set;
            mandatory true;
            description
              "Extended Community EVPN Link Bandwidth Set";
          }
        }
      }
      container extended-community-bandwidth-sets {
        description
          "Information about Bandwidth sets";
        list extended-community-bandwidth-set {
          key "set-name";
          description
            "Information about an individual set";
          leaf set-name {
            type xr:Cisco-ios-xr-string;
            description
              "Set name";
          }
          leaf rpl-extended-community-bandwidth-set {
            type xr:Rpl-set;
            mandatory true;
            description
              "Extended Community Bandwidth Set";
          }
        }
      }
      container community-sets {
        description
          "Information about Community sets";
        list community-set {
          key "set-name";
          description
            "Information about an individual set";
          leaf set-name {
            type xr:Cisco-ios-xr-string;
            description
              "Set name";
          }
          leaf rpl-community-set {
            type xr:Rpl-set;
            mandatory true;
            description
              "Community Set";
          }
        }
      }
      container as-path-sets {
        description
          "Information about AS Path sets";
        list as-path-set {
          key "set-name";
          description
            "Information about an individual set";
          leaf set-name {
            type xr:Cisco-ios-xr-string;
            description
              "Set name";
          }
          leaf rplas-path-set {
            type xr:Rpl-set;
            mandatory true;
            description
              "ASPath Set";
          }
        }
      }
      container tag-sets {
        description
          "Information about Tag sets";
        list tag-set {
          key "set-name";
          description
            "Information about an individual set";
          leaf set-name {
            type xr:Cisco-ios-xr-string;
            description
              "Set name";
          }
          leaf rpl-tag-set {
            type xr:Rpl-set;
            mandatory true;
            description
              "Tag Set";
          }
        }
      }
      container etag-sets {
        description
          "Information about Etag sets";
        list etag-set {
          key "set-name";
          description
            "Information about an individual set";
          leaf set-name {
            type xr:Cisco-ios-xr-string;
            description
              "Set name";
          }
          leaf etag-set-as-text {
            type xr:Rpl-set;
            mandatory true;
            description
              "Etag Set";
          }
        }
      }
      container extended-community-rt-sets {
        description
          "Information about RT sets";
        list extended-community-rt-set {
          key "set-name";
          description
            "Information about an individual set";
          leaf set-name {
            type xr:Cisco-ios-xr-string;
            description
              "Set name";
          }
          leaf rpl-extended-community-rt-set {
            type xr:Rpl-set;
            mandatory true;
            description
              "Extended Community RT Set";
          }
        }
      }
    }
    container limits {
      description
        "Limits for Routing Policy";
      leaf maximum-lines-of-policy {
        type uint32;
        default "131072";
        description
          "Maximum number of lines of policy configuration
           that may be configured in total";
      }
      leaf maximum-number-of-policies {
        type uint32;
        default "5000";
        description
          "Maximum number of policies that may be
           configured";
      }
    }
    leaf set-exit-as-abort {
      type empty;
      description
        "Set exit under RPL config to abort";
    }
    leaf editor {
      type string;
      description
        "'emacs' or 'vim' or 'nano'";
    }
  }
}
