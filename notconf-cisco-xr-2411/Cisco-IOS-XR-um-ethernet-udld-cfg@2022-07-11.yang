module Cisco-IOS-XR-um-ethernet-udld-cfg {
  namespace "http://cisco.com/ns/yang/Cisco-IOS-XR-um-ethernet-udld-cfg";
  prefix um-ethernet-udld-cfg;

  import ietf-yang-types {
    prefix yang;
  }
  import Cisco-IOS-XR-um-interface-cfg {
    prefix a1;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ethernet-udld package configuration.

     This YANG module augments the
     modules with configuration data.

     Copyright (c) 2022 by Cisco Systems, Inc.
     All rights reserved.";

  revision 2022-07-11 {
    semver:module-version "1.0.0";
    description
      "Added missing description statement to nodes";
  }
  revision 2022-02-09 {
    description
      "Initial release";
  }

  grouping IF-ETHER-BODY {
    description
      "Grouping for if-ether";
    container ethernet {
      description
        "Ethernet per-interface configuration commands";
      container udld {
        presence "Indicates a udld node is configured.";
        description
          "Enable the UniDirectional Link Detection protocol";
        container mode {
          description
            "Set the mode in which to run the UDLD protocol";
          container normal {
            must "not(../aggressive)";
            presence "Indicates a normal node is configured.";
            description
              "Run UDLD in normal mode";
          }
          container aggressive {
            must "not(../normal)";
            presence "Indicates a aggressive node is configured.";
            description
              "Run UDLD in aggressive mode";
          }
        }
        leaf message-time {
          type uint32 {
            range "7..90" {
              description
                "'Mslow' message time (in seconds) to use for the UDLD protocol";
            }
          }
          description
            "Set the 'Mslow' message time (in seconds) for the UDLD protocol";
        }
        container logging {
          description
            "Set whether operational UDLD syslogs are displayed";
          container disable {
            presence "Indicates a disable node is configured.";
            description
              "Suppress operational UDLD syslogs";
          }
        }
        container destination {
          description
            "Set the destination MAC address used in UDLD frames sent/received on this port";
          container mac-address {
            description
              "Set the destination MAC address used in UDLD frames sent/received on this port";
            leaf address {
              type yang:mac-address;
              must "not(../cisco-l2cp or ../ieee-slow-protocols)";
              description
                "Set the destination MAC address used in UDLD frames sent/received on this port";
            }
            container ieee-slow-protocols {
              must "not(../cisco-l2cp or ../address)";
              presence "Indicates a ieee-slow-protocols node is configured.";
              description
                "Use the IEEE slow protocol destination MAC address";
            }
            container cisco-l2cp {
              must "not(../ieee-slow-protocols or ../address)";
              presence "Indicates a cisco-l2cp node is configured.";
              description
                "Use the Cisco L2CP MAC address (used by CDP)";
            }
          }
        }
      }
    }
  }

  augment "/a1:interfaces/a1:interface" {
    description
      "This augment extends active nodes configuration";
    uses IF-ETHER-BODY;
  }
  augment "/a1:interfaces/a1:interface-preconfigure" {
    description
      "This augment extends preconfigured nodes
       configuration";
    uses IF-ETHER-BODY;
  }
}
