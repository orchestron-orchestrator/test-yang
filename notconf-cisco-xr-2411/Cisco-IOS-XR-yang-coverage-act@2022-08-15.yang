module Cisco-IOS-XR-yang-coverage-act {
  namespace "http://cisco.com/ns/yang/Cisco-IOS-XR-yang-coverage-act";
  prefix yang-coverage-act;

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR Controller to interact with Yang coverage logging.

     Copyright (c) 2022 by Cisco Systems, Inc.
     All rights reserved.";

  revision 2022-08-15 {
    semver:module-version "1.0.0";
    description
      "Initial model definition.";
    reference
      "IOS-XR 7.9.1";
  }

  typedef yang-coverage-test-phase {
    type enumeration {
      enum "UT" {
        value 10;
        description
          "Unit test phase";
      }
      enum "IT" {
        value 20;
        description
          "Integration test phase";
      }
      enum "DT" {
        value 30;
        description
          "Development test phase";
      }
      enum "SIT" {
        value 40;
        description
          "System integration test phase";
      }
      enum "ACCEPTANCE" {
        value 50;
        description
          "Acceptance test phase";
      }
    }
    description
      "Supported test phases for Yang coverage logging";
  }

  typedef yang-coverage-test-type {
    type enumeration {
      enum "MANUAL" {
        value 10;
        description
          "Manual testing, i.e. not part of a regression. If the testing is
           scripted use OCCASIONAL";
      }
      enum "PRECOMMIT" {
        value 20;
        description
          "Pre-commit gating testing, i.e. integrated into the pre-commit
           workflow. If testing is manually triggered use MANUAL";
      }
      enum "NIGHTLY" {
        value 30;
        description
          "Nightly regression testing, i.e. automated testing run via, e.g.
           Jenkins, a cron job, etc.";
      }
      enum "OCCASIONAL" {
        value 40;
        description
          "Occasional testing, i.e, ad-hoc but automated testing, run when
           needed, or infrequently. If the testing is performed manually,
           not via scripting, use MANUAL";
      }
    }
    description
      "Supported types of testing for Yang coverage logging";
  }

  rpc yang-coverage-clear-test-logs {
    description
      "Clear any existing Yang coverage test logs";
  }

  rpc yang-coverage-get-test-logs {
    description
      "Get the current set of Yang coverage test logs";

    input {
      leaf test-name {
        type string;
        description
          "Name for the current testing being performed. This is not used by
           the yang coverage tooling, but provides the option to filter
           results specific to this test from the report database.
           e.g. ifmgr_ut1, cafy_ap_ipv4, enxr-sanity";
      }
      leaf test-phase {
        type yang-coverage-test-phase;
        description
          "Test phase the current logs on box were collected in. This allows
           the yang coverage results to be filtered by test phase, to see
           what levels of coverage each phase provides";
      }
      leaf test-type {
        type yang-coverage-test-type;
        description
          "Type of testing the current logs on box were collected in. This
           allows the yang coverage results to be filtered by test type,
           e.g. the level of PRECOMMIT coverage, vs NIGHTLY, etc.";
      }
    }
  }
}
