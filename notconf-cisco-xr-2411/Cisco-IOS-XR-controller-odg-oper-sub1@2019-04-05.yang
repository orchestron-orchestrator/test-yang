submodule Cisco-IOS-XR-controller-odg-oper-sub1 {
  belongs-to Cisco-IOS-XR-controller-odg-oper {
    prefix Cisco-IOS-XR-controller-odg-oper;
  }

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR controller-odg package operational data.

     Copyright (c) 2013-2019 by Cisco Systems, Inc.
     All rights reserved.";

  revision 2019-04-05 {
    semver:module-version "1.0.0";
    description
      "Establish semantic version baseline.";
  }
  revision 2015-11-09 {
    description
      "IOS XR 6.0 revision.";
  }

  typedef Fault-types-et {
    type enumeration {
      enum "lockout-request" {
        value 0;
        description
          "Lockout Request";
      }
      enum "lockout-release" {
        value 1;
        description
          "Lockout Release";
      }
      enum "force-request" {
        value 2;
        description
          "Force switch request";
      }
      enum "force-release" {
        value 3;
        description
          "Force switch release";
      }
      enum "signal-fail" {
        value 4;
        description
          "Signal fail event ";
      }
      enum "signal-fail-clear" {
        value 5;
        description
          "Signal fail clear event";
      }
      enum "signal-degrade" {
        value 6;
        description
          "Signal Degrade event";
      }
      enum "signal-degrade-clear" {
        value 7;
        description
          " Signal Degrade clear event";
      }
      enum "manual-request" {
        value 8;
        description
          "Manual switch request";
      }
      enum "manual-release" {
        value 9;
        description
          "Manual switch release";
      }
      enum "wait-to-restore" {
        value 10;
        description
          "Wait to restore expire";
      }
      enum "exercise-request" {
        value 11;
        description
          " Exercise request";
      }
      enum "exercise-release" {
        value 12;
        description
          "Exercise release ";
      }
      enum "revert-request" {
        value 13;
        description
          " Revert request";
      }
      enum "donot-revert" {
        value 14;
        description
          "Do not revert";
      }
      enum "no-request" {
        value 15;
        description
          "No request ";
      }
      enum "max-events" {
        value 16;
        description
          "Max events";
      }
    }
    description
      "Fault types et";
  }

  typedef Odg-aps-states-et {
    type enumeration {
      enum "odg-st-lo" {
        value 0;
        description
          "Lockout for Protection Request";
      }
      enum "odg-st-sfp" {
        value 1;
        description
          "Signal Failed on Protecting";
      }
      enum "odg-st-fs" {
        value 2;
        description
          " Forced Switch";
      }
      enum "odg-st-sfw" {
        value 3;
        description
          " Signal failed on Working";
      }
      enum "odg-st-sd" {
        value 4;
        description
          "Signal Degrade";
      }
      enum "odg-st-ms" {
        value 5;
        description
          "Manual Switch";
      }
      enum "odg-st-wtr" {
        value 6;
        description
          "Wait to restore";
      }
      enum "odg-st-exer" {
        value 7;
        description
          "Exercise";
      }
      enum "odg-st-rr" {
        value 8;
        description
          "Reverse Request";
      }
      enum "odg-st-dnr" {
        value 9;
        description
          "Do Not Revert State";
      }
      enum "odg-st-nr" {
        value 10;
        description
          "No Request State";
      }
      enum "odg-max-states" {
        value 11;
        description
          "Max state";
      }
      enum "odg-no-st" {
        value 17;
        description
          "APS State Not Set";
      }
    }
    description
      "Odg aps states et";
  }

  typedef Prot-et {
    type enumeration {
      enum "no-state" {
        description
          "Not Present";
      }
      enum "active" {
        description
          "Active";
      }
      enum "active-tx" {
        description
          "Active tx";
      }
      enum "active-rx" {
        description
          "Active rx";
      }
      enum "not-active" {
        description
          "Not Active";
      }
      enum "failed" {
        description
          "Failed";
      }
      enum "extra" {
        description
          "Extra";
      }
      enum "unsupported" {
        description
          "Unsupported";
      }
    }
    description
      "Prot et";
  }

  typedef Odg-aps-mon-lvl {
    type enumeration {
      enum "odg-mon-pm" {
        value 0;
        description
          "Performance Monitoring";
      }
      enum "odg-tcm-1" {
        value 1;
        description
          "TCM 1";
      }
      enum "odg-tcm-2" {
        value 2;
        description
          "TCM 2";
      }
      enum "odg-tcm-3" {
        value 3;
        description
          "TCM 3";
      }
      enum "odg-tcm-4" {
        value 4;
        description
          "TCM 4";
      }
      enum "odg-tcm-5" {
        value 5;
        description
          "TCM 5";
      }
      enum "odg-tcm-6" {
        value 6;
        description
          "TCM 6";
      }
      enum "odg-mon-sm" {
        value 7;
        description
          "Section Monitoring";
      }
    }
    description
      "Odg aps mon lvl";
  }

  typedef Odg-revert-et {
    type enumeration {
      enum "non-rev" {
        value 0;
        description
          "Non Revertive";
      }
      enum "rev" {
        value 1;
        description
          "Revertive";
      }
    }
    description
      "Odg revert et";
  }

  typedef Odg-direction-et {
    type enumeration {
      enum "uni-dir" {
        value 0;
        description
          "Uni directional";
      }
      enum "bi-dir" {
        value 1;
        description
          "Bi directional";
      }
    }
    description
      "Odg direction et";
  }

  typedef Odg-aps-et {
    type enumeration {
      enum "noaps" {
        value 0;
        description
          "No Aps";
      }
      enum "with-aps" {
        value 1;
        description
          "With APS";
      }
    }
    description
      "Odg aps et";
  }

  typedef Brd-et {
    type enumeration {
      enum "b-1-1" {
        value 0;
        description
          "1+1";
      }
      enum "b-1-n" {
        value 1;
        description
          "1:N";
      }
    }
    description
      "Brd et";
  }

  typedef Req-st-et {
    type enumeration {
      enum "aps-nr" {
        value 0;
        description
          "No Request State";
      }
      enum "aps-dnr" {
        value 1;
        description
          "Do Not Revert State";
      }
      enum "aps-rr" {
        value 2;
        description
          "Reverse Request";
      }
      enum "aps-exer" {
        value 4;
        description
          "Exercise";
      }
      enum "aps-wtr" {
        value 6;
        description
          "Wait to Restore";
      }
      enum "aps-ms" {
        value 8;
        description
          "Manual Switch";
      }
      enum "aps-sd" {
        value 10;
        description
          "Signal Degrade";
      }
      enum "aps-sf" {
        value 12;
        description
          "Signal Failed";
      }
      enum "aps-low" {
        value 13;
        description
          "Lockout for Working";
      }
      enum "aps-fs" {
        value 14;
        description
          "Forced Switch";
      }
      enum "aps-lop" {
        value 15;
        description
          "Lockout for Protection";
      }
    }
    description
      "Req st et";
  }

  grouping ODG-ODU-EDM-ALARM {
    description
      " ODG ODU Alarm";
    leaf is-alarm-detected {
      type boolean;
      description
        "Flag to indicate if the alarm is detected";
    }
  }

  grouping ODG-ODU-ALARM-INFO {
    description
      "ODG ODU Alarm";
    container switched-to-restore {
      description
        "Switched To Restore";
      uses ODG-ODU-EDM-ALARM;
    }
    container switched-to-protection {
      description
        "Switched To Protection";
      uses ODG-ODU-EDM-ALARM;
    }
    container lockout-switch-request {
      description
        "Lockout Switch Request On Controller or
         Equipment or UPSR or SNC";
      uses ODG-ODU-EDM-ALARM;
    }
    container force-switch-request {
      description
        "Force Switch Request On Controller or Equipment
         or UPSR or SNC";
      uses ODG-ODU-EDM-ALARM;
    }
    container manual-switch-request {
      description
        "Manual Switch Request On Controller or Equipment
         or UPSR or SNC";
      uses ODG-ODU-EDM-ALARM;
    }
    container wait-to-restore {
      description
        "Wait To Restore";
      uses ODG-ODU-EDM-ALARM;
    }
    container failure-to-switch-to-protection {
      description
        "Failure To Switch To Protection";
      uses ODG-ODU-EDM-ALARM;
    }
  }

  grouping ODG-ODU-CHNL-ID {
    description
      "odg oduk chnl id";
    leaf slot {
      type int32;
      description
        "slot";
    }
    leaf port {
      type int32;
      description
        "port";
    }
    leaf id {
      type int32;
      description
        "id";
    }
  }

  grouping ODG-APS-CHNL-ID {
    description
      "odg aps chnl id";
    container id {
      description
        "channelID";
      uses ODG-ODU-CHNL-ID;
    }
    leaf rack {
      type int32;
      description
        "rack";
    }
    leaf slot {
      type int32;
      description
        "slot";
    }
    leaf instance {
      type int32;
      description
        "instance";
    }
    leaf port {
      type int32;
      description
        "port";
    }
    leaf dev {
      type int32;
      description
        "dev";
    }
    leaf mode {
      type int32;
      description
        "mode";
    }
    leaf x-flag {
      type int32;
      description
        "x flag";
    }
    leaf active-flag {
      type int32;
      description
        "active flag";
    }
    leaf odu-rate {
      type int32;
      description
        "OduRate";
    }
    leaf oduhandle {
      type int32;
      description
        "OduHandle";
    }
    leaf odu-name {
      type string;
      description
        "odu name";
    }
    leaf odustate {
      type Prot-et;
      description
        "odu state";
    }
    leaf local-failure {
      type int32;
      description
        "Local Failure";
    }
    leaf remote-failure {
      type int32;
      description
        "Remote Failure";
    }
    leaf wtr-left {
      type uint32;
      description
        "Wait to Restore Left Timer";
    }
  }

  grouping ODG-APS-PROV-INFO {
    description
      "odg aps prov info t";
    leaf aps {
      type Odg-aps-et;
      description
        "aps";
    }
    leaf bridge {
      type Brd-et;
      description
        "bridge";
    }
    leaf direction {
      type Odg-direction-et;
      description
        "direction";
    }
    leaf revertive {
      type Odg-revert-et;
      description
        "revertive";
    }
    leaf wait-to-restore {
      type int32;
      description
        "WaitToRestore";
    }
    leaf hold-off {
      type int32;
      description
        "HoldOffTimer";
    }
    leaf level {
      type Odg-aps-mon-lvl;
      description
        "ApsLevel";
    }
  }

  grouping ODG-APS-REQ-ST-PT {
    description
      "odg aps req st pt";
    leaf state {
      type Req-st-et;
      description
        "state";
    }
    leaf aps {
      type int32;
      description
        "aps";
    }
    leaf bridge {
      type Brd-et;
      description
        "bridge";
    }
    leaf direction {
      type int32;
      description
        "direction";
    }
    leaf revert {
      type int32;
      description
        "revertive";
    }
  }

  grouping ODG-APS-CHNL-CTX {
    description
      "channel contrext info";
    container request-protection {
      description
        "RequestProtection";
      uses ODG-APS-REQ-ST-PT;
    }
    leaf request-signal {
      type int32;
      description
        "RequestSignal";
    }
    leaf bridge-signal {
      type int32;
      description
        "BridgeSignal";
    }
    leaf response {
      type int32;
      description
        "response";
    }
    leaf role {
      type int32;
      description
        "OduRole";
    }
    leaf context-num {
      type int32;
      description
        "ContextNum";
    }
    leaf message-type {
      type int32;
      description
        "MessageType";
    }
    leaf event-type {
      type int32;
      description
        "EventType";
    }
  }

  grouping ODG-ODU-EDM-PORT-INFO {
    description
      "ODG ODU information";
    container near-channel {
      description
        "NearChannel";
      uses ODG-APS-CHNL-CTX;
    }
    container far-channel {
      description
        "FarChannel";
      uses ODG-APS-CHNL-CTX;
    }
    container provision-info {
      description
        "ProvisionInfo";
      uses ODG-APS-PROV-INFO;
    }
    container working-id {
      description
        "WorkingID";
      uses ODG-APS-CHNL-ID;
    }
    container protecting-id {
      description
        "ProtectingID";
      uses ODG-APS-CHNL-ID;
    }
    container restore-id {
      description
        "RestoreID";
      uses ODG-APS-CHNL-ID;
    }
    container fwd-id {
      description
        "FwdID";
      uses ODG-APS-CHNL-ID;
    }
    container alarm {
      description
        "Alarm";
      uses ODG-ODU-ALARM-INFO;
    }
    leaf aps-current-state {
      type Odg-aps-states-et;
      description
        "ApsCurrentState";
    }
    leaf prev-state {
      type Odg-aps-states-et;
      description
        "PreviousState";
    }
    leaf fault-type {
      type Fault-types-et;
      description
        "FaultType";
    }
    leaf node-use {
      type int32;
      description
        "node use";
    }
    leaf odg-id {
      type int32;
      description
        "odugroup id";
    }
    leaf odg-handle {
      type int32;
      description
        "odugroup handle";
    }
    leaf odg-fgid {
      type int32;
      description
        "odu group fgid";
    }
    leaf bmap-event {
      type int32;
      description
        "bitmap event";
    }
    leaf bmap-index {
      type int32;
      description
        "bitmap index";
    }
    leaf status-code {
      type int32;
      description
        "status code";
    }
  }
}
