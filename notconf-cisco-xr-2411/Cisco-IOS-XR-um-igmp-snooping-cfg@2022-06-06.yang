module Cisco-IOS-XR-um-igmp-snooping-cfg {
  namespace "http://cisco.com/ns/yang/Cisco-IOS-XR-um-igmp-snooping-cfg";
  prefix um-igmp-snooping-cfg;

  import Cisco-IOS-XR-types {
    prefix xr;
  }
  import ietf-inet-types {
    prefix inet;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR igmp-snooping package configuration.

     This YANG module augments the
     modules with configuration data.

     Copyright (c) 2022 by Cisco Systems, Inc.
     All rights reserved.";

  revision 2022-06-06 {
    semver:module-version "1.0.0";
    description
      "Added mrouter-forwarding, always/sync for topology-change and sync for process support";
  }
  revision 2022-02-02 {
    description
      "Initial release";
  }

  container igmp {
    description
      "IPv4 Address Family";
    container snooping {
      description
        "Enter IGMP snooping subcommands";
      container profiles {
        description
          "Enter IGMP snooping profile name";
        list profile {
          key "profile-name";
          description
            "Enter IGMP snooping profile name";
          leaf profile-name {
            type xr:Cisco-ios-xr-string {
              length "1..32" {
                description
                  "Profile name - maximum 32 characters";
              }
            }
            description
              "Enter IGMP snooping profile name";
          }
          leaf system-ip-address {
            type inet:ipv4-address-no-zone;
            description
              "Source address for generated IGMP messages";
          }
          leaf minimum-version {
            type uint32 {
              range "2..3" {
                description
                  "Enter minimum-version";
              }
            }
            description
              "Configure minimum IGMP version (default 2)";
          }
          container report-suppression {
            description
              "Minimize number of IGMP reports sent to mrouters";
            container disable {
              presence "Indicates a disable node is configured.";
              description
                "Disable report-suppression";
            }
          }
          container tcn {
            description
              "Configure behavior on topology change";
            container query {
              description
                "Require G-Query to expedite relearning";
              container solicit {
                presence "Indicates a solicit node is configured.";
                description
                  "Solicit a G-Query on topology change (default disabled)";
              }
            }
            container flood {
              description
                "Add all STP ports to all mroutes during topology change";
              container query {
                description
                  "tcn flood query";
                leaf count {
                  type uint32 {
                    range "1..10" {
                      description
                        "Enter tcn flood query count";
                    }
                  }
                  description
                    "Topology change complete after count G-Queries (default 2)";
                }
              }
              container disable {
                presence "Indicates a disable node is configured.";
                description
                  "Disable TCN flooding";
              }
            }
          }
          container router-alert-check {
            description
              "Check for IP RA Option in snooped IGMP messages";
            container disable {
              presence "Indicates a disable node is configured.";
              description
                "Disable router-alert-check";
            }
          }
          container ttl-check {
            description
              "Check TTL is 1 in snooped IGMP messages";
            container disable {
              presence "Indicates a disable node is configured.";
              description
                "Disable TTL checking";
            }
          }
          container internal-querier {
            presence "Indicates a internal-querier node is configured.";
            description
              "Configure the IGMP internal-querier";
            leaf max-response-time {
              type uint32 {
                range "1..25" {
                  description
                    "Enter max-response-time in seconds";
                }
              }
              description
                "IGMP G-Query MRT value (default 10)";
            }
            leaf query-interval {
              type uint32 {
                range "1..18000" {
                  description
                    "Enter query-interval in seconds";
                }
              }
              description
                "Time between periodic G-Queries (default 60)";
            }
            leaf robustness-variable {
              type uint32 {
                range "1..7" {
                  description
                    "Enter robustness-variable";
                }
              }
              description
                "IGMP robustness-variable (default 2)";
            }
            container tcn {
              description
                "Configure internal-querier behavior on topology change";
              container query {
                description
                  "Configure internal-querier tcn query";
                leaf count {
                  type uint32 {
                    range "0..7" {
                      description
                        "Enter tcn query count";
                    }
                  }
                  description
                    "Number of TCN G-Queries to send (default 2)";
                }
                leaf interval {
                  type uint32 {
                    range "1..18000" {
                      description
                        "Enter query interval in seconds";
                    }
                  }
                  description
                    "Time between TCN G-Queries (default 10)";
                }
                leaf max-response-time {
                  type uint32 {
                    range "1..25" {
                      description
                        "Enter max-response-time in seconds";
                    }
                  }
                  description
                    "IGMP G-Query MRT value (default Querier's MRT)";
                }
              }
            }
            container timer {
              description
                "Other querier present timer";
              leaf expiry {
                type uint32 {
                  range "60..300" {
                    description
                      "Enter timer expiry in seconds";
                  }
                }
                description
                  "timer expiry (default QQI*QRV+MRT/2)";
              }
            }
            leaf version {
              type uint32 {
                range "2..3" {
                  description
                    "Enter internal-querier version";
                }
              }
              description
                "IGMP version (default 3)";
            }
          }
          container querier {
            description
              "Configure IGMPv2 Querier information";
            leaf query-interval {
              type uint32 {
                range "1..18000" {
                  description
                    "Enter query-interval in seconds";
                }
              }
              description
                "Time between periodic G-Queries (default 60)";
            }
            leaf robustness-variable {
              type uint32 {
                range "1..7" {
                  description
                    "Enter robustness-variable";
                }
              }
              description
                "Querier robustness-variable (default 2)";
            }
          }
          container last-member-query {
            description
              "Configure last member query behavior";
            leaf interval {
              type uint32 {
                range "100..5000" {
                  description
                    "Enter last member query interval in milliseconds";
                }
              }
              description
                "Last member query interval (default 1000)";
            }
            leaf count {
              type uint32 {
                range "1..7" {
                  description
                    "Enter last member query count";
                }
              }
              description
                "Last member query count (default 2)";
            }
          }
          leaf unsolicited-report-interval {
            type uint32 {
              range "100..5000" {
                description
                  "Enter unsolicited-report-interval in milliseconds";
              }
            }
            description
              "Time between state-change reports (default 1000)";
          }
          container immediate-leave {
            presence "Indicates a immediate-leave node is configured.";
            description
              "Remove membership immediately on receipt of leave";
          }
          container mrouter {
            presence "Indicates a mrouter node is configured.";
            description
              "Configure a static mrouter on a port";
          }
          container mrouter-forwarding {
            description
              "Forward multicast to all mrouters";
            container disable {
              presence "Indicates a disable node is configured.";
              description
                "Disable mrouter forwarding";
            }
          }
          container router-guard {
            presence "Indicates a router-guard node is configured.";
            description
              "Prevent dynamic mrouter discovery on a port";
          }
          container static {
            description
              "Configure static group membership on a port";
            container group {
              description
                "Configure a static group";
              list ip-address {
                key "address";
                description
                  "Enter a valid multicast address";
                leaf address {
                  type inet:ipv4-address-no-zone;
                  description
                    "Enter a valid multicast address";
                }
              }
              container ip-src-addresses {
                description
                  "Enter a valid multicast address";
                list ip-address {
                  key "address";
                  description
                    "Enter a valid multicast address";
                  leaf address {
                    type inet:ipv4-address-no-zone;
                    description
                      "Enter a valid multicast address";
                  }
                  container source {
                    description
                      "Configure source address for static source-group";
                    list ip-address {
                      key "address";
                      description
                        "Enter a valid unicast ip address";
                      leaf address {
                        type inet:ipv4-address-no-zone;
                        description
                          "Enter a valid multicast address";
                      }
                    }
                  }
                }
              }
            }
          }
          leaf access-group {
            type xr:Cisco-ios-xr-string {
              length "1..32" {
                description
                  "Enter access-list name";
              }
            }
            description
              "Configure group membership filter";
          }
          container group {
            description
              "Configure group membership limits";
            leaf limit {
              type uint32 {
                range "0..65535" {
                  description
                    "Enter group limit";
                }
              }
              description
                "Limit the number of groups or source-groups allowed on a port";
            }
            leaf threshold {
              type uint32 {
                range "0..65535" {
                  description
                    "Enter threshold value";
                }
              }
              must "../limit";
              description
                "Specify group threshold value for the port ";
            }
            leaf policy {
              type xr:Cisco-ios-xr-string {
                length "1..256" {
                  description
                    "Enter route-policy name";
                }
              }
              description
                "Specify a route-policy to set the group weight";
            }
          }
          container startup {
            description
              "Configure startup behavior";
            container query {
              description
                "Configure startup query behavior";
              leaf count {
                type uint32 {
                  range "0..7" {
                    description
                      "Enter startup query count";
                  }
                }
                description
                  "Number of G-Queries to send (default 2)";
              }
              leaf interval {
                type uint32 {
                  range "1..18000" {
                    description
                      "Enter query interval in seconds";
                  }
                }
                description
                  "Time between Startup G-Queries (default 10)";
              }
              leaf max-response-time {
                type uint32 {
                  range "1..25" {
                    description
                      "Enter max-response-time in seconds";
                  }
                }
                description
                  "IGMP G-Query MRT value (default Querier's MRT)";
              }
              container port-up {
                description
                  "Startup query behavior when port goes up";
                container disable {
                  presence "Indicates a disable node is configured.";
                  description
                    "Disable startup queries on port-up";
                }
              }
              container iccp-group {
                description
                  "Startup query behavior for iccp-group";
                container port-active {
                  presence "Indicates a port-active node is configured.";
                  description
                    "Issue startup queries when iccp-group goes active";
                }
              }
              container topology-change {
                presence "Indicates a topology-change node is configured.";
                description
                  "Issue startup queries on topology_change";
              }
              container topology-change-always {
                presence "Indicates a topology-change always node is configured.";
                description
                  "Send g-queries on topology-change even when not STP root";
              }
              container topology-change-sync {
                presence "Indicates a topology-change sync node is configured.";
                description
                  "Remove unrefreshed membership state";
              }
              container process {
                description
                  "Issue startup queries on process event";
                container start {
                  presence "Indicates a start node is configured.";
                  description
                    "Issue startup queries on process start";
                }
                container start-sync {
                  presence "Indicates a sync node is configured.";
                  description
                    "Remove unrefreshed membership state";
                }
              }
            }
          }
          container redundancy {
            description
              "Configure redundancy";
            container iccp-group {
              description
                "Configure redundancy iccp-group behavior";
              container report-standby-state {
                description
                  "Report standby port membership";
                container disable {
                  presence "Indicates a disable node is configured.";
                  description
                    "Disable reporting";
                }
              }
            }
          }
          container default-bridge-domain {
            description
              "Configure this as default profile for L2VPN BDs";
            container all {
              description
                "All types of bridge-domain";
              container enable {
                presence "Indicates a enable node is configured.";
                description
                  "Enable this profile";
              }
            }
          }
        }
      }
    }
  }
}
