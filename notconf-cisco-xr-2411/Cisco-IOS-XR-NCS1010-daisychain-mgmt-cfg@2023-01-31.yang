module Cisco-IOS-XR-NCS1010-daisychain-mgmt-cfg {
  namespace "http://cisco.com/ns/yang/Cisco-IOS-XR-NCS1010-daisychain-mgmt-cfg";
  prefix ncs1010-daisychain-mgmt-cfg;

  import cisco-semver {
    prefix semver;
  }
  import Cisco-IOS-XR-ifmgr-cfg {
    prefix a1;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR NCS1010-daisychain-mgmt package configuration.

     This YANG module augments the
       Cisco-IOS-XR-ifmgr-cfg
     module with configuration data.

     Copyright (c) 2013-2023 by Cisco Systems, Inc.
     All rights reserved.";

  revision 2023-01-31 {
    semver:module-version "1.0.0";
    description
      "Daisy chain mgmt interface cfg";
  }
  revision 2019-04-05 {
    description
      "Establish semantic version baseline.";
  }
  revision 2015-11-09 {
    description
      "IOS XR 6.0 revision.";
  }

  augment "/a1:interface-configurations/a1:interface-configuration" {
    description
      "This augment extends the configuration data of
       'Cisco-IOS-XR-ifmgr-cfg'";
    leaf bridge-port-interface {
      type string;
      description
        "Enable bridge-port routed-interface";
    }
  }
}
