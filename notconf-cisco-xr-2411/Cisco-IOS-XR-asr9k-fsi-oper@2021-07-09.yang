module Cisco-IOS-XR-asr9k-fsi-oper {
  namespace "http://cisco.com/ns/yang/Cisco-IOS-XR-asr9k-fsi-oper";
  prefix asr9k-fsi-oper;

  import Cisco-IOS-XR-types {
    prefix xr;
  }
  import cisco-semver {
    prefix semver;
  }

  include Cisco-IOS-XR-asr9k-fsi-oper-sub1 {
    revision-date 2021-07-09;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR asr9k-fsi package operational data.

     This module contains definitions
     for the following management objects:
       fabric-stats: Fabric stats operational data

     Copyright (c) 2013-2021 by Cisco Systems, Inc.
     All rights reserved.";

  revision 2021-07-09 {
    semver:module-version "2.0.0";
    description
      "Add support to FabricStats to query stats by the counter-name";
  }
  revision 2020-02-14 {
    semver:module-version "1.0.0";
    description
      "Support for generic show counters";
  }
  revision 2019-04-05 {
    description
      "Establish semantic version baseline.";
  }
  revision 2015-11-09 {
    description
      "IOS XR 6.0 revision.";
  }

  container fabric-stats {
    config false;
    description
      "Fabric stats operational data";
    container nodes {
      description
        "Table of Nodes";
      list node {
        key "node-name";
        description
          "Information about a particular node";
        container statses {
          description
            "Table of stats information";
          list stats {
            key "type";
            description
              "Stats information for a particular type";
            container stats-array {
              description
                "Stats information for a particular counter
                 type";
              uses FSI-SHOW-GENERIC-STATS;
            }
            container counter-names {
              description
                "Counter List information for a particular
                 Stats ";
              list counter-name {
                key "type";
                description
                  "Counter Name from the list counters";
                container counter {
                  description
                    "Counter information for a particular
                     counter name";
                  uses FSI-SHOW-COUNTER-STATS;
                }
                leaf type {
                  type xr:Cisco-ios-xr-string;
                  description
                    "Counter asic type";
                }
              }
            }
            leaf type {
              type xr:Cisco-ios-xr-string;
              description
                "Fabric asic type";
            }
          }
        }
        leaf node-name {
          type xr:Node-id;
          description
            "Node name";
        }
      }
    }
  }
}
