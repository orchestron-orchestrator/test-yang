module Cisco-IOS-XR-um-gnss-receiver-cfg {
  namespace "http://cisco.com/ns/yang/Cisco-IOS-XR-um-gnss-receiver-cfg";
  prefix um-gnss-receiver-cfg;

  import Cisco-IOS-XR-um-location-cfg {
    prefix location;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR gnss-receiver package configuration.

     This YANG module augments the
     modules with configuration data.

     Copyright (c) 2021-2022 by Cisco Systems, Inc.
     All rights reserved.";

  revision 2022-07-11 {
    semver:module-version "1.1.0";
    description
      "Added missing description statement to nodes";
  }
  revision 2021-10-19 {
    semver:module-version "1.0.0";
    description
      "Initial release";
  }

  typedef Fsync-ql-option {
    type enumeration {
      enum "option-1" {
        value 1;
        description
          "ITU-T Option 1";
      }
      enum "option-2,-generation-1" {
        value 2;
        description
          "ITU-T Option 2, Generation 1";
      }
      enum "option-2,-generation-2" {
        value 3;
        description
          "ITU-T Option 2, Generation 2";
      }
    }
    description
      "Fsync ql option";
  }

  typedef Fsync-ql-value {
    type enumeration {
      enum "dnu" {
        value 1;
        description
          "This signal should not be used for
           synchronization";
      }
      enum "o1-e-prtc" {
        value 20;
        description
          "ITU-T Option 1: Enhanced primary reference
           timing clock";
      }
      enum "o1-prtc" {
        value 21;
        description
          "ITU-T Option 1: Primary reference timing clock";
      }
      enum "o1-prc" {
        value 22;
        description
          "ITU-T Option 1: Primary reference clock";
      }
      enum "o1-ssu-a" {
        value 23;
        description
          "ITU-T Option 1: Type I or V subordinate clock";
      }
      enum "o1-ssu-b" {
        value 24;
        description
          "ITU-T Option 1: Type IV subordinate clock";
      }
      enum "o1-e-eec" {
        value 25;
        description
          "ITU-T Option 1: Enhanced ethernet equipment
           clock";
      }
      enum "o1-eec1" {
        value 26;
        description
          "ITU-T Option 1: Ethernet equipment clock";
      }
      enum "o1-sec" {
        value 27;
        description
          "ITU-T Option 1: SONET equipment clock";
      }
      enum "o1-e-prc" {
        value 28;
        description
          "ITU-T Option 1: Enhanced primary reference
           clock";
      }
      enum "o2-g1-e-prtc" {
        value 40;
        description
          "ITU-T Option 2, Generation 1: Enhanced primary
           reference timing clock";
      }
      enum "o2-g1-prtc" {
        value 41;
        description
          "ITU-T Option 2, Generation 1: Primary reference
           timing clock";
      }
      enum "o2-g1-prs" {
        value 42;
        description
          "ITU-T Option 2, Generation 1: Primary reference
           source";
      }
      enum "o2-g1-stu" {
        value 43;
        description
          "ITU-T Option 2, Generation 1: Synchronized -
           traceability unknown";
      }
      enum "o2-g1-st2" {
        value 44;
        description
          "ITU-T Option 2, Generation 1: Stratum 2";
      }
      enum "o2-g1-st3" {
        value 45;
        description
          "ITU-T Option 2, Generation 1: Stratum 3";
      }
      enum "o2-g1-e-eec" {
        value 46;
        description
          "ITU-T Option 2, Generation 1: Enhanced ethernet
           equipment clock";
      }
      enum "o2-g1-eec2" {
        value 47;
        description
          "ITU-T Option 2, Generation 1: Ethernet
           equipment clock";
      }
      enum "o2-g1-smc" {
        value 48;
        description
          "ITU-T Option 2, Generation 1: SONET clock self
           timed";
      }
      enum "o2-g1-st4" {
        value 49;
        description
          "ITU-T Option 2, Generation 1: Stratum 4 freerun";
      }
      enum "o2-g1-e-prc" {
        value 51;
        description
          "ITU-T Option 2, Generation 1: Enhanced primary
           reference clock";
      }
      enum "o2-g2-e-prtc" {
        value 60;
        description
          "ITU-T Option 2, Generation 2: Enhanced primary
           reference timing clock";
      }
      enum "o2-g2-prtc" {
        value 61;
        description
          "ITU-T Option 2, Generation 2: Primary reference
           timing clock";
      }
      enum "o2-g2-prs" {
        value 62;
        description
          "ITU-T Option 2, Generation 2: Primary reference
           source";
      }
      enum "o2-g2-stu" {
        value 63;
        description
          "ITU-T Option 2, Generation 2: Synchronized -
           traceability unknown";
      }
      enum "o2-g2-st2" {
        value 64;
        description
          "ITU-T Option 2, Generation 2: Stratum 2";
      }
      enum "o2-g2-tnc" {
        value 65;
        description
          "ITU-T Option 2, Generation 2: Transit node
           clock";
      }
      enum "o2-g2-st3e" {
        value 66;
        description
          "ITU-T Option 2, Generation 2: Stratum 3E";
      }
      enum "o2-g2-st3" {
        value 67;
        description
          "ITU-T Option 2, Generation 2: Stratum 3";
      }
      enum "o2-g2-e-eec" {
        value 68;
        description
          "ITU-T Option 2, Generation 2: Enhanced ethernet
           equipment clock";
      }
      enum "o2-g2-eec2" {
        value 69;
        description
          "ITU-T Option 2, Generation 2: Ethernet
           equipment clock";
      }
      enum "o2-g2-smc" {
        value 70;
        description
          "ITU-T Option 2, Generation 2: SONET clock self
           timed";
      }
      enum "o2-g2-st4" {
        value 71;
        description
          "ITU-T Option 2, Generation 2: Stratum 4 freerun";
      }
      enum "o2-g2-e-prc" {
        value 73;
        description
          "ITU-T Option 2, Generation 2: Enhanced primary
           reference clock";
      }
    }
    description
      "Fsync ql value";
  }

  grouping LOCATION-BODY {
    description
      "Grouping for location";
    container gnss-receivers {
      description
        "GNSS receiver configuration commands";
      list gnss-receiver {
        key "gnss-receiver-id";
        description
          "GNSS receiver configuration commands";
        leaf gnss-receiver-id {
          type uint32 {
            range "0..4294967295" {
              description
                "GNSS receiver number";
            }
          }
          description
            "GNSS receiver configuration commands";
        }
        container frequency {
          description
            "Frequency Synchronization configuration";
          container synchronization {
            description
              "Frequency Synchronization configuration";
            container ssm {
              description
                "SSM configuration commands";
              container disable {
                presence "Indicates a disable node is configured.";
                description
                  "Disable sending of SSMs";
              }
            }
            leaf priority {
              type uint32 {
                range "1..254" {
                  description
                    "Source priority";
                }
              }
              description
                "Source priority";
            }
            leaf time-of-day-priority {
              type uint32 {
                range "1..254" {
                  description
                    "Source time-of-day priority";
                }
              }
              description
                "Source time-of-day priority";
            }
            container quality {
              description
                "Quality level configuration";
              container transmit {
                description
                  "Set the quality level to be transmitted";
                leaf quality-level-option {
                  type Fsync-ql-option;
                  must "../exact-quality-level-value or ../min-quality-level-value or ../max-quality-level-value or (../min-quality-level-value and ../max-quality-level-value)";
                  description
                    "Quality level option";
                }
                leaf exact-quality-level-value {
                  type Fsync-ql-value;
                  must "../quality-level-option and not(../min-quality-level-value or ../max-quality-level-value)";
                  description
                    "Exact quality level value";
                }
                leaf min-quality-level-value {
                  type Fsync-ql-value;
                  must "../quality-level-option and not(../exact-quality-level-value)";
                  description
                    "Minimum quality level value";
                }
                leaf max-quality-level-value {
                  type Fsync-ql-value;
                  must "../quality-level-option and not(../exact-quality-level-value)";
                  description
                    "Maximum quality level value";
                }
              }
              container receive {
                description
                  "Adjust the received quality level";
                leaf quality-level-option {
                  type Fsync-ql-option;
                  must "../exact-quality-level-value or ../min-quality-level-value or ../max-quality-level-value or (../min-quality-level-value and ../max-quality-level-value)";
                  description
                    "Quality level option";
                }
                leaf exact-quality-level-value {
                  type Fsync-ql-value;
                  must "../quality-level-option and not(../min-quality-level-value or ../max-quality-level-value)";
                  description
                    "Exact quality level value";
                }
                leaf min-quality-level-value {
                  type Fsync-ql-value;
                  must "../quality-level-option and not(../exact-quality-level-value)";
                  description
                    "Minimum quality level value";
                }
                leaf max-quality-level-value {
                  type Fsync-ql-value;
                  must "../quality-level-option and not(../exact-quality-level-value)";
                  description
                    "Maximum quality level value";
                }
              }
            }
            leaf wait-to-restore {
              type uint32 {
                range "0..12" {
                  description
                    "Wait-to-restore time, in minutes";
                }
              }
              description
                "Set the wait-to-restore time";
            }
            container selection {
              description
                "Selection configuration commands";
              container input {
                presence "Indicates a input node is configured.";
                description
                  "Enable this source for selection";
              }
            }
          }
        }
        container shutdown {
          presence "Indicates a shutdown node is configured.";
          description
            "Shutdown the GNSS receiver";
        }
        container anti-jam {
          description
            "Anti-jam mode configuration";
          container disable {
            presence "Indicates a disable node is configured.";
            description
              "Disable anti-jam mode";
          }
        }
        container constellation {
          description
            "Constellation configuration";
          container auto {
            must
              "not(../gps or ../galileo
               or ../beidou or ../qzss
               or ../glonass or ../sbas
               or ../irnss)";
            presence "Indicates a auto node is configured.";
            description
              "Auto-select the constellation";
          }
          container gps {
            must
              "not(../auto or ../galileo
               or ../beidou or ../qzss
               or ../glonass or ../sbas
               or ../irnss)";
            presence "Indicates a gps node is configured.";
            description
              "GPS";
          }
          container galileo {
            must
              "not(../auto or ../gps
               or ../beidou or ../qzss
               or ../glonass or ../sbas
               or ../irnss)";
            presence "Indicates a galileo node is configured.";
            description
              "Galileo";
          }
          container beidou {
            must
              "not(../auto or ../gps
               or ../galileo or ../qzss
               or ../glonass or ../sbas
               or ../irnss)";
            presence "Indicates a beidou node is configured.";
            description
              "Beidou";
          }
          container qzss {
            must
              "not(../auto or ../gps
               or ../galileo or ../beidou
               or ../glonass or ../sbas
               or ../irnss)";
            presence "Indicates a qzss node is configured.";
            description
              "QZSS";
          }
          container glonass {
            must
              "not(../auto or ../gps
               or ../galileo or ../beidou
               or ../qzss or ../sbas
               or ../irnss)";
            presence "Indicates a glonass node is configured.";
            description
              "GLONASS";
          }
          container sbas {
            must
              "not(../auto or ../gps
               or ../galileo or ../beidou
               or ../qzss or ../glonass
               or ../irnss)";
            presence "Indicates a sbas node is configured.";
            description
              "SBAS (WAAS)";
          }
          container irnss {
            must
              "not(../auto or ../gps
               or ../galileo or ../beidou
               or ../qzss or ../glonass
               or ../sbas)";
            presence "Indicates a irnss node is configured.";
            description
              "IRNSS";
          }
        }
        container snr {
          description
            "SNR threshold configuration";
          leaf threshold {
            type uint32 {
              range "0..40" {
                description
                  "SNR threshold value, in dB-Hz";
              }
            }
            description
              "SNR threshold configuration";
          }
        }
        container elevation {
          description
            "Elevation threshold configuration";
          leaf threshold {
            type uint32 {
              range "0..40" {
                description
                  "Elevation threshold value, in degrees";
              }
            }
            description
              "Elevation threshold configuration";
          }
        }
        container pdop {
          description
            "PDOP threshold configuration";
          leaf threshold {
            type uint32 {
              range "0..10" {
                description
                  "PDOP threshold value";
              }
            }
            description
              "PDOP threshold configuration";
          }
        }
        container traim {
          description
            "TRAIM threshold configuration";
          leaf threshold {
            type uint32 {
              range "0..2" {
                description
                  "TRAIM threshold value, in microseconds";
              }
            }
            description
              "TRAIM threshold configuration";
          }
        }
        container cable-delay {
          description
            "Cable-delay compensation configuration";
          leaf compensation {
            type int32 {
              range "-1000000..1000000" {
                description
                  "Cable-delay compensation value, in nanoseconds";
              }
            }
            description
              "Cable-delay compensation configuration";
          }
        }
        container onepps {
          description
            "1PPS polarity configuration";
          container polarity {
            description
              "1PPS polarity configuration";
            container positive {
              must "not(../negative)";
              presence "Indicates a positive node is configured.";
              description
                "Positive 1PPS polarity";
            }
            container negative {
              must "not(../positive)";
              presence "Indicates a negative node is configured.";
              description
                "Negative 1PPD polarity";
            }
          }
        }
      }
    }
  }

  augment "/location:locations/location:location" {
    description
      "This augment extends active nodes configuration";
    uses LOCATION-BODY;
  }
  augment "/location:locations/location:preconfigured-location" {
    description
      "This augment extends preconfigured nodes
       configuration";
    uses LOCATION-BODY;
  }
}
