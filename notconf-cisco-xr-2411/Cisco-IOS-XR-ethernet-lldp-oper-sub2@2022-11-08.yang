submodule Cisco-IOS-XR-ethernet-lldp-oper-sub2 {
  belongs-to Cisco-IOS-XR-ethernet-lldp-oper {
    prefix Cisco-IOS-XR-ethernet-lldp-oper;
  }

  import Cisco-IOS-XR-types {
    prefix xr;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR ethernet-lldp package operational data.

     Copyright (c) 2013-2022 by Cisco Systems, Inc.
     All rights reserved.";

  revision 2022-11-08 {
    semver:module-version "1.2.0";
    description
      "Added system-description field
       2022-04-01
         Added last clear time and transmit failure fields
       2022-03-01
         Added interface stats fields";
  }
  revision 2020-09-01 {
    semver:module-version "1.1.0";
    description
      "Fixing backward compatibility error in module.";
  }
  revision 2019-04-05 {
    semver:module-version "1.0.1";
    description
      "Establish semantic version baseline.";
  }
  revision 2017-11-13 {
    description
      "Added a new notification.";
  }
  revision 2015-11-09 {
    description
      "IOS XR 6.0 revision.";
  }

  grouping LLDP-MGR-GLOBAL-INFO {
    description
      "LLDP global info";
    leaf chassis-id {
      xr:event-telemetry "Subscribe Telemetry Event";
      type string;
      description
        "Chassis identifier";
    }
    leaf chassis-id-sub-type {
      xr:event-telemetry "Subscribe Telemetry Event";
      type uint8;
      description
        "Chassis ID sub type";
    }
    leaf system-name {
      xr:event-telemetry "Subscribe Telemetry Event";
      type string;
      description
        "System Name";
    }
    leaf timer {
      xr:event-telemetry "Subscribe Telemetry Event";
      type uint32;
      description
        "Rate at which LLDP packets re sent (in sec)";
    }
    leaf hold-time {
      xr:event-telemetry "Subscribe Telemetry Event";
      type uint32;
      description
        "Length  of time  (in sec)that receiver must keep
         thispacket";
    }
    leaf re-init {
      xr:event-telemetry "Subscribe Telemetry Event";
      type uint32;
      description
        "Delay (in sec) for LLDPinitialization on
         anyinterface";
    }
    leaf system-description {
      xr:event-telemetry "Subscribe Telemetry Event";
      type string;
      description
        "System Description";
    }
  }
}
