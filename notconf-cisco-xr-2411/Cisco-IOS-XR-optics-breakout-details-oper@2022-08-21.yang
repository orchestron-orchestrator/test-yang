module Cisco-IOS-XR-optics-breakout-details-oper {
  namespace "http://cisco.com/ns/yang/Cisco-IOS-XR-optics-breakout-details-oper";
  prefix optics-breakout-details-oper;

  import Cisco-IOS-XR-types {
    prefix xr;
  }
  import cisco-semver {
    prefix semver;
  }

  include Cisco-IOS-XR-optics-breakout-details-oper-sub1 {
    revision-date 2022-08-21;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR optics-breakout-details package operational data.

     This module contains definitions
     for the following management objects:
       optics-breakout-details: Optics Breakout Details

     Copyright (c) 2013-2022 by Cisco Systems, Inc.
     All rights reserved.";

  revision 2022-08-21 {
    semver:module-version "1.0.0";
    description
      "Schema added.";
  }
  revision 2019-04-05 {
    description
      "Establish semantic version baseline.";
  }
  revision 2015-11-09 {
    description
      "IOS XR 6.0 revision.";
  }

  container optics-breakout-details {
    config false;
    description
      "Optics Breakout Details";
    container controllers {
      description
        "Optics driver optics controller Table";
      list controller {
        key "controller-name";
        description
          "Optics Controller Name";
        leaf controller-name {
          type xr:Interface-name;
          description
            "Controller name";
        }
        uses BREAKOUT-DETAILS-OP;
      }
    }
  }
}
