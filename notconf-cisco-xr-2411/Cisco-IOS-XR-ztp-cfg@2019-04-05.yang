module Cisco-IOS-XR-ztp-cfg {
  namespace "http://cisco.com/ns/yang/Cisco-IOS-XR-ztp-cfg";
  prefix ztp-cfg;

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ztp package configuration.

     This module contains definitions
     for the following management objects:
       ztp: ZTP configuration data

     Copyright (c) 2013-2019 by Cisco Systems, Inc.
     All rights reserved.";

  revision 2019-04-05 {
    semver:module-version "1.0.0";
    description
      "Establish semantic version baseline.";
  }
  revision 2015-11-09 {
    description
      "IOS XR 6.0 revision.";
  }

  container ztp {
    description
      "ZTP configuration data";
    leaf usb-boot {
      type empty;
      description
        "Enable ZTP USB boot";
    }
  }
}
