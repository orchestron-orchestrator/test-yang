module Cisco-IOS-XR-sysadmin-show-bmc {
  namespace "http://www.cisco.com/ns/yang/Cisco-IOS-XR-sysadmin-show-bmc";
  prefix show_bmc;

  import cisco-semver {
    prefix semver;
  }

  organization
    "Cisco Systems Inc.";
  contact
    "Cisco Systems, Inc.
     Customer Service

     Postal: 170 West Tasman Drive
     San Jose, CA 95134

     Tel: +1 800 553-NETS

     E-mail: cs-yang@cisco.com";
  description
    "This module contains a collection of YANG
     definitions for Cisco IOS-XR SysAdmin configuration.

     This module holds bmc data for chassis.

     Copyright (c) 2012-2020 by Cisco Systems, Inc.
     All rights reserved.";

  revision 2021-02-02 {
    semver:module-version "2.0.0";
    description
      "Initial revision of show bmc commands";
  }

  grouping bmc-brief-oper-group {
    container brief {
      list chassis_serial {
        key "serial_number";
        leaf serial_number {
          type string;
        }
        container brief-data {
          leaf racknum {
            type string;
          }
          leaf ip_address {
            type string;
          }
        }
      }
    }
  }

  container bmc {
    config false;
    uses bmc-brief-oper-group;
  }
}
