module Cisco-IOS-XR-procfind-oper {
  namespace "http://cisco.com/ns/yang/Cisco-IOS-XR-procfind-oper";
  prefix procfind-oper;

  import Cisco-IOS-XR-types {
    prefix xr;
  }
  import cisco-semver {
    prefix semver;
  }

  include Cisco-IOS-XR-procfind-oper-sub1 {
    revision-date 2023-06-13;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR procfind package operational data.

     This module contains definitions
     for the following management objects:
       proc-distribution: Process distribution information

     Copyright (c) 2013-2023 by Cisco Systems, Inc.
     All rights reserved.";

  revision 2023-06-13 {
    semver:module-version "3.0.0";
    description
      "Added good description renamed the PID container to ProcessInfo container.";
  }
  revision 2020-02-28 {
    semver:module-version "2.0.0";
    description
      "Added new field PID in schema.";
  }
  revision 2019-04-05 {
    semver:module-version "1.0.1";
    description
      "Establish semantic version baseline.";
  }
  revision 2019-02-18 {
    description
      "Added good description for bag fields.";
  }
  revision 2015-11-09 {
    description
      "IOS XR 6.0 revision.";
  }

  container proc-distribution {
    config false;
    description
      "Process distribution information";
    container nodes {
      description
        "List of nodes";
      list node {
        key "node-name";
        description
          "Process distribution information per node";
        leaf node-name {
          type xr:Node-id;
          description
            "The node name";
        }
        list process {
          key "proc-name";
          description
            "Process distribution information";
          leaf proc-name {
            type xr:Cisco-ios-xr-string {
              length "1..256";
            }
            description
              "Process Name";
          }
          list process-info {
            key "process-info";
            description
              "Process distribution information";
            container filter-type {
              description
                "Process distribution information";
              uses PROCFIND-PROC;
            }
            leaf process-info {
              type xr:Cisco-ios-xr-string {
                length "1..32";
              }
              description
                "ProcessInfo";
            }
          }
        }
      }
    }
  }
}
