module Cisco-IOS-XR-lpts-ifib-act {
  namespace "http://cisco.com/ns/yang/Cisco-IOS-XR-lpts-ifib-act";
  prefix lpts-ifib-act;

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR action package configuration.

     Copyright (c) 2016-2020 by Cisco Systems, Inc.
     All rights reserved.";

  revision 2020-09-20 {
    semver:module-version "1.0.0";
    description
      "Initial revision.";
  }

  rpc clear-lpts-ifib-statistics-location {
    description
      "Clear lpts ifib stats location";

    input {
      leaf node-location {
        type string;
        description
          "Node location";
      }
    }
  }
  rpc clear-lpts-ifib-times-location {
    description
      "Clear ifib times location";

    input {
      leaf node-location {
        type string;
        mandatory true;
        description
          "Node location";
      }
    }
  }
}
