module Cisco-IOS-XR-um-traps-flash-cfg {
  namespace "http://cisco.com/ns/yang/Cisco-IOS-XR-um-traps-flash-cfg";
  prefix um-traps-flash-cfg;

  import Cisco-IOS-XR-um-snmp-server-cfg {
    prefix a1;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR traps-flash package configuration.

     This YANG module augments the
     modules with configuration data.

     Copyright (c) 2020-2022 by Cisco Systems, Inc.
     All rights reserved.";

  revision 2022-07-11 {
    semver:module-version "1.0.0";
    description
      "Added missing description statement to nodes";
  }
  revision 2020-04-24 {
    semver:module-version "1.0.0";
    description
      "Initial release";
  }

  augment "/a1:snmp-server/a1:traps" {
    description
      "This augment extends snmp-server traps nodes
       configuration";
    container flash {
      description
        "Enable  flash-mib traps";
      container insertion {
        presence "Indicates a insertion node is configured.";
        description
          "Enable ciscoFlashDeviceInsertedNotif";
      }
      container removal {
        presence "Indicates a removal node is configured.";
        description
          "Enable ciscoFlashDeviceRemovedNotif";
      }
    }
  }
}
