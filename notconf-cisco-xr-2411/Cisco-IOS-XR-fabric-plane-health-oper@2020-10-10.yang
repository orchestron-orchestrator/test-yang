module Cisco-IOS-XR-fabric-plane-health-oper {
  namespace "http://cisco.com/ns/yang/Cisco-IOS-XR-fabric-plane-health-oper";
  prefix fabric-plane-health-oper;

  import cisco-semver {
    prefix semver;
  }

  include Cisco-IOS-XR-fabric-plane-health-oper-sub1 {
    revision-date 2020-10-10;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR fabric-plane-health package operational data.

     This module contains definitions
     for the following management objects:
       fabric: Fabric Data

     Copyright (c) 2013-2020 by Cisco Systems, Inc.
     All rights reserved.";

  revision 2020-10-10 {
    semver:module-version "1.0.0";
    description
      "Yang Schema some leaf nodes type changed to prevent memory leak.";
  }
  revision 2020-06-26 {
    description
      "Yang Schema added with task-name.";
  }
  revision 2019-04-05 {
    description
      "Establish semantic version baseline.";
  }
  revision 2015-11-09 {
    description
      "IOS XR 6.0 revision.";
  }

  container fabric {
    config false;
    description
      "Fabric Data";
    container fabric-plane-ids {
      description
        "Fabric Plane data for available planes";
      list fabric-plane-id {
        key "fabric-plane-key";
        description
          "Filter Fabric Plane data for specific plane";
        container fabric-plane-info {
          description
            "Fabric Plane info for specific plane";
          uses FSDBAGG-EDM-PLANE-INFO;
        }
        container fabric-plane-stats {
          description
            "Fabric Plane statistics for specific plane";
          uses FSDBAGG-EDM-PLANE-STATS;
        }
        leaf fabric-plane-key {
          type uint32;
          description
            "Plane Number";
        }
      }
    }
    container fabric-health {
      description
        "Fabric Health Data";
      uses FSDBAGG-EDM-FABRIC-HEALTH;
    }
  }
}
