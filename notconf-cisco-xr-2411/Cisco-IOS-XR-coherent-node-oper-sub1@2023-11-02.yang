submodule Cisco-IOS-XR-coherent-node-oper-sub1 {
  belongs-to Cisco-IOS-XR-coherent-node-oper {
    prefix Cisco-IOS-XR-coherent-node-oper;
  }

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR coherent-node package operational data.

     Copyright (c) 2013-2023 by Cisco Systems, Inc.
     All rights reserved.";

  revision 2023-11-02 {
    semver:module-version "1.1.0";
    description
      "Added a leaf optics subtype
       2023-05-29
         Increase in interface name length";
  }
  revision 2019-04-05 {
    semver:module-version "1.0.0";
    description
      "Establish semantic version baseline.";
  }
  revision 2015-11-09 {
    description
      "IOS XR 6.0 revision.";
  }

  grouping COH-ETH-INTERFACE-DATA {
    description
      "Hundredgig interface data";
    leaf ifname {
      type string {
        length "0..80";
      }
      description
        "ifname";
    }
    leaf intf-handle {
      type string {
        length "0..128";
      }
      description
        "intf handle";
    }
    leaf admin-state {
      type string {
        length "0..128";
      }
      description
        "admin state";
    }
    leaf admin-up {
      type boolean;
      description
        "admin up";
    }
    leaf is-created {
      type boolean;
      description
        "is created";
    }
  }

  grouping COH-ETH-INTERFACE-INFO {
    description
      "Hundredgig interface info";
    list eth-data {
      description
        "eth data";
      uses COH-ETH-INTERFACE-DATA;
    }
  }

  grouping COH-PLUGGABLE-INFO {
    description
      "Coherent pluggable information";
    leaf deviation {
      type string {
        length "0..17";
      }
      description
        "deviation";
    }
    leaf part-number {
      type string {
        length "0..17";
      }
      description
        "part number";
    }
    leaf serial-number {
      type string {
        length "0..12";
      }
      description
        "serial number";
    }
    leaf date-code-number {
      type string {
        length "0..9";
      }
      description
        "date code number";
    }
    leaf clei-code-number {
      type string {
        length "0..11";
      }
      description
        "CLEI code number";
    }
    leaf vendorname {
      type string {
        length "0..17";
      }
      description
        "vendorname";
    }
    leaf description {
      type string {
        length "0..65";
      }
      description
        "description";
    }
    leaf pid {
      type string {
        length "0..19";
      }
      description
        "pid";
    }
    leaf vid {
      type string {
        length "0..5";
      }
      description
        "vid";
    }
    leaf module-hardware-version-number {
      type string {
        length "0..16";
      }
      description
        "module hardware version number";
    }
    leaf module-firmware-running-version-number {
      type string {
        length "0..16";
      }
      description
        "module firmware running version number";
    }
    leaf module-firmware-committed-version-number {
      type string {
        length "0..16";
      }
      description
        "module firmware committed version number";
    }
    leaf ctp-type {
      type uint32;
      description
        "ctp type";
    }
    leaf optics-subtype {
      type uint32;
      description
        "Coherent Optics Subtype";
    }
  }

  grouping COH-PORT-DATA {
    description
      "Coherent front panel port data";
    container ctp-info {
      description
        "ctp info";
      uses COH-PLUGGABLE-INFO;
    }
    container interface-info {
      description
        "interface info";
      uses COH-ETH-INTERFACE-INFO;
    }
    leaf rsip {
      type uint32;
      description
        "rsip";
    }
    leaf optics-ctrl-created {
      type boolean;
      description
        "optics ctrl created";
    }
    leaf dsp-ctrl-created {
      type boolean;
      description
        "dsp ctrl created";
    }
    leaf has-pluggable {
      type boolean;
      description
        "has pluggable";
    }
    leaf optics-admin-up {
      type boolean;
      description
        "optics admin up";
    }
    leaf dsp-admin-up {
      type boolean;
      description
        "dsp admin up";
    }
    leaf end-of-config {
      type boolean;
      description
        "end of config";
    }
    leaf optics-laser-state {
      type boolean;
      description
        "optics laser state";
    }
    leaf laser-state {
      type boolean;
      description
        "laser state";
    }
    leaf laser-on-pending {
      type boolean;
      description
        "laser on pending";
    }
    leaf provisioning-needed {
      type boolean;
      description
        "provisioning needed";
    }
    leaf force-reprovision {
      type boolean;
      description
        "force reprovision";
    }
    leaf configured-frequency {
      type uint32;
      description
        "configured frequency";
    }
    leaf provisioned-frequency {
      type uint32;
      description
        "provisioned frequency";
    }
    leaf fp-port-idx {
      type string {
        length "0..128";
      }
      description
        "fp port idx";
    }
    leaf configured-tx-power {
      type string {
        length "0..128";
      }
      description
        "configured tx power";
    }
    leaf provisioned-tx-power {
      type string {
        length "0..128";
      }
      description
        "provisioned tx power";
    }
    leaf configured-cd-min {
      type string {
        length "0..128";
      }
      description
        "configured cd min";
    }
    leaf provisioned-cd-min {
      type string {
        length "0..128";
      }
      description
        "provisioned cd min";
    }
    leaf configured-cd-max {
      type string {
        length "0..128";
      }
      description
        "configured cd max";
    }
    leaf provisioned-cd-max {
      type string {
        length "0..128";
      }
      description
        "provisioned cd max";
    }
    leaf configured-traffic-type {
      type string {
        length "0..128";
      }
      description
        "configured traffic type";
    }
    leaf provisioned-traffic-type {
      type string {
        length "0..128";
      }
      description
        "provisioned traffic type";
    }
    leaf configured-loopback-mode {
      type string {
        length "0..128";
      }
      description
        "configured loopback mode";
    }
    leaf provisioned-loopback-mode {
      type string {
        length "0..128";
      }
      description
        "provisioned loopback mode";
    }
    leaf expected-ctp2-led-state {
      type string {
        length "0..128";
      }
      description
        "expected ctp2 led state";
    }
    leaf provisioned-ctp2-led-state {
      type string {
        length "0..128";
      }
      description
        "provisioned ctp2 led state";
    }
    leaf led-op-rc {
      type int32;
      description
        "led op rc";
    }
    leaf laser-op-rc {
      type int32;
      description
        "laser op rc";
    }
    leaf wlen-op-rc {
      type int32;
      description
        "wlen op rc";
    }
    leaf traffic-op-rc {
      type int32;
      description
        "traffic op rc";
    }
    leaf loopback-op-rc {
      type int32;
      description
        "loopback op rc";
    }
    leaf tx-power-op-rc {
      type int32;
      description
        "tx power op rc";
    }
    leaf cd-min-op-rc {
      type int32;
      description
        "cd min op rc";
    }
    leaf cd-max-op-rc {
      type int32;
      description
        "cd max op rc";
    }
    leaf provisioning-failed {
      type boolean;
      description
        "provisioning failed";
    }
    leaf ctp2-hw-alarms {
      type string {
        length "0..128";
      }
      description
        "ctp2 hw alarms";
    }
    leaf dsp-hw-alarms {
      type string {
        length "0..256";
      }
      description
        "dsp hw alarms";
    }
    leaf is-pm-port-created-opt {
      type boolean;
      description
        "is pm port created opt";
    }
    leaf rc-pm-port-opt {
      type int32;
      description
        "rc pm port opt";
    }
    leaf pm-port-state-opt {
      type int32;
      description
        "pm port state opt";
    }
    leaf rc-pm-provision-opt {
      type int32;
      description
        "rc pm provision opt";
    }
    leaf is-alarm-port-created-opt {
      type boolean;
      description
        "is alarm port created opt";
    }
    leaf rc-alarm-port-opt {
      type int32;
      description
        "rc alarm port opt";
    }
    leaf is-pm-port-created-dsp {
      type boolean;
      description
        "is pm port created dsp";
    }
    leaf rc-pm-port-dsp {
      type int32;
      description
        "rc pm port dsp";
    }
    leaf pm-port-state-dsp {
      type int32;
      description
        "pm port state dsp";
    }
    leaf rc-pm-provision-dsp {
      type int32;
      description
        "rc pm provision dsp";
    }
    leaf is-alarm-port-created-dsp {
      type boolean;
      description
        "is alarm port created dsp";
    }
    leaf rc-alarm-port-dsp {
      type int32;
      description
        "rc alarm port dsp";
    }
  }

  grouping COH-HEALTH-DATA {
    description
      "Coherent health Data";
    leaf aipc-srvr-state {
      type boolean;
      description
        "aipc srvr state";
    }
    leaf sysdb-state {
      type boolean;
      description
        "sysdb state";
    }
    leaf pm-state {
      type boolean;
      description
        "pm state";
    }
    leaf optics-ea-conn {
      type boolean;
      description
        "optics ea conn";
    }
    leaf dsp-ea-conn {
      type boolean;
      description
        "dsp ea conn";
    }
    leaf vether-state {
      type boolean;
      description
        "vether state";
    }
    leaf morgoth-alive {
      type boolean;
      description
        "morgoth alive";
    }
    leaf prov-infra-state {
      type boolean;
      description
        "prov infra state";
    }
    leaf pending-provision {
      type boolean;
      description
        "pending provision";
    }
    leaf pulse-sent {
      type boolean;
      description
        "pulse sent";
    }
    leaf inside-prov-loop {
      type boolean;
      description
        "inside prov loop";
    }
    leaf fpd-in-progress {
      type boolean;
      description
        "fpd in progress";
    }
    leaf prov-run-count {
      type uint32;
      description
        "prov run count";
    }
    leaf sdk-version {
      type string {
        length "0..255";
      }
      description
        "sdk version";
    }
    leaf dsp0-version {
      type string {
        length "0..255";
      }
      description
        "dsp0 version";
    }
    leaf dsp1-version {
      type string {
        length "0..255";
      }
      description
        "dsp1 version";
    }
    leaf dsp2-version {
      type string {
        length "0..255";
      }
      description
        "dsp2 version";
    }
    leaf board-type {
      type string {
        length "0..255";
      }
      description
        "board type";
    }
    leaf jlink-op {
      type string {
        length "0..6144";
      }
      description
        "jlink op";
    }
    list port-data {
      description
        "port data";
      uses COH-PORT-DATA;
    }
  }

  grouping COH-OP-TIME-STATS {
    description
      "Coherent operation stats";
    leaf start {
      type string {
        length "0..255";
      }
      description
        "start";
    }
    leaf end {
      type string {
        length "0..255";
      }
      description
        "end";
    }
    leaf time-taken {
      type string {
        length "0..255";
      }
      description
        "time taken";
    }
    leaf worst-time {
      type string {
        length "0..255";
      }
      description
        "worst time";
    }
  }

  grouping COH-PORT-OP-STATS {
    description
      "Port specific op stats";
    container laser-on-stats {
      description
        "laser on stats";
      uses COH-OP-TIME-STATS;
    }
    container laser-off-stats {
      description
        "laser off stats";
      uses COH-OP-TIME-STATS;
    }
    container wl-op-stats {
      description
        "wl op stats";
      uses COH-OP-TIME-STATS;
    }
    container txpwr-op-stats {
      description
        "txpwr op stats";
      uses COH-OP-TIME-STATS;
    }
    container cdmin-op-stats {
      description
        "cdmin op stats";
      uses COH-OP-TIME-STATS;
    }
    container cdmax-op-stats {
      description
        "cdmax op stats";
      uses COH-OP-TIME-STATS;
    }
    container traffictype-op-stats {
      description
        "traffictype op stats";
      uses COH-OP-TIME-STATS;
    }
    leaf rsip {
      type uint32;
      description
        "rsip";
    }
    leaf fp-port-idx {
      type string {
        length "0..128";
      }
      description
        "fp port idx";
    }
    leaf laser-state {
      type boolean;
      description
        "laser state";
    }
    leaf provisioned-frequency {
      type uint32;
      description
        "provisioned frequency";
    }
    leaf tx-power {
      type int32;
      description
        "tx power";
    }
    leaf cd-min {
      type int32;
      description
        "cd min";
    }
    leaf cd-max {
      type int32;
      description
        "cd max";
    }
    leaf traffic-type {
      type string {
        length "0..128";
      }
      description
        "traffic type";
    }
  }

  grouping COH-TIME-STATS {
    description
      "Coherent driver time stats";
    leaf driver-init {
      type string {
        length "0..255";
      }
      description
        "driver init";
    }
    leaf driver-operational {
      type string {
        length "0..255";
      }
      description
        "driver operational";
    }
    leaf device-created {
      type string {
        length "0..255";
      }
      description
        "device created";
    }
    leaf optics-controllers-created {
      type string {
        length "0..255";
      }
      description
        "optics controllers created";
    }
    leaf dsp-controllers-created {
      type string {
        length "0..255";
      }
      description
        "dsp controllers created";
    }
    leaf eth-intf-created {
      type string {
        length "0..255";
      }
      description
        "eth intf created";
    }
    list port-stat {
      description
        "port stat";
      uses COH-PORT-OP-STATS;
    }
  }
}
