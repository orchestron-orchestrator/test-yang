module Cisco-IOS-XR-spirit-ether-ea-oper {
  namespace "http://cisco.com/ns/yang/Cisco-IOS-XR-spirit-ether-ea-oper";
  prefix spirit-ether-ea-oper;

  import Cisco-IOS-XR-types {
    prefix xr;
  }
  import cisco-semver {
    prefix semver;
  }

  include Cisco-IOS-XR-spirit-ether-ea-oper-sub1 {
    revision-date 2021-12-02;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR spirit-ether-ea package operational data.

     This module contains definitions
     for the following management objects:
       ethernet-hardware: ethernet operational data

     Copyright (c) 2013-2021 by Cisco Systems, Inc.
     All rights reserved.";

  revision 2021-12-02 {
    semver:module-version "1.0.0";
    description
      "Added Stream Name.";
  }
  revision 2019-04-05 {
    description
      "Establish semantic version baseline.";
  }
  revision 2015-11-09 {
    description
      "IOS XR 6.0 revision.";
  }

  container ethernet-hardware {
    config false;
    description
      "ethernet operational data";
    container nodes {
      description
        "List of nodes with platform specific ether-ea
         data";
      list node {
        key "node-name";
        description
          "Pre-ifib data for particular node";
        container status {
          description
            "ether_ea status data";
          uses VKG-ETHER-EA-SHOW-STATUS-ENTRY;
        }
        leaf node-name {
          type xr:Node-id;
          description
            "The node name";
        }
      }
    }
  }
}
