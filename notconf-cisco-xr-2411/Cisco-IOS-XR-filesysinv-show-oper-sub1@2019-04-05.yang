submodule Cisco-IOS-XR-filesysinv-show-oper-sub1 {
  belongs-to Cisco-IOS-XR-filesysinv-show-oper {
    prefix Cisco-IOS-XR-filesysinv-show-oper;
  }

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR filesysinv-show package operational data.

     Copyright (c) 2013-2019 by Cisco Systems, Inc.
     All rights reserved.";

  revision 2019-04-05 {
    semver:module-version "1.0.0";
    description
      "Establish semantic version baseline.";
  }
  revision 2015-11-09 {
    description
      "IOS XR 6.0 revision.";
  }

  typedef Filesysinv-classification {
    type enumeration {
      enum "unclassified" {
        value 0;
        description
          "Unclassified file type";
      }
      enum "executable" {
        value 1;
        description
          "Executable type of file";
      }
      enum "direct-ory" {
        value 2;
        description
          "Directory";
      }
      enum "config" {
        value 3;
        description
          "Config type of file";
      }
      enum "volatile" {
        value 4;
        description
          "Volatile type of file";
      }
      enum "library" {
        value 5;
        description
          "Library type of file";
      }
    }
    description
      "File Classification";
  }

  typedef Filesys-inv-digest-algorithm {
    type enumeration {
      enum "digest-invalid" {
        value 0;
        description
          "DIGEST INVALID";
      }
      enum "md5" {
        value 1;
        description
          "MD5";
      }
      enum "sha1" {
        value 2;
        description
          "SHA1";
      }
      enum "sha256" {
        value 3;
        description
          "SHA256";
      }
      enum "sha384" {
        value 4;
        description
          "SHA384";
      }
      enum "sha512" {
        value 5;
        description
          "SHA512";
      }
    }
    description
      "Digest Algorithm";
  }

  typedef Filesys-inv-change-kind {
    type enumeration {
      enum "change-kind-invalid" {
        value 0;
        description
          "Change Kind Invalid";
      }
      enum "change-kind-created" {
        value 1;
        description
          "Change Kind Created";
      }
      enum "change-kind-contents-modified" {
        value 2;
        description
          "Change Kind Modified";
      }
      enum "change-kind-deleted" {
        value 3;
        description
          "Change Kind Deleted";
      }
      enum "change-kind-meta-data-modified" {
        value 4;
        description
          "Change Kind Metadata Modified";
      }
    }
    description
      "Change Kind";
  }

  typedef Filesys-inv-package-kind {
    type enumeration {
      enum "package-invalid" {
        value 0;
        description
          "Package Invalid";
      }
      enum "package-rpm" {
        value 1;
        description
          "Package RPM";
      }
      enum "package-anonymous" {
        value 2;
        description
          "Package Anonymous";
      }
    }
    description
      "Package Kind";
  }

  typedef Filesys-inv-container {
    type enumeration {
      enum "container-invalid" {
        value 0;
        description
          "CONTAINER INVALID";
      }
      enum "container-host" {
        value 1;
        description
          "CONTAINER HOST";
      }
      enum "container-sys-admin" {
        value 2;
        description
          "CONTAINER SYSADMIN";
      }
      enum "container-xr" {
        value 3;
        description
          "CONTAINER XR";
      }
    }
    description
      "Container Kind";
  }

  typedef Filesys-inv-signature {
    type enumeration {
      enum "signature-invalid" {
        value 0;
        description
          "Signature Invalid";
      }
      enum "rsa" {
        value 1;
        description
          "RSA";
      }
      enum "ecdsa" {
        value 2;
        description
          "ECDSA";
      }
    }
    description
      "Signature Type";
  }

  grouping FILESYS-INV-DIGEST {
    description
      "Digest";
    leaf algorithm {
      type Filesys-inv-digest-algorithm;
      description
        "Algorithm for this digest";
    }
    leaf digest-value {
      type string;
      description
        "Hash of the event data, base64 encoded";
    }
  }

  grouping FILESYS-INV-FILE-META-DATA {
    description
      "File Meta Data";
    leaf uid {
      type uint32;
      description
        "user id";
    }
    leaf gid {
      type uint32;
      description
        "group id";
    }
    leaf devid {
      type uint64;
      description
        "Device ID on which this file resides";
    }
    leaf inode {
      type uint64;
      description
        "Inode number";
    }
    leaf blocks {
      type uint64;
      description
        "No of blocks of the file";
    }
    leaf size {
      type uint64;
      units "byte";
      description
        "Size of the file in bytes";
    }
    leaf atime {
      type int64;
      description
        "Last access time of the file";
    }
    leaf mtime {
      type int64;
      description
        "Last Modification time of the file";
    }
    leaf ctime {
      type int64;
      description
        "Creation time of the file";
    }
    leaf mode {
      type uint32;
      description
        "File type and mode";
    }
  }

  grouping FILESYS-INV-FILE {
    description
      "File";
    container meta {
      description
        "Metadata of the file";
      uses FILESYS-INV-FILE-META-DATA;
    }
    container digest {
      description
        "Digest";
      uses FILESYS-INV-DIGEST;
    }
    leaf name {
      type string;
      description
        "Complete path of the file";
    }
    leaf package-kind {
      type Filesys-inv-package-kind;
      description
        "Package Kind";
    }
    leaf change-kind {
      type Filesys-inv-change-kind;
      description
        "Change Kind";
    }
    leaf package-name {
      type string;
      description
        "Package Name";
    }
    leaf parent-package-name {
      type string;
      description
        "Package Name";
    }
    leaf package-version {
      type string;
      description
        "Package version";
    }
    leaf classification {
      type Filesysinv-classification;
      description
        "File Classification";
    }
  }

  grouping FILESYS-INV-FILE-SYSTEM-SIGNED-SNAPSHOT {
    description
      "FileSystemSignedSnapshot";
    leaf signature {
      type uint8;
      description
        "Signature version designates the format of the
         signed data";
    }
    leaf signature-version {
      type uint32;
      description
        "Signature Version";
    }
    leaf signature-type {
      type Filesys-inv-signature;
      description
        "Signature Type";
    }
    leaf snapshot-block-no {
      type uint32;
      description
        "Block No";
    }
    leaf snap-time {
      type string;
      description
        "Time when the snapshot was taken";
    }
    leaf container {
      type Filesys-inv-container;
      description
        "Container type";
    }
    leaf release-version {
      type string;
      description
        "Release Version";
    }
    leaf chassis-serial-number {
      type string;
      description
        "Chassis serial number";
    }
    list files {
      description
        "List of entities in snapshot";
      uses FILESYS-INV-FILE;
    }
  }
}
