module Cisco-IOS-XR-rptiming-dti-oper {
  namespace "http://cisco.com/ns/yang/Cisco-IOS-XR-rptiming-dti-oper";
  prefix rptiming-dti-oper;

  import Cisco-IOS-XR-types {
    prefix xr;
  }
  import cisco-semver {
    prefix semver;
  }

  include Cisco-IOS-XR-rptiming-dti-oper-sub1 {
    revision-date 2019-04-05;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR rptiming-dti package operational data.

     This module contains definitions
     for the following management objects:
       dti-controller: DTI interface controller status and
         configuration

     Copyright (c) 2013-2019 by Cisco Systems, Inc.
     All rights reserved.";

  revision 2019-04-05 {
    semver:module-version "1.0.0";
    description
      "Establish semantic version baseline.";
  }
  revision 2015-11-09 {
    description
      "IOS XR 6.0 revision.";
  }

  container dti-controller {
    config false;
    description
      "DTI interface controller status and configuration";
    container nodes {
      description
        "List of nodes applicable to DTI controller";
      list node {
        key "node-name";
        description
          "DTI operational data for a single node";
        container client {
          description
            "Display DTI client status";
          uses DTI-CLIENT-INFO;
        }
        container port {
          description
            "Display DTI input port status";
          uses DTI-PORT-INFO;
        }
        container time-of-day {
          description
            "Display DTI time-of-day status";
          uses DTI-TOD-INFO;
        }
        leaf node-name {
          type xr:Node-id;
          description
            "Node Name";
        }
      }
    }
  }
}
