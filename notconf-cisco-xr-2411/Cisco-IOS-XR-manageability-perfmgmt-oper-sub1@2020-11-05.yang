submodule Cisco-IOS-XR-manageability-perfmgmt-oper-sub1 {
  belongs-to Cisco-IOS-XR-manageability-perfmgmt-oper {
    prefix Cisco-IOS-XR-manageability-perfmgmt-oper;
  }

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR manageability-perfmgmt package operational data.

     Copyright (c) 2013-2020 by Cisco Systems, Inc.
     All rights reserved.";

  revision 2020-11-05 {
    semver:module-version "1.1.0";
    description
      "changed bandwidth type from 32-bit to 64-bit";
  }
  revision 2019-04-05 {
    semver:module-version "1.0.0";
    description
      "Establish semantic version baseline.";
  }
  revision 2017-09-07 {
    description
      "Fixed type translation error.";
  }
  revision 2015-11-09 {
    description
      "IOS XR 6.0 revision.";
  }

  grouping PM-INTERFACE-DATARATE-BAG {
    description
      "Datarate information";
    leaf time-stamp {
      type uint64;
      units "second";
      description
        "Timestamp of sample in seconds drom UCT";
    }
    leaf input-data-rate {
      type uint32;
      units "bit/s";
      description
        "Input datarate in 1000's of bps";
    }
    leaf input-packet-rate {
      type uint32;
      units "packet/s";
      description
        "Input packets per second";
    }
    leaf output-data-rate {
      type uint32;
      units "bit/s";
      description
        "Output datarate in 1000's of bps";
    }
    leaf output-packet-rate {
      type uint32;
      units "packet/s";
      description
        "Output packets per second";
    }
    leaf input-peak-rate {
      type uint32;
      description
        "Peak input datarate";
    }
    leaf input-peak-pkts {
      type uint32;
      description
        "Peak input packet rate";
    }
    leaf output-peak-rate {
      type uint32;
      description
        "Peak output datarate";
    }
    leaf output-peak-pkts {
      type uint32;
      description
        "Peak output packet rate";
    }
    leaf bandwidth {
      type uint64;
      units "kbit/s";
      description
        "Bandwidth (in kbps)";
    }
  }

  grouping PM-INTERFACE-BASIC-STATS {
    description
      "PM Interface Basic Counters";
    leaf time-stamp {
      type uint64;
      units "second";
      description
        "Timestamp of sample in seconds from UCT";
    }
    leaf in-packets {
      type uint64;
      description
        "Packets received";
    }
    leaf in-octets {
      type uint64;
      units "byte";
      description
        "Bytes received";
    }
    leaf out-packets {
      type uint64;
      description
        "Packets sent";
    }
    leaf out-octets {
      type uint64;
      units "byte";
      description
        "Bytes sent";
    }
    leaf input-total-drops {
      type uint64;
      description
        "Inbound correct packets discarded";
    }
    leaf input-queue-drops {
      type uint64;
      description
        "Input queue drops";
    }
    leaf input-total-errors {
      type uint64;
      description
        "Inbound incorrect packets discarded";
    }
    leaf output-total-drops {
      type uint64;
      description
        "Outbound correct packets discarded";
    }
    leaf output-queue-drops {
      type uint64;
      description
        "Output queue drops";
    }
    leaf output-total-errors {
      type uint64;
      description
        "Outbound incorrect packets discarded";
    }
  }

  grouping PM-INTERFACE-GENERIC-BAG {
    description
      "PM Interface Generic Counters";
    leaf time-stamp {
      type uint64;
      units "second";
      description
        "Timestamp of sample in seconds drom UCT";
    }
    leaf in-packets {
      type uint64;
      description
        "Packets received";
    }
    leaf in-octets {
      type uint64;
      units "byte";
      description
        "Bytes received";
    }
    leaf out-packets {
      type uint64;
      description
        "Packets sent";
    }
    leaf out-octets {
      type uint64;
      units "byte";
      description
        "Bytes sent";
    }
    leaf in-ucast-pkts {
      type uint64;
      description
        "Unicast packets received";
    }
    leaf in-multicast-pkts {
      type uint64;
      description
        "Multicast packets received";
    }
    leaf in-broadcast-pkts {
      type uint64;
      description
        "Broadcast packets received";
    }
    leaf out-ucast-pkts {
      type uint64;
      description
        "Unicast packets sent";
    }
    leaf out-multicast-pkts {
      type uint64;
      description
        "Multicast packets sent";
    }
    leaf out-broadcast-pkts {
      type uint64;
      description
        "Broadcast packets sent";
    }
    leaf output-total-drops {
      type uint32;
      description
        "Outbound correct packets discarded";
    }
    leaf input-total-drops {
      type uint32;
      description
        "Inbound correct packets discarded";
    }
    leaf input-queue-drops {
      type uint32;
      description
        "Input queue drops";
    }
    leaf input-unknown-proto {
      type uint32;
      description
        "Inbound packets discarded with unknown proto";
    }
    leaf output-total-errors {
      type uint32;
      description
        "Outbound incorrect packets discarded";
    }
    leaf output-underrun {
      type uint32;
      description
        "Output underruns";
    }
    leaf input-total-errors {
      type uint32;
      description
        "Inbound incorrect packets discarded";
    }
    leaf input-crc {
      type uint32;
      description
        "Inbound packets discarded with incorrect CRC";
    }
    leaf input-overrun {
      type uint32;
      description
        "Input overruns";
    }
    leaf input-frame {
      type uint32;
      description
        "Inbound framing errors";
    }
  }

  grouping PM-BGP-NBR-BAG {
    description
      "PM BGP Neighbor Information";
    leaf time-stamp {
      type uint64;
      units "second";
      description
        "Timestamp of sample in seconds drom UCT";
    }
    leaf input-messages {
      type uint32;
      description
        "Number of messages received";
    }
    leaf output-messages {
      type uint32;
      description
        "Number of messages sent";
    }
    leaf input-update-messages {
      type uint32;
      description
        "Number of update messages received";
    }
    leaf output-update-messages {
      type uint32;
      description
        "Number of update messages sent";
    }
    leaf conn-established {
      type uint32;
      description
        "Number of times the connection was established";
    }
    leaf conn-dropped {
      type uint32;
      description
        "Number of times connection was dropped";
    }
    leaf errors-received {
      type uint32;
      description
        "Number of error notifications received on the
         connection";
    }
    leaf errors-sent {
      type uint32;
      description
        "Number of error notifications sent on the
         connection";
    }
  }

  grouping PM-NODE-MEM-BAG {
    description
      "PM System Resources Memory Information";
    leaf time-stamp {
      type uint64;
      units "second";
      description
        "Timestamp of sample in seconds drom UCT";
    }
    leaf curr-memory {
      type uint32;
      units "byte";
      description
        "Current application memory (Bytes) in use";
    }
    leaf peak-memory {
      type uint32;
      units "megabyte";
      description
        "Max. system memory (MBytes) used since bootup";
    }
  }

  grouping PM-NODE-PROCESS-BAG {
    description
      "PM Process CPU and Memory Information";
    leaf time-stamp {
      type uint64;
      units "second";
      description
        "Timestamp of sample in seconds drom UCT";
    }
    leaf peak-memory {
      type uint32;
      units "kilobyte";
      description
        "Max. dynamic memory (KBytes) used since startup
         time";
    }
    leaf average-cpu-used {
      type uint32;
      description
        "Average %CPU utilization";
    }
    leaf no-threads {
      type uint32;
      description
        "Number of threads";
    }
  }

  grouping PM-NODE-CPU-BAG {
    description
      "PM System Resources CPU Information";
    leaf time-stamp {
      type uint64;
      units "second";
      description
        "Timestamp of sample in seconds drom UCT";
    }
    leaf no-processes {
      type uint32;
      description
        "Number of processes in the system";
    }
    leaf average-cpu-used {
      type uint32;
      description
        "Average system %CPU utilization";
    }
  }

  grouping PM-MPLS-LDP-BAG {
    description
      "PM MPLS LDP Neighbor bag";
    leaf time-stamp {
      type uint64;
      units "second";
      description
        "Timestamp of sample in seconds drom UCT";
    }
    leaf total-msgs-sent {
      type uint16;
      description
        "Total messages sent";
    }
    leaf total-msgs-rcvd {
      type uint16;
      description
        "Total messages received";
    }
    leaf init-msgs-sent {
      type uint16;
      description
        "Init messages sent";
    }
    leaf init-msgs-rcvd {
      type uint16;
      description
        "Tnit messages received";
    }
    leaf address-msgs-sent {
      type uint16;
      description
        "Address messages sent";
    }
    leaf address-msgs-rcvd {
      type uint16;
      description
        "Address messages received";
    }
    leaf address-withdraw-msgs-sent {
      type uint16;
      description
        "Address withdraw messages sent";
    }
    leaf address-withdraw-msgs-rcvd {
      type uint16;
      description
        "Address withdraw messages received";
    }
    leaf label-mapping-msgs-sent {
      type uint16;
      description
        "Label mapping messages sent";
    }
    leaf label-mapping-msgs-rcvd {
      type uint16;
      description
        "Label mapping messages received";
    }
    leaf label-withdraw-msgs-sent {
      type uint16;
      description
        "Label withdraw messages sent";
    }
    leaf label-withdraw-msgs-rcvd {
      type uint16;
      description
        "Label withdraw messages received";
    }
    leaf label-release-msgs-sent {
      type uint16;
      description
        "Label release messages sent";
    }
    leaf label-release-msgs-rcvd {
      type uint16;
      description
        "Label release messages received";
    }
    leaf notification-msgs-sent {
      type uint16;
      description
        "Notification messages sent";
    }
    leaf notification-msgs-rcvd {
      type uint16;
      description
        "Notification messages received";
    }
    leaf keepalive-msgs-sent {
      type uint16;
      description
        "Keepalive messages sent";
    }
    leaf keepalive-msgs-rcvd {
      type uint16;
      description
        "Keepalive messages received";
    }
  }

  grouping PM-OSPF-V3PROTO-BAG {
    description
      "PM OSPF v3 Protocol Information";
    leaf time-stamp {
      type uint64;
      units "second";
      description
        "Timestamp of sample in seconds drom UCT";
    }
    leaf input-packets {
      type uint32;
      description
        "Total number of packets received";
    }
    leaf output-packets {
      type uint32;
      description
        "Total number of packets sent";
    }
    leaf input-hello-packets {
      type uint32;
      description
        "Number of Hello packets received";
    }
    leaf output-hello-packets {
      type uint32;
      description
        "Number of Hello packets sent";
    }
    leaf input-db-ds {
      type uint32;
      description
        "Number of DBD packets received";
    }
    leaf input-db-ds-lsa {
      type uint32;
      description
        "Number of LSA received in DBD packets";
    }
    leaf output-db-ds {
      type uint32;
      description
        "Number of DBD packets sent";
    }
    leaf output-db-ds-lsa {
      type uint32;
      description
        "Number of LSA sent in DBD packets";
    }
    leaf input-ls-requests {
      type uint32;
      description
        "Number of LS Requests received";
    }
    leaf input-ls-requests-lsa {
      type uint32;
      description
        "Number of LSA received in LS Requests";
    }
    leaf output-ls-requests {
      type uint32;
      description
        "Number of LS Requests sent";
    }
    leaf output-ls-requests-lsa {
      type uint32;
      description
        "Number of LSA sent in LS Requests";
    }
    leaf input-lsa-updates {
      type uint32;
      description
        "Number of LSA Updates received";
    }
    leaf input-lsa-updates-lsa {
      type uint32;
      description
        "Number of LSA received in LSA Updates";
    }
    leaf output-lsa-updates {
      type uint32;
      description
        "Number of LSA Updates sent";
    }
    leaf output-lsa-updates-lsa {
      type uint32;
      description
        "Number of LSA sent in LSA Updates";
    }
    leaf input-lsa-acks {
      type uint32;
      description
        "Number of LSA Acknowledgements received";
    }
    leaf input-lsa-acks-lsa {
      type uint32;
      description
        "Number of LSA received in LSA Acknowledgements";
    }
    leaf output-lsa-acks {
      type uint32;
      description
        "Number of LSA Acknowledgements sent";
    }
    leaf output-lsa-acks-lsa {
      type uint32;
      description
        "Number of LSA sent in LSA Acknowledgements";
    }
  }

  grouping PM-OSPF-V2PROTO-BAG {
    description
      "PM OSPF v2 Protocol Information";
    leaf time-stamp {
      type uint64;
      units "second";
      description
        "Timestamp of sample in seconds drom UCT";
    }
    leaf input-packets {
      type uint32;
      description
        "Total number of packets received";
    }
    leaf output-packets {
      type uint32;
      description
        "Total number of packets sent";
    }
    leaf input-hello-packets {
      type uint32;
      description
        "Number of Hello packets received";
    }
    leaf output-hello-packets {
      type uint32;
      description
        "Number of Hello packets sent";
    }
    leaf input-db-ds {
      type uint32;
      description
        "Number of DBD packets received";
    }
    leaf input-db-ds-lsa {
      type uint32;
      description
        "Number of LSA received in DBD packets";
    }
    leaf output-db-ds {
      type uint32;
      description
        "Number of DBD packets sent";
    }
    leaf output-db-ds-lsa {
      type uint32;
      description
        "Number of LSA sent in DBD packets";
    }
    leaf input-ls-requests {
      type uint32;
      description
        "Number of LS Requests received";
    }
    leaf input-ls-requests-lsa {
      type uint32;
      description
        "Number of LSA received in LS Requests";
    }
    leaf output-ls-requests {
      type uint32;
      description
        "Number of LS Requests sent";
    }
    leaf output-ls-requests-lsa {
      type uint32;
      description
        "Number of LSA sent in LS Requests";
    }
    leaf input-lsa-updates {
      type uint32;
      description
        "Number of LSA Updates received";
    }
    leaf input-lsa-updates-lsa {
      type uint32;
      description
        "Number of LSA received in LSA Updates";
    }
    leaf output-lsa-updates {
      type uint32;
      description
        "Number of LSA Updates sent";
    }
    leaf output-lsa-updates-lsa {
      type uint32;
      description
        "Number of LSA sent in LSA Updates";
    }
    leaf input-lsa-acks {
      type uint32;
      description
        "Number of LSA Acknowledgements received";
    }
    leaf input-lsa-acks-lsa {
      type uint32;
      description
        "Number of LSA received in LSA Acknowledgements";
    }
    leaf output-lsa-acks {
      type uint32;
      description
        "Number of LSA Acknowledgements sent";
    }
    leaf output-lsa-acks-lsa {
      type uint32;
      description
        "Number of LSA sent in LSA Acknowledgements";
    }
    leaf checksum-errors {
      type uint32;
      description
        "Number of packets received with checksum errors";
    }
  }
}
