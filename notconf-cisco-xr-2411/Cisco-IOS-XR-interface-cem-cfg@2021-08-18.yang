module Cisco-IOS-XR-interface-cem-cfg {
  namespace "http://cisco.com/ns/yang/Cisco-IOS-XR-interface-cem-cfg";
  prefix interface-cem-cfg;

  import Cisco-IOS-XR-types {
    prefix xr;
  }
  import cisco-semver {
    prefix semver;
  }
  import Cisco-IOS-XR-ifmgr-cfg {
    prefix a1;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR interface-cem package configuration.

     This YANG module augments the
       Cisco-IOS-XR-ifmgr-cfg
     module with configuration data.

     Copyright (c) 2013-2021 by Cisco Systems, Inc.
     All rights reserved.";

  revision 2021-08-18 {
    semver:module-version "2.0.0";
    description
      "Replaced default option with best-match option in payload and dejitter command under cem interface configuration.";
  }
  revision 2019-04-05 {
    semver:module-version "1.0.0";
    description
      "Establish semantic version baseline.";
  }
  revision 2015-11-09 {
    description
      "IOS XR 6.0 revision.";
  }

  typedef Cem-if-dummy-mode {
    type enumeration {
      enum "last-frame" {
        value 0;
        description
          "Last frame";
      }
      enum "user-defined" {
        value 1;
        description
          "User defined";
      }
    }
    description
      "Cem if dummy mode";
  }

  typedef Cem-recover-clock {
    type enumeration {
      enum "adaptive" {
        value 1;
        description
          "Adaptive recover";
      }
      enum "differential" {
        value 2;
        description
          "Differential recover";
      }
    }
    description
      "Cem recover clock";
  }

  typedef Endpoint-send {
    type enumeration {
      enum "send-ascii" {
        value 1;
        description
          "Endpoint Send ascii string";
      }
      enum "send-hex" {
        value 2;
        description
          "Endpoint Send hex string";
      }
    }
    description
      "Endpoint send";
  }

  typedef Endpoint-expected {
    type enumeration {
      enum "expected-ascii" {
        value 3;
        description
          "Endpoint Expected ascii string";
      }
      enum "expected-hex" {
        value 4;
        description
          "Endpoint Expected hex string";
      }
    }
    description
      "Endpoint expected";
  }

  augment "/a1:interface-configurations/a1:interface-configuration" {
    description
      "This augment extends the configuration data of
       'Cisco-IOS-XR-ifmgr-cfg'";
    container cem {
      presence "CLI submode compatibility.";
      description
        "Configure CEM interface";
      container clock {
        description
          "Configure clock for this CEM interface";
        leaf recover-clock-type {
          type Cem-recover-clock;
          description
            "Configure the Recover clock type";
        }
      }
      container idle {
        description
          "Configure idle pattern";
        leaf pattern {
          type xr:Hex-integer;
          description
            "Idle pattern from 0x0 to 0xff";
        }
      }
      container dummy {
        description
          "Configure bit-pattern for filling in lost or
           corrupted frames";
        leaf pattern {
          type xr:Hex-integer;
          description
            "User defined bit pattern from 0x0 to 0xff for
             CEM frame";
        }
        leaf mode {
          type Cem-if-dummy-mode;
          description
            "Configure mode";
        }
      }
      container payload-dejitter {
        description
          "Configure payload size and dejitter buffer
           length";
        leaf payload {
          type uint32 {
            range "0..1472";
          }
          must "not(../dejitter)";
          description
            "32-1472 is valid range, '0' value indicates to
             choose best suitable payload value for the
             given dejitter buffer length";
        }
        leaf dejitter {
          type uint32 {
            range "0..500000";
          }
          must "not(../payload)";
          description
            "1-500000 is valid range, '0' value indicates
             to choose best suitable dejitter buffer length
             value for the given payload";
        }
      }
      container endpoint {
        description
          "Configure Endpoint parameters for this CEM
           interface";
        container expected {
          description
            "Configure the Endpoint Expected value";
          leaf string-type {
            type Endpoint-expected;
            description
              "Endpoint Expected string type (ascii or hex
               format)";
          }
          leaf ascii-string {
            when "../string-type = 'expected-ascii'" {
              description
                "../StringType = EXPECTED_ASCII";
            }
            type string {
              length "1..64";
            }
            description
              "ASCII text (Max 64 characters)";
          }
          leaf hex-string {
            when "../string-type = 'expected-hex'" {
              description
                "../StringType = EXPECTED_HEX";
            }
            type string {
              length "1..128";
            }
            description
              "Hex nibbles (The string length should be an
               even number and Max length is 128)";
          }
        }
        container send {
          description
            "Configure the Endpoint Send value";
          leaf string-type {
            type Endpoint-send;
            description
              "Endpoint Send string type (ascii or hex
               format)";
          }
          leaf ascii-string {
            when "../string-type = 'send-ascii'" {
              description
                "../StringType = SEND_ASCII";
            }
            type string {
              length "1..64";
            }
            description
              "ASCII text (Max 64 characters)";
          }
          leaf hex-string {
            when "../string-type = 'send-hex'" {
              description
                "../StringType = SEND_HEX";
            }
            type string {
              length "1..128";
            }
            description
              "Hex nibbles (The string length should be an
               even number and Max length is 128)";
          }
        }
      }
      leaf class {
        type string {
          length "1..80";
        }
        description
          "Attach a CEM class to this interface";
      }
    }
  }
}
