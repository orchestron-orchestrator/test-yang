module Cisco-IOS-XR-um-ncs1001-eth-switch-cfg {
  namespace "http://cisco.com/ns/yang/Cisco-IOS-XR-um-ncs1001-eth-switch-cfg";
  prefix um-ncs1001-eth-switch-cfg;

  import Cisco-IOS-XR-um-location-cfg {
    prefix location;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ncs1001-eth-switch package configuration.

     This YANG module augments the
     modules with configuration data.

     Copyright (c) 2023 by Cisco Systems, Inc.
     All rights reserved.";

  revision 2023-03-24 {
    semver:module-version "1.0.0";
    description
      "Initial release";
  }

  grouping LOCATION-BODY {
    description
      "Grouping for location";
    container eth-switch {
      description
        "ethernet switch";
      container ports {
        description
          "ethernet switch port";
        list port {
          key "port-id";
          description
            "ethernet switch port";
          leaf port-id {
            type enumeration {
              enum "SfpUdc3" {
                value 0;
                description
                  "SFP  slot 3 port    ( 0)";
              }
              enum "SfpUdc2" {
                value 4;
                description
                  "SFP  slot 2 port    ( 4)";
              }
              enum "SfpUdc1" {
                value 8;
                description
                  "SFP  slot 1 port    ( 8)";
              }
              enum "Rj45Udc1" {
                value 12;
                description
                  "UDC1 port           (12)";
              }
              enum "Rj45Udc2" {
                value 16;
                description
                  "UDC2 port           (16)";
              }
              enum "Rj45Udc3" {
                value 20;
                description
                  "UDC3 port           (20)";
              }
              enum "CpuMgmt" {
                value 24;
                description
                  "CPU side Mgmt ports (24)";
              }
              enum "Rj45Mgmt" {
                value 26;
                description
                  "RJ45 Mgmt port      (26)";
              }
              enum "SfpMgmt" {
                value 27;
                description
                  "SFP  Mgmt port      (27)";
              }
            }
            description
              "ethernet switch port";
          }
          container disable {
            presence "Indicates a disable node is configured.";
            description
              "disable the specified port ";
          }
          container enable-loopback {
            presence "Indicates a enable-loopback node is configured.";
            description
              "enable loopback";
          }
          container enable-clear-on-read {
            presence "Indicates a enable-clear-on-read node is configured.";
            description
              "enable clear on read";
          }
        }
      }
    }
  }

  augment "/location:locations/location:location" {
    description
      "This augment extends active nodes configuration";
    uses LOCATION-BODY;
  }
  augment "/location:locations/location:preconfigured-location" {
    description
      "This augment extends preconfigured nodes
       configuration";
    uses LOCATION-BODY;
  }
}
