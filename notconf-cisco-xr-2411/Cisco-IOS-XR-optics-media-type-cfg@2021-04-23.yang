module Cisco-IOS-XR-optics-media-type-cfg {
  namespace "http://cisco.com/ns/yang/Cisco-IOS-XR-optics-media-type-cfg";
  prefix optics-media-type-cfg;

  import cisco-semver {
    prefix semver;
  }
  import Cisco-IOS-XR-ifmgr-cfg {
    prefix a1;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR optics-media-type package configuration.

     This YANG module augments the
       Cisco-IOS-XR-ifmgr-cfg
     module with configuration data.

     Copyright (c) 2013-2021 by Cisco Systems, Inc.
     All rights reserved.";

  revision 2021-04-23 {
    semver:module-version "1.0.0";
    description
      "Removed unused imports";
  }
  revision 2020-07-23 {
    description
      "Schema added.";
  }
  revision 2019-04-05 {
    description
      "Establish semantic version baseline.";
  }
  revision 2015-11-09 {
    description
      "IOS XR 6.0 revision.";
  }

  typedef Media-type-list {
    type string {
      pattern "(rj45)";
    }
    description
      "rj45:rj45 optics media type config";
  }

  augment "/a1:interface-configurations/a1:interface-configuration" {
    description
      "This augment extends the configuration data of
       'Cisco-IOS-XR-ifmgr-cfg'";
    leaf media-type {
      type Media-type-list;
      description
        "MediaType config for optics";
    }
  }
}
