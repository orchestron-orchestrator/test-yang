module Cisco-IOS-XR-ipv4-ma-cfg {
  namespace "http://cisco.com/ns/yang/Cisco-IOS-XR-ipv4-ma-cfg";
  prefix ipv4-ma-cfg;

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ipv4-ma package configuration.

     This module contains definitions
     for the following management objects:
       ipv4-network-global: IPv4 network global configuration data
       subscriber-pta: PTA Subscriber configuration

     Copyright (c) 2013-2021 by Cisco Systems, Inc.
     All rights reserved.";

  revision 2021-10-25 {
    semver:module-version "1.0.0";
    description
      "Enabled DHCP client support on physical interface.";
  }
  revision 2019-04-05 {
    semver:module-version "1.0.0";
    description
      "Establish semantic version baseline.";
  }
  revision 2015-07-30 {
    description
      "Descriptions updated.";
  }
  revision 2015-01-07 {
    description
      "IOS XR 5.3.1 revision.";
  }

  typedef Ipv4-qppb {
    type enumeration {
      enum "none" {
        value 0;
        description
          "No QPPB configuration";
      }
      enum "ip-prec" {
        value 1;
        description
          "Enable ip-precedence based QPPB";
      }
      enum "qos-grp" {
        value 2;
        description
          "Enable qos-group based QPPB";
      }
      enum "both" {
        value 3;
        description
          "Enable both ip-precedence and qos-group based
           QPPB";
      }
    }
    description
      "Ipv4 qppb";
  }

  container ipv4-network-global {
    description
      "IPv4 network global configuration data";
    container unnumbered {
      description
        "Enable IPv4 processing without an explicit
         address";
      container mpls {
        description
          "Configure MPLS routing protocol parameters";
        container te {
          description
            "IPv4 commands for MPLS Traffic Engineering";
          leaf interface {
            type string;
            description
              "Enable IP processing without an explicit
               address on MPLS Traffic-Eng";
          }
        }
      }
    }
    container qppb {
      description
        "QPPB";
      leaf source {
        type Ipv4-qppb;
        description
          "QPPB configuration on source";
      }
      leaf destination {
        type Ipv4-qppb;
        description
          "QPPB configuration on destination";
      }
    }
    leaf source-route {
      type boolean;
      default "true";
      description
        "The flag for enabling whether to process packets
         with source routing header options";
    }
    leaf reassemble-max-packets {
      type uint32 {
        range "1..50";
      }
      units "percentage";
      description
        "Percentage of total packets available in the
         system";
    }
    leaf reassemble-time-out {
      type uint32 {
        range "1..120";
      }
      units "second";
      description
        "Number of seconds a reassembly queue will hold
         before timeout";
    }
  }
  container subscriber-pta {
    description
      "PTA Subscriber configuration";
    leaf tcp-mss-adjust {
      type uint32 {
        range "1280..1536";
      }
      units "byte";
      description
        "TCP MSS Adjust (bytes)";
    }
  }
}
