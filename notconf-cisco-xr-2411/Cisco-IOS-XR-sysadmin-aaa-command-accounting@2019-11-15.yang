module Cisco-IOS-XR-sysadmin-aaa-command-accounting {
  namespace "http://www.cisco.com/ns/yang/Cisco-IOS-XR-sysadmin-aaa-command-accounting";
  prefix admin-accounting;

  import tailf-aaa {
    prefix aaa;
  }
  import cisco-semver {
    prefix semver;
  }

  organization
    "Cisco Systems Inc.";
  contact
    "Cisco Systems, Inc.
     Customer Service

     Postal: 170 West Tasman Drive
     San Jose, CA 95134

     Tel: +1 800 553-NETS

     E-mail: cs-yang@cisco.com";
  description
    "This module is used to enable/disable the command accounting via XR
     Copyright(c) 2016 by Cisco Systems, Inc.
     All rights reserved.

     Copyright (c) 2012-2020 by Cisco Systems, Inc.
     All rights reserved.";

  revision 2019-11-15 {
    semver:module-version "1.0.0";
    description
      "Initial revision";
  }

  augment "/aaa:aaa" {
    container admin-accounting {
      leaf enable {
        type boolean;
        default "false";
      }
    }
  }
}
