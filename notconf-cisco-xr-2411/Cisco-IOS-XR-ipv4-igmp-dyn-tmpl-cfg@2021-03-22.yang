module Cisco-IOS-XR-ipv4-igmp-dyn-tmpl-cfg {
  namespace "http://cisco.com/ns/yang/Cisco-IOS-XR-ipv4-igmp-dyn-tmpl-cfg";
  prefix ipv4-igmp-dyn-tmpl-cfg;

  import Cisco-IOS-XR-types {
    prefix xr;
  }
  import cisco-semver {
    prefix semver;
  }
  import Cisco-IOS-XR-subscriber-infra-tmplmgr-cfg {
    prefix a1;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ipv4-igmp-dyn-tmpl package configuration.

     This YANG module augments the
       Cisco-IOS-XR-subscriber-infra-tmplmgr-cfg
     module with configuration data.

     Copyright (c) 2013-2021 by Cisco Systems, Inc.
     All rights reserved.";

  revision 2021-03-22 {
    semver:module-version "2.0.0";
    description
      "Added new threashold leaf";
  }
  revision 2019-04-05 {
    semver:module-version "1.0.0";
    description
      "Establish semantic version baseline.";
  }
  revision 2015-11-09 {
    description
      "IOS XR 6.0 revision.";
  }

  typedef Dyn-tmpl-multicast-mode {
    type enumeration {
      enum "qos-correlation" {
        value 1;
        description
          "QOS Correlation";
      }
      enum "passive" {
        value 2;
        description
          "Passive";
      }
    }
    description
      "Dyn tmpl multicast mode";
  }

  grouping IGMP {
    description
      "Common node of ppp, ip-subscriber";
    container igmp {
      description
        "IGMPconfiguration";
      container default-vrf {
        description
          "Default VRF";
        container max-groups {
          presence "Indicates a max-groups node is configured.";
          description
            "IGMP Max Groups";
          leaf max-groups {
            type uint32 {
              range "1..40000";
            }
            mandatory true;
            description
              "Maximum number of groups accepted per
               interface by this router";
          }
          leaf threshold {
            type uint32 {
              range "1..40000";
            }
            description
              " Threshold for number of groups accepted per
               interface by this router";
          }
          leaf access-list-name {
            type xr:Cisco-ios-xr-string {
              length "1..64";
            }
            description
              "Access-list to account for";
          }
        }
        container explicit-tracking {
          presence "Indicates a explicit-tracking node is configured.";
          description
            "IGMPv3 explicit host tracking";
          leaf enable {
            type boolean;
            mandatory true;
            description
              "Enable or disable, when value is TRUE or
               FALSE respectively";
          }
          leaf access-list-name {
            type xr:Cisco-ios-xr-string {
              length "1..64";
            }
            description
              "Access list specifying tracking group range";
          }
        }
        leaf access-group {
          type xr:Cisco-ios-xr-string {
            length "1..64";
          }
          description
            "Access list specifying access-list group range";
        }
        leaf version {
          type uint32 {
            range "1..3";
          }
          default "3";
          description
            "IGMP Version";
        }
        leaf query-interval {
          type uint32 {
            range "1..3600";
          }
          units "second";
          default "60";
          description
            "Query interval in seconds";
        }
        leaf query-max-response-time {
          type uint32 {
            range "1..25";
          }
          units "second";
          default "10";
          description
            "Query response value in seconds";
        }
        leaf multicast-mode {
          type Dyn-tmpl-multicast-mode;
          description
            "Configure Multicast mode variable";
        }
      }
    }
  }

  augment "/a1:dynamic-template/a1:ip-subscribers/a1:ip-subscriber" {
    description
      "This augment extends the configuration data of
       'Cisco-IOS-XR-subscriber-infra-tmplmgr-cfg'";
    uses IGMP;
  }
  augment "/a1:dynamic-template/a1:ppps/a1:ppp" {
    description
      "This augment extends the configuration data of
       'Cisco-IOS-XR-subscriber-infra-tmplmgr-cfg'";
    uses IGMP;
  }
}
