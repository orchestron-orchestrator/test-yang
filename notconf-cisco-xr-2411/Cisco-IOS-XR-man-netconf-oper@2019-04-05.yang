module Cisco-IOS-XR-man-netconf-oper {
  namespace "http://cisco.com/ns/yang/Cisco-IOS-XR-man-netconf-oper";
  prefix man-netconf-oper;

  import Cisco-IOS-XR-types {
    prefix xr;
  }
  import cisco-semver {
    prefix semver;
  }

  include Cisco-IOS-XR-man-netconf-oper-sub1 {
    revision-date 2019-04-05;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR man-netconf package operational data.

     This module contains definitions
     for the following management objects:
       netconf-yang: Netconf-yang Operation Model

     Copyright (c) 2013-2019 by Cisco Systems, Inc.
     All rights reserved.";

  revision 2019-04-05 {
    semver:module-version "1.0.1";
    description
      "Establish semantic version baseline.";
  }
  revision 2015-11-09 {
    description
      "IOS XR 6.0 revision.";
  }

  container netconf-yang {
    config false;
    description
      "Netconf-yang Operation Model";
    container clients {
      description
        "List of Active Sessions Information";
      list client {
        key "session-id";
        description
          "Active Session Information";
        leaf session-id {
          type xr:Cisco-ios-xr-string;
          description
            "Session ID";
        }
        uses NC-SESSION-B;
      }
    }
    container rate-limit {
      description
        "Rate-limit Statistics";
      uses NC-RATELIMIT-STATS-B;
    }
    container capabilities {
      description
        "List of Capabilities";
      uses NC-CAPABILITIES-B;
    }
    container notification-subscriptions {
      description
        "Notification Subscriptions";
      container subscriptions {
        description
          "List of Notification Subscriptions Statistics";
        list subscription {
          key "session-id";
          description
            "Subscription Statistics";
          leaf session-id {
            type xr:Cisco-ios-xr-string;
            description
              "Session ID";
          }
          uses NC-NTFS-STATS-B;
        }
      }
    }
    container statistics {
      description
        "Summary and Sessions Statistics";
      container summary {
        description
          "Summary Statistics";
        uses NC-SUMMARY-STATS-B;
      }
      container sessions {
        description
          "List of Sessions Statistics";
        list session {
          key "session-id";
          description
            "Session Statistics";
          leaf session-id {
            type xr:Cisco-ios-xr-string;
            description
              "Session ID";
          }
          uses NC-SESSION-STATS-B;
        }
      }
    }
    container status {
      description
        "Netconf Agent Status";
      uses NC-STATUS-B;
    }
  }
}
