module cisco-xr-metadata {
  namespace "http://cisco.com/ns/yang/cisco-xr-metadata";
  prefix xr-md;

  import ietf-yang-metadata {
    prefix ietf-md;
  }

  organization
    "Cisco Systems, Inc.";
  contact
    "Cisco Systems, Inc.
     Customer Service

     Postal: 170 West Tasman Drive
     San Jose, CA 95134

     Tel: +1 800 553-NETS

     E-mail: cs-yang@cisco.com";
  description
    "This module defines metadata annotations that are defined and used for
     Cisco IOS-XR yang modules.";

  revision 2023-01-25 {
    description
      "Initial revision.";
  }

  ietf-md:annotation "mode" {
    type enumeration {
      enum legacy {
        value 1;
        description
          "Legacy-mode get operation";
      }
    }
  }
}
