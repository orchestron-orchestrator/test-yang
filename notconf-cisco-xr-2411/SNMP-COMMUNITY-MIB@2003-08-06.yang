module SNMP-COMMUNITY-MIB {
  namespace "http://tail-f.com/ns/mibs/SNMP-COMMUNITY-MIB/200308060000Z";
  prefix SNMP_COMMUNITY_MIB;

  import tailf-common {
    prefix tailf;
  }
  import SNMPv2-TC {
    prefix SNMPv2_TC;
  }
  import SNMP-TARGET-MIB {
    prefix SNMP_TARGET_MIB;
  }
  import SNMP-FRAMEWORK-MIB {
    prefix SNMP_FRAMEWORK_MIB;
  }

  revision 2003-08-06 {
    description
      "";
  }

  tailf:id "";
  tailf:snmp-mib-module-name "SNMP-COMMUNITY-MIB";

  typedef snmpCommunityIndexType {
    type string {
      length "1 .. 32";
    }
  }

  typedef snmpCommunityNameType {
    type string;
  }

  typedef snmpCommunitySecurityNameType {
    type string {
      length "1 .. 32";
    }
  }

  typedef snmpCommunityContextNameType {
    type string {
      length "min .. 32";
    }
  }

  typedef snmpTargetAddrNameType {
    type string {
      length "1 .. 32";
    }
  }

  typedef snmpTargetAddrTMaskType {
    type tailf:hex-list {
      tailf:value-length "min .. 255";
      pattern "(((([0-9A-Fa-f]{2}):){0,254}([0-9A-Fa-f]{2}))){0,1}";
    }
  }

  typedef snmpTargetAddrMMSType {
    type int32 {
      range "0 .. 2147483647";
    }
  }

  container SNMP-COMMUNITY-MIB {
    container snmpCommunityTable {
      list snmpCommunityEntry {
        tailf:sort-order "snmp-implied";
        tailf:snmp-oid "1.3.6.1.6.3.18.1.1";
        tailf:callpoint "snmp";
        key "snmpCommunityIndex";
        leaf snmpCommunityIndex {
          tailf:snmp-oid "1.3.6.1.6.3.18.1.1.1.1";
          type snmpCommunityIndexType;
        }
        leaf snmpCommunityName {
          tailf:snmp-oid "1.3.6.1.6.3.18.1.1.1.2";
          type snmpCommunityNameType;
          mandatory true;
        }
        leaf snmpCommunitySecurityName {
          tailf:snmp-oid "1.3.6.1.6.3.18.1.1.1.3";
          type snmpCommunitySecurityNameType;
          mandatory true;
        }
        leaf snmpCommunityContextEngineID {
          tailf:snmp-oid "1.3.6.1.6.3.18.1.1.1.4";
          type SNMP_FRAMEWORK_MIB:SnmpEngineID;
          mandatory true;
        }
        leaf snmpCommunityContextName {
          tailf:snmp-oid "1.3.6.1.6.3.18.1.1.1.5";
          type snmpCommunityContextNameType;
          default "";
        }
        leaf snmpCommunityTransportTag {
          tailf:snmp-oid "1.3.6.1.6.3.18.1.1.1.6";
          type SNMP_TARGET_MIB:SnmpTagValue;
          default "";
        }
        leaf snmpCommunityStorageType {
          tailf:snmp-oid "1.3.6.1.6.3.18.1.1.1.7";
          type SNMPv2_TC:StorageType;
          default "permanent";
        }
      }
    }
  }
}
