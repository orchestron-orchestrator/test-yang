module Cisco-IOS-XR-asr9k-np-act {
  namespace "http://cisco.com/ns/yang/Cisco-IOS-XR-np-act.yang";
  prefix asr9k-np-act;

  import cisco-semver {
    prefix semver;
  }
  import Cisco-IOS-XR-types {
    prefix csc;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR action package configuration.

     Copyright (c) 2016-2021, 2023 by Cisco Systems, Inc.
     All rights reserved.";

  revision 2023-04-20 {
    semver:module-version "1.1.0";
    description
      "IOS XR 7.11.1 revision.";
  }
  revision 2020-12-08 {
    semver:module-version "1.0.0";
    description
      "IOS XR 7.3.1 revision.";
  }

  rpc prm-np-clear-counters {
    csc:xr-task "system";
    csc:cli-command "clear controller np counters <np> location <location>";
    description
      "Action to clear prm np debug counters";

    input {
      leaf location {
        type string;
        mandatory true;
        description
          "Location string for LC to perform clear on.";
      }
      leaf np {
        type string;
        mandatory true;
        description
          "NP to perform clear operation on. All is accepted.";
      }
    }
  }
  rpc prm-np-clear-fabric-counters {
    csc:xr-task "system";
    csc:cli-command "clear controller np fabric-counters <path> <np> location <location>";
    description
      "Action to clear prm np debug fabric-counters";

    input {
      leaf location {
        type string;
        mandatory true;
        description
          "Location string for LC to perform clear on.";
      }
      leaf np {
        type string;
        mandatory true;
        description
          "NP to perform clear operation on. All is accepted.";
      }
      leaf path {
        type string;
        mandatory true;
        description
          "RX/TX Path to perform clear operation on. All is accepted.";
      }
    }
  }
  rpc prm-np-clear-punt-path-counters {
    csc:xr-task "system";
    csc:cli-command "clear controller np punt-path-counters <path> <host-info> location <location>";
    description
      "Action to clear prm np punt-path-counters";

    input {
      leaf location {
        type string;
        mandatory true;
        description
          "Location string for LC to perform clear on.";
      }
      leaf host-info {
        type string;
        mandatory true;
        description
          "Host-info to perform clear operation on.";
      }
      leaf path {
        type string;
        mandatory true;
        description
          "RX/TX Path to perform clear operation on. All is accepted.";
      }
    }
  }
  rpc prm-np-clear-fast-drops {
    csc:xr-task "system";
    csc:cli-command "clear controller np fast-drop location <location>";
    description
      "Action to clear prm np fast-drops";

    input {
      leaf location {
        type string;
        mandatory true;
        description
          "Location string for LC to perform clear on.";
      }
    }
  }
  rpc prm-np-clear-soft-errors {
    csc:xr-task "system";
    csc:cli-command "clear controller np soft-errors location <location>";
    description
      "Action to clear prm np soft-errors";

    input {
      leaf location {
        type string;
        mandatory true;
        description
          "Location string for LC to perform clear on.";
      }
    }
  }
  rpc prm-np-clear-drvlog {
    csc:xr-task "system";
    csc:cli-command "clear controller np drvlog location <location>";
    description
      "Action to clear prm np driver log";

    input {
      leaf location {
        type string;
        mandatory true;
        description
          "Location string for LC to perform clear on.";
      }
    }
  }
}
