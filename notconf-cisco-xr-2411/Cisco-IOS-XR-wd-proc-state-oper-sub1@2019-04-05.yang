submodule Cisco-IOS-XR-wd-proc-state-oper-sub1 {
  belongs-to Cisco-IOS-XR-wd-proc-state-oper {
    prefix Cisco-IOS-XR-wd-proc-state-oper;
  }

  import Cisco-IOS-XR-types {
    prefix xr;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR wd-proc-state package operational data.

     Copyright (c) 2013-2019 by Cisco Systems, Inc.
     All rights reserved.";

  revision 2019-04-05 {
    semver:module-version "1.0.0";
    description
      "Establish semantic version baseline.";
  }
  revision 2015-11-09 {
    description
      "IOS XR 6.0 revision.";
  }

  grouping PROCESS-DEATH-INFO-BAG {
    description
      "Detail of process death event";
    leaf location {
      xr:event-telemetry "Subscribe Telemetry Event";
      type string;
      description
        "Location where process death occured";
    }
    leaf process-name {
      xr:event-telemetry "Subscribe Telemetry Event";
      type string;
      description
        "Process Name";
    }
    leaf pid {
      xr:event-telemetry "Subscribe Telemetry Event";
      type uint32;
      description
        "Process PID";
    }
    leaf jid {
      xr:event-telemetry "Subscribe Telemetry Event";
      type uint32;
      description
        "Process JobID";
    }
  }
}
