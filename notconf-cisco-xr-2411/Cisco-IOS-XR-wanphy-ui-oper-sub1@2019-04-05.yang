submodule Cisco-IOS-XR-wanphy-ui-oper-sub1 {
  belongs-to Cisco-IOS-XR-wanphy-ui-oper {
    prefix Cisco-IOS-XR-wanphy-ui-oper;
  }

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR wanphy-ui package operational data.

     Copyright (c) 2013-2019 by Cisco Systems, Inc.
     All rights reserved.";

  revision 2019-04-05 {
    semver:module-version "1.0.1";
    description
      "Establish semantic version baseline.";
  }
  revision 2015-11-09 {
    description
      "IOS XR 6.0 revision.";
  }

  typedef Wanphy-alarm-rep-status {
    type enumeration {
      enum "disable" {
        description
          "Alarm reporting is disable";
      }
      enum "enable" {
        description
          "Alarm reporting is enable";
      }
    }
    description
      "WANPHY Alarm Report Status";
  }

  typedef Wanphy-mode-info {
    type enumeration {
      enum "lan" {
        description
          "LAN mode";
      }
      enum "wan" {
        description
          "WAN mode";
      }
    }
    description
      "WANPHY Modes";
  }

  grouping WANPHY-EDM-INFO {
    description
      "WAN-PHY Information";
    leaf admin-mode {
      type Wanphy-mode-info;
      description
        "Configuration Mode";
    }
    leaf port-state {
      type uint32;
      description
        "Port State";
    }
    leaf section-lof {
      type uint32;
      description
        "Section LOF";
    }
    leaf section-los {
      type uint32;
      description
        "Section LOS";
    }
    leaf section-bip {
      type uint64;
      description
        "Section BIP(B1)";
    }
    leaf line-ais {
      type uint32;
      description
        "Line AIS";
    }
    leaf line-rdi {
      type uint32;
      description
        "Line RDI";
    }
    leaf line-febe {
      type uint64;
      description
        "Line FEBE";
    }
    leaf line-bip {
      type uint64;
      description
        "Line BIP(B2) ";
    }
    leaf path-ais {
      type uint32;
      description
        "Path AIS";
    }
    leaf path-rdi {
      type uint32;
      description
        "Path RDI";
    }
    leaf path-febe {
      type uint64;
      description
        "Path FEBE";
    }
    leaf path-bip {
      type uint64;
      description
        "Path BIP(B3)";
    }
    leaf path-lop {
      type uint32;
      description
        "Path LOP";
    }
    leaf path-newptr {
      type uint32;
      description
        "Path NEWPTR";
    }
    leaf path-pse {
      type uint32;
      description
        "Path PSE";
    }
    leaf path-nse {
      type uint32;
      description
        "Path NSE";
    }
    leaf wis-alarms-ser {
      type uint32;
      description
        "WIS Alarms SER";
    }
    leaf wis-alarms-felcdp {
      type uint32;
      description
        "WIS Alarms FELCDP";
    }
    leaf wis-alarms-feaisp {
      type uint32;
      description
        "WIS Alarms FEAISP";
    }
    leaf wis-alarms-wlos {
      type uint32;
      description
        "WIS Alarms WLOS";
    }
    leaf wis-alarms-plcd {
      type uint32;
      description
        "WIS Alarms PLCD";
    }
    leaf wis-alarms-lfebip {
      type uint64;
      description
        "WIS Alarms LFEBIP";
    }
    leaf wis-alarms-pbec {
      type uint64;
      description
        "WIS Alarms PBEC";
    }
    leaf wis-alarms-plmp {
      type uint32;
      description
        "WIS Alarms PLMP";
    }
    leaf sf-ber-threshold {
      type uint32;
      description
        "BER thresholds: SF. Value 'd' in 10e-%d";
    }
    leaf sd-ber-threshold {
      type uint32;
      description
        "BER thresholds: SD. Value 'd' in 10e-%d";
    }
    leaf sf-ber-report {
      type Wanphy-alarm-rep-status;
      description
        "SF_BER Report";
    }
    leaf sd-ber-report {
      type Wanphy-alarm-rep-status;
      description
        "SD_BER Report";
    }
    leaf operational-mode {
      type Wanphy-mode-info;
      description
        "Operational Mode";
    }
    leaf remote-ip {
      type string;
      description
        "Remote IP Address";
    }
    leaf register-p-febe {
      type uint32;
      description
        "Register P_FEBE";
    }
    leaf register-l-fe-bip {
      type uint32;
      description
        "Register L_FE_BIP";
    }
    leaf register-l-bip {
      type uint32;
      description
        "Register L_BIP";
    }
    leaf register-p-bec {
      type uint32;
      description
        "Register P_BEC";
    }
    leaf register-s-bip {
      type uint32;
      description
        "Register S_BIP";
    }
    leaf register-j1-rx0 {
      type uint32;
      description
        "Register J1-Rx0";
    }
    leaf register-j1-rx1 {
      type uint32;
      description
        "Register J1-Rx1";
    }
    leaf register-j1-rx2 {
      type uint32;
      description
        "Register J1-Rx2";
    }
    leaf register-j1-rx3 {
      type uint32;
      description
        "Register J1-Rx3";
    }
    leaf register-j1-rx4 {
      type uint32;
      description
        "Register J1-Rx4";
    }
    leaf register-j1-rx5 {
      type uint32;
      description
        "Register J1-Rx5";
    }
    leaf register-j1-rx6 {
      type uint32;
      description
        "Register J1-Rx6";
    }
    leaf register-j1-rx7 {
      type uint32;
      description
        "Register J1-Rx7";
    }
    leaf wanphy-poll-timer {
      type uint32;
      description
        "wanphy poll timer";
    }
  }
}
