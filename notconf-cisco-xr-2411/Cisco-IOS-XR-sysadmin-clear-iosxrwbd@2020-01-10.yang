module Cisco-IOS-XR-sysadmin-clear-iosxrwbd {
  namespace "http://www.cisco.com/ns/yang/Cisco-IOS-XR-sysadmin-clear-iosxrwbd";
  prefix calvados_clear;

  import Cisco-IOS-XR-sysadmin-ethsw-esdma-cli-iosxrwbd {
    prefix esdma;
  }
  import tailf-common {
    prefix tailf;
  }
  import Cisco-IOS-XR-sysadmin-fabric-iosxrwbd {
    prefix fabric;
  }
  import Cisco-IOS-XR-sysadmin-asic-errors-ael {
    prefix aelclear;
  }
  import cisco-semver {
    prefix semver;
  }

  organization
    "Cisco Systems Inc.";
  contact
    "Cisco Systems, Inc.
     Customer Service

     Postal: 170 West Tasman Drive
     San Jose, CA 95134

     Tel: +1 800 553-NETS

     E-mail: cs-yang@cisco.com";
  description
    "This module contains a collection of YANG
     definitions for Cisco IOS-XR SysAdmin configuration.

     This module defines the top level container for
     all 'clear' commands for Sysadmin.

     Copyright(c) 2020 by Cisco Systems, Inc.
     All rights reserved.

     Copyright (c) 2012-2020 by Cisco Systems, Inc.
     All rights reserved.";

  revision 2020-01-10 {
    semver:module-version "1.0.0";
    description
      "Created initial 'clear' implementation for Whitebox";
  }

  grouping asic_clear {
    tailf:action "statistics";
  }

  container clear {
    container controller {
      container switch {
        uses esdma:switch_clear;
      }
      uses fabric:fabric_clear;
    }
    uses aelclear:ael-clear-asic-errors-grp;
  }
}
