module Cisco-IOS-XR-controller-och-oper {
  namespace "http://cisco.com/ns/yang/Cisco-IOS-XR-controller-och-oper";
  prefix controller-och-oper;

  import Cisco-IOS-XR-types {
    prefix xr;
  }
  import cisco-semver {
    prefix semver;
  }

  include Cisco-IOS-XR-controller-och-oper-sub1 {
    revision-date 2022-05-23;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR controller-och package operational data.

     This module contains definitions
     for the following management objects:
       och-oper: Och operational data

     Copyright (c) 2013-2022 by Cisco Systems, Inc.
     All rights reserved.";

  revision 2022-05-23 {
    semver:module-version "1.0.0";
    description
      "total-rx-power leaf is changed to rx-power in och-info container";
  }
  revision 2022-03-25 {
    description
      "Added transport_admin_state for OCH controller";
  }
  revision 2021-06-28 {
    description
      "New Oper Model Added for Och Controller";
  }
  revision 2019-04-05 {
    description
      "Establish semantic version baseline.";
  }
  revision 2015-11-09 {
    description
      "IOS XR 6.0 revision.";
  }

  container och-oper {
    config false;
    description
      "Och operational data";
    container och-ports {
      description
        "All Och Port operational data";
      list och-port {
        key "name";
        description
          "Och operational data";
        container och-info {
          description
            "Och operational data";
          uses OCH-EDM-INFO;
        }
        leaf name {
          type xr:Interface-name;
          description
            "Port name";
        }
      }
    }
  }
}
