module Cisco-IOS-XR-npu-cfg-macsec-fips-post-oper {
  namespace "http://cisco.com/ns/yang/Cisco-IOS-XR-npu-cfg-macsec-fips-post-oper";
  prefix npu-cfg-macsec-fips-post-oper;

  import Cisco-IOS-XR-types {
    prefix xr;
  }
  import cisco-semver {
    prefix semver;
  }

  include Cisco-IOS-XR-npu-cfg-macsec-fips-post-oper-sub1 {
    revision-date 2022-06-30;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR npu-cfg-macsec-fips-post package operational data.

     This module contains definitions
     for the following management objects:
       show-macsec-fips-post: Macsec FIPS POST operational data

     Copyright (c) 2013-2022 by Cisco Systems, Inc.
     All rights reserved.";

  revision 2022-06-30 {
    semver:module-version "1.0.0";
    description
      "Yang Schema added MACSEC FIPS Post";
  }
  revision 2019-04-05 {
    description
      "Establish semantic version baseline.";
  }
  revision 2015-11-09 {
    description
      "IOS XR 6.0 revision.";
  }

  container show-macsec-fips-post {
    config false;
    description
      "Macsec FIPS POST operational data";
    container nodes {
      description
        "Table of Nodes";
      list node {
        key "node-name";
        description
          "Information about a particular node";
        container macsec-fips-post {
          description
            "Macsec FIPS Post for Node";
          uses MACSEC-FIPS-POST-INFO;
        }
        leaf node-name {
          type xr:Node-id;
          description
            "Node name";
        }
      }
    }
  }
}
