module Cisco-IOS-XR-smart-license-act {
  namespace "http://cisco.com/ns/yang/Cisco-IOS-XR-smart-license-act";
  prefix smart-license-act;

  import cisco-semver {
    prefix semver;
  }


  include "Cisco-IOS-XR-smart-license-errors";

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR action package configuration.

     Copyright (c) 2016-2020 by Cisco Systems, Inc.
     All rights reserved.";

  revision 2020-07-09 {
    semver:module-version "1.0.0";
    description
      "IOS XR 7.4.1 revision.";
  }

  typedef operation-status-enum {
    type enumeration {
      enum "success" {
        value 0;
        description
          "Operation was a success";
      }
      enum "failed" {
        value 1;
        description
          "Operation failed";
      }
    }
    description
      "Smart license operation status";
  }

  typedef request-type-enum {
    type enumeration {
      enum "None" {
        value 0;
        description
          "ReservationSystemTypeNone";
      }
      enum "local" {
        value 1;
        description
          "ReservationSystemTypeLocal";
      }
      enum "all" {
        value 2;
        description
          "ReservationSystemTypeAll";
      }
      enum "universal" {
        value 3;
        description
          "ReservationSystemTypeUniversal";
      }
    }
    description
      "Smart license reservation request type";
  }

  grouping overall-op-status {
    description
      "Overall operation status";
    leaf operation-status {
      type operation-status-enum;
      description
        "Status of operation: Success or Failure";
    }
    leaf return-code {
      type error-enum;
      description
        "The return code";
    }
  }

  grouping smartagent-udi {
    description
      "smartagent udi";
    leaf pid {
      type string;
      description
        "The Product Identifier. Always combined with sn.";
    }
    leaf sn {
      type string;
      description
        "The system serial number. Always combined with
         pid.";
    }
    leaf vid {
      type string;
      description
        "The version identifier. Usually combined with
         pid & sn.";
    }
    leaf uuid {
      type string;
      description
        "A 32 byte hex value generated by the system.
         This will be in proper UUID format 8-4-4-4-12.
         Often used by VMs or other systems that do not
         have a hardware identifier.";
    }
    leaf suvi {
      type string;
      description
        "Free form virtual identifier often used by
         software only devices like software routers or
         VMs.";
    }
    leaf host-identifier {
      type string;
      description
        "Host identifier available on some systems.
         Typically 8 hex digits.";
    }
    leaf mac-address {
      type string;
      description
        "The MAC address of the system. This is usually
         only used if there  is nothing else available to
         be used as an identifier.";
    }
  }

  grouping udi-string-data-list {
    description
      "Return codes";
    container udi {
      description
        "UDI";
      uses smartagent-udi;
    }
    leaf data {
      type string;
      description
        "Reservation codes: Example: request code if
         reservation request is being carried out,return
         code in case of reservation return etc";
    }
  }

  grouping res-codes {
    description
      "Return codes for SLR-PLR";
    container response {
      description
        "Contains the overall status of operation and error code";
      uses overall-op-status;
    }
    leaf display-string {
      type string;
      description
        "Reservation display string";
    }
    container udi {
      description
        "UDI";
      uses smartagent-udi;
    }
    leaf request-code {
      type string;
      description
        "Reservation request code";
    }
    leaf confirmation-code {
      type string;
      description
        "Reservation request code";
    }
    leaf reservation-return-code {
      type string;
      description
        "Reservation request code";
    }
  }

  rpc de-register {
    description
      "De-register. This will immediately de-register the device.
       If state:operational-mode=opr-mode-reporting then this will return
       notsupported in output:return-code";

    output {
      container response {
        description
          "Contains the overall status of operation and error code";
        uses overall-op-status;
      }
    }
  }
  rpc renew-id {
    description
      "Under normal operations smart licensing will automatically renew
       the ID certificates used for regsitration. This command can
       be used if the customer wants to initiate a manual
       registration renewal.
       If state:operational-mode=opr-mode-reporting then this
       will return notsupported in output:return-code";

    output {
      container response {
        description
          "Contains the overall status of operation and error code";
        uses overall-op-status;
      }
    }
  }
  rpc renew-auth {
    description
      "Under normal operations smart licensing will automatically renew
       the license authorization every 30 days. This command can
       be used if the customer wants to initiate a manual
       renewal.
       If state:operational-mode=opr-mode-reporting then this
       will return notsupported in output:return-code";

    output {
      container response {
        description
          "Contains the overall status of operation and error code";
        uses overall-op-status;
      }
    }
  }
  rpc register-id-token {
    description
      "Register with an ID token.
       This will begin the registration process. Since the registration
       process will take somewhere between seconds and hours you must get the
       registration-success or registration-fail notifications
       or check the registration status in smart-license:state
       to know the status of the registration.
       If state:operational-mode=opr-mode-reporting then this
       will return notsupported in output:return-code";

    input {
      leaf id-token {
        type string {
          length "1..255";
        }
        description
          "The ID token used to register.";
      }
      leaf force {
        type boolean;
        default "false";
        description
          "Force the registration if set.";
      }
    }
    output {
      container response {
        description
          "Contains the overall status of operation and error code";
        uses overall-op-status;
      }
    }
  }
  rpc reservation-request {
    description
      "Reservation request for PLR/SLR mode";

    input {
      leaf request-type {
        type request-type-enum;
        description
          "Reservation request type";
      }
    }
    output {
      container reservation-codes {
        description
          "Contains return code information of operation";
        uses res-codes;
      }
    }
  }
  rpc reservation-return {
    description
      "Return reservation for the active system";

    input {
      leaf request-type {
        type request-type-enum;
        description
          "Reservation request type";
      }
    }
    output {
      container reservation-codes {
        description
          "Contains return code information of operation";
        uses res-codes;
      }
    }
  }
  rpc reservation-return-authorization {
    description
      "Return a smart license reservation from an authorization code.";

    input {
      leaf auth-code {
        type string;
        description
          "Auth code to be returned";
      }
      container file {
        description
          "Return auth code from file";
        leaf file-path {
          type string;
          description
            "File containing auth code to be returned";
        }
      }
    }
    output {
      container reservation-codes {
        description
          "Contains return code information of operation";
        uses res-codes;
      }
    }
  }
  rpc reservation-install {
    description
      "Install a smart license reservation authorization code";

    input {
      leaf authorization-code {
        type string;
        description
          "Install the auth code";
      }
      container file {
        description
          "Install auth code from file";
        leaf file-path {
          type string;
          description
            "File containing auth code to be installed";
        }
      }
    }
    output {
      container reservation-codes {
        description
          "Contains return code information of operation";
        uses res-codes;
      }
    }
  }
  rpc reservation-cancel {
    description
      "Cancel reservation for the active system";

    input {
      leaf request-type {
        type request-type-enum;
        description
          "Reservation request type";
      }
    }
    output {
      container response {
        description
          "Contains the overall status of operation and error code";
        uses overall-op-status;
      }
    }
  }
}
