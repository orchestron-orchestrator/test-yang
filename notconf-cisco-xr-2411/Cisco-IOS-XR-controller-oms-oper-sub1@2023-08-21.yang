submodule Cisco-IOS-XR-controller-oms-oper-sub1 {
  belongs-to Cisco-IOS-XR-controller-oms-oper {
    prefix Cisco-IOS-XR-controller-oms-oper;
  }

  import Cisco-IOS-XR-types {
    prefix xr;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR controller-oms package operational data.

     Copyright (c) 2013-2023 by Cisco Systems, Inc.
     All rights reserved.";

  revision 2023-08-21 {
    semver:module-version "1.0.0";
    description
      "Added support for Egress Amplifier Back Reflection status, Egress Amplifier Back Reflection Power and Egress Amplifier Back Reflection Ratio";
  }
  revision 2023-07-11 {
    description
      "egress-ampli-gain-config leaf data-type changed from uint32 to int32";
  }
  revision 2023-06-02 {
    description
      "Added support for tx-voa-attenuation and rx-voa-attenuation";
  }
  revision 2023-06-02 {
    description
      "Added support for ingress-ampli-osri and egress-ampli-osri";
  }
  revision 2023-06-02 {
    description
      "Added support for EDFA parameters";
  }
  revision 2022-05-23 {
    description
      "total-rx-power leaf is changed to rx-power in oms-info container";
  }
  revision 2022-03-25 {
    description
      "Added transport_admin_state for OMS controller";
  }
  revision 2021-06-28 {
    description
      "New Oper Model Added for Oms Controller";
  }
  revision 2019-04-05 {
    description
      "Establish semantic version baseline.";
  }
  revision 2015-11-09 {
    description
      "IOS XR 6.0 revision.";
  }

  typedef Amplifier-gain-range {
    type enumeration {
      enum "ampli-invalid-gain-range" {
        value 0;
        description
          "Invalid";
      }
      enum "ampli-normal-gain-range" {
        value 1;
        description
          "Normal";
      }
      enum "ampli-ext-end-ed-gain-range" {
        value 2;
        description
          "Extended";
      }
    }
    description
      "Amplifier gain range";
  }

  typedef Amplifier-working-mode {
    type enumeration {
      enum "invalid" {
        value 0;
        description
          "Invalid";
      }
      enum "gain" {
        value 1;
        description
          "Gain";
      }
      enum "power" {
        value 2;
        description
          "Power";
      }
    }
    description
      "Amplifier working mode";
  }

  typedef Ots-tas {
    type enumeration {
      enum "ots-tas-ui-oos" {
        value 0;
        description
          "Out Of Service";
      }
      enum "ots-tas-ui-main" {
        value 1;
        description
          "Maintenance";
      }
      enum "ots-tas-ui-is" {
        value 2;
        description
          "In Service";
      }
      enum "ots-tas-ui-ains" {
        value 3;
        description
          "Automatic In Service";
      }
    }
    description
      "Ots tas";
  }

  typedef Conn-verfcn-state {
    type enumeration {
      enum "conn-vrfcn-state-failed" {
        value 0;
        description
          "Failed";
      }
      enum "conn-vrfcn-state-inprogress" {
        value 1;
        description
          "Inprogress";
      }
      enum "conn-vrfcn-state-success" {
        value 2;
        description
          "Success";
      }
      enum "conn-vrfcn-state-not-running" {
        value 3;
        description
          "Notrunning";
      }
    }
    description
      "Conn verfcn state";
  }

  typedef Led-state {
    type enumeration {
      enum "off" {
        value 0;
        description
          "Off";
      }
      enum "green-on" {
        value 1;
        description
          "Green";
      }
      enum "green-flashing" {
        value 2;
        description
          "Green Flashing";
      }
      enum "yellow-on" {
        value 3;
        description
          "Yellow";
      }
      enum "yellow-flashing" {
        value 4;
        description
          "Yellow Flashing";
      }
      enum "red-on" {
        value 5;
        description
          "Red";
      }
      enum "red-flashing" {
        value 6;
        description
          "Red Flashing";
      }
      enum "na" {
        value 7;
        description
          "Not Applicable";
      }
    }
    description
      "Led state";
  }

  typedef Ots-controller-state {
    type enumeration {
      enum "ots-state-up" {
        value 0;
        description
          "Up";
      }
      enum "ots-state-down" {
        value 1;
        description
          "Down";
      }
      enum "ots-state-admin-down" {
        value 2;
        description
          "Administratively Down";
      }
    }
    description
      "Ots controller state";
  }

  grouping ALARM-INFO {
    description
      "Alarm Detail";
    leaf is-detected {
      type boolean;
      description
        "Flag to indicate if defect has been detected";
    }
    leaf counter {
      type uint32;
      description
        "Alarm counter";
    }
  }

  grouping OTS-TONE-INFO {
    description
      "Ots Tone information";
    leaf tone-freq {
      type string;
      description
        "Tone Frequency";
    }
    leaf tone-rate {
      type uint32;
      description
        "Tone Rate";
    }
    leaf pattern {
      type string;
      description
        "Tone pattern";
    }
    leaf pattern-expected {
      type string;
      description
        "Tone pattern expected";
    }
    leaf dectected-oob {
      type uint32;
      description
        "Detected OOB";
    }
    leaf state {
      xr:event-telemetry "Subscribe Telemetry Event";
      type Conn-verfcn-state;
      description
        "Connection verification state";
    }
    leaf pattern-received {
      type string;
      description
        "Tone pattern received";
    }
  }

  grouping OTS-ALARM-INFO {
    description
      "Optics Alarm Detail";
    leaf is-detected {
      type boolean;
      description
        "is defect detected?";
    }
    leaf counter {
      type uint32;
      description
        "Alarm counter";
    }
  }

  grouping OMS-EDM-INFO {
    description
      "OMS controller operational information";
    container rx-los-p {
      description
        "RC LOS P";
      uses OTS-ALARM-INFO;
    }
    container tx-power-fail-low {
      description
        "TX POWER FAIL LOW";
      uses OTS-ALARM-INFO;
    }
    container oms-tone-info {
      description
        "Oms tone info";
      uses OTS-TONE-INFO;
    }
    container ingress-ampli-gain-low {
      description
        "Information related to INGRESS-AMPLI-GAIN-LOW
         alarm";
      uses ALARM-INFO;
    }
    container ingress-ampli-gain-high {
      description
        "Information related to INGRESS-AMPLI-GAIN-HIGH
         alarm";
      uses ALARM-INFO;
    }
    container egress-auto-laser-shut {
      description
        "Information related to EGRESS-AUTO-LASER-SHUT
         alarm";
      uses ALARM-INFO;
    }
    container egress-ampli-gain-low {
      description
        "Information related to EGRESS-AMPLI-GAIN-LOW
         alarm";
      uses ALARM-INFO;
    }
    container egress-ampli-gain-high {
      description
        "Information related to EGRESS-AMPLI-GAIN-HIGH
         alarm";
      uses ALARM-INFO;
    }
    container high-tx-br-pwr {
      description
        "Information related to HIGH-TX-BR-POWER alarm";
      uses ALARM-INFO;
    }
    leaf rx-power {
      type int32;
      description
        " Receive Power for OMS in units of 0.01 dBm";
    }
    leaf tx-power {
      type int32;
      description
        " Transmit Power for OMS in units of 0.01 dBm";
    }
    leaf channel-frequency {
      type uint32;
      description
        "Frequency read from hw in the units of 0.01THz";
    }
    leaf channel-width {
      type uint32;
      description
        "Channel Width (in Unit of 0.1 GHz)";
    }
    leaf channel-wavelength {
      type uint32;
      description
        "Wavelength in unit of 0.01 nm";
    }
    leaf add-drop-port {
      type string;
      description
        "Add Drop port  ots R/S/I/P";
    }
    leaf controller-state {
      xr:event-telemetry "Subscribe Telemetry Event";
      type Ots-controller-state;
      description
        "Ots controller state: Up, Down or
         Administratively Down";
    }
    leaf led-state {
      xr:event-telemetry "Subscribe Telemetry Event";
      type Led-state;
      description
        "Showing Current Colour of led state";
    }
    leaf transport-admin-state {
      xr:event-telemetry "Subscribe Telemetry Event";
      type Ots-tas;
      description
        "Transport Admin State";
    }
    leaf ingress-ampli-gain {
      type int32;
      description
        "Ingress Ampli Gain in the unit of 0.1dB";
    }
    leaf ingress-ampli-tilt {
      type int32;
      description
        "Ingress Ampli Tilt in the unit of 0.1dB";
    }
    leaf ingress-ampli-working-mode {
      type Amplifier-working-mode;
      description
        "Ingress Amplifier working mode";
    }
    leaf egress-ampli-gain {
      type int32;
      description
        "Egress Ampli Gain in the unit of 0.1dB";
    }
    leaf egress-ampli-tilt {
      type int32;
      description
        "Egress Ampli Tilt in the unit of 0.1dB";
    }
    leaf egress-ampli-gain-range {
      type Amplifier-gain-range;
      description
        "Egress Ampli gain range";
    }
    leaf egress-ampli-working-mode {
      type Amplifier-working-mode;
      description
        "Egress Amplifier working mode";
    }
    leaf ingress-ampli-gain-config {
      type uint32;
      description
        "Ingress Ampli Gain configured value in units of
         0.1dB";
    }
    leaf egress-ampli-gain-range-config {
      type Amplifier-gain-range;
      description
        "Egress Ampli Gain Range configured value";
    }
    leaf egress-ampli-gain-config {
      type int32;
      description
        "Egress Ampli gain configured value in units of 0
         .1dB";
    }
    leaf egress-ampli-power-config {
      type int32;
      description
        "Egress Amplifier Power configured value in the
         units of 0.1 dBm";
    }
    leaf ingress-ampli-power-config {
      type int32;
      description
        "Ingress Amplifier Power configured value in the
         units of 0.1 dBm";
    }
    leaf egress-ampli-working-mode-config {
      type Amplifier-working-mode;
      description
        "Egress Amplifier configured working mode";
    }
    leaf ingress-ampli-working-mode-config {
      type Amplifier-working-mode;
      description
        "Ingress Amplifier configured working mode";
    }
    leaf rx-voa-attenuation {
      type int32;
      description
        "Rx Voa Attenuation in the units of 0.1dB";
    }
    leaf tx-voa-attenuation {
      type int32;
      description
        "Tx Voa Attenuation in the units of 0.1dB";
    }
    leaf rx-voa-attenuation-config-val {
      type int32;
      description
        "RX VOA attenuation configured value in units of
         0.1dB";
    }
    leaf tx-voa-attenuation-config-val {
      type int32;
      description
        "TX VOA attenuation configured value in units of
         0.1dB";
    }
    leaf ingress-ampli-osri {
      type boolean;
      description
        "Ingress Ampli Optical Safety Remote
         Interlock(OSRI) Status";
    }
    leaf egress-ampli-osri {
      type boolean;
      description
        "Egress Ampli Optical Safety Remote
         Interlock(OSRI) Status";
    }
    leaf ingress-ampli-osri-configured {
      type boolean;
      description
        "Ingress Amplifier Optical Safety Remote
         Interlock(OSRI) Configured Status";
    }
    leaf egress-ampli-osri-configured {
      type boolean;
      description
        "Egress Amplifier Optical Safety Remote
         Interlock(OSRI) Configured Status";
    }
    leaf egress-amplifier-back-reflection {
      type boolean;
      description
        "Egress Amplifier Back Reflection";
    }
    leaf egress-amplifier-back-reflection-configured {
      type boolean;
      description
        "Egress Amplifier Back Reflection Configured";
    }
    leaf egress-amplifier-back-reflection-high-threshold {
      type int32;
      description
        "Egress Amplifier Back Reflection High Threshold
         in units of 0.1 dBm";
    }
    leaf egress-ampli-br-power {
      type int32;
      description
        "Egress Ampli Back Reflection Power in the units
         of 0.01 dBm";
    }
    leaf egress-ampli-br-ratio {
      type int32;
      description
        "Egress Amplifier Back Reflection Ratio in the
         units of 0.01 dB";
    }
  }
}
