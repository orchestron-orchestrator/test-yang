submodule Cisco-IOS-XR-tty-show-line-oper-sub1 {
  belongs-to Cisco-IOS-XR-tty-show-line-oper {
    prefix Cisco-IOS-XR-tty-show-line-oper;
  }

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR tty-show-line package operational data.

     Copyright (c) 2013-2023 by Cisco Systems, Inc.
     All rights reserved.";

  revision 2023-06-13 {
    semver:module-version "1.1.0";
    description
      "Updated line id range";
  }
  revision 2021-08-27 {
    semver:module-version "1.0.0";
    description
      "yang support for show line";
  }
  revision 2019-04-05 {
    description
      "Establish semantic version baseline.";
  }
  revision 2015-11-09 {
    description
      "IOS XR 6.0 revision.";
  }

  grouping SHOWLINE-ENTRY {
    description
      "Per Line Information";
    leaf tty {
      type string;
      description
        "Tty id";
    }
    leaf speed {
      type uint32;
      description
        "Baud rate";
    }
    leaf hw-overrun-errors {
      type uint32;
      description
        "Hardware overruns";
    }
    leaf sw-overrun-errors {
      type uint32;
      description
        "Software overruns";
    }
    leaf ingress-access-list {
      type string;
      description
        "ingress access list";
    }
    leaf egress-access-list {
      type string;
      description
        "egress access list";
    }
  }
}
