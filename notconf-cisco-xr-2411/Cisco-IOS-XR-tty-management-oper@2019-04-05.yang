module Cisco-IOS-XR-tty-management-oper {
  namespace "http://cisco.com/ns/yang/Cisco-IOS-XR-tty-management-oper";
  prefix tty-management-oper;

  import cisco-semver {
    prefix semver;
  }
  import Cisco-IOS-XR-tty-server-oper {
    prefix a1;
  }

  include Cisco-IOS-XR-tty-management-oper-sub1 {
    revision-date 2019-04-05;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR tty-management package operational data.

     This YANG module augments the
       Cisco-IOS-XR-tty-server-oper
     module with state data.

     Copyright (c) 2013-2019 by Cisco Systems, Inc.
     All rights reserved.";

  revision 2019-04-05 {
    semver:module-version "1.0.1";
    description
      "Establish semantic version baseline.";
  }
  revision 2017-05-01 {
    description
      "Fixing backward compatibility error in module.";
  }
  revision 2015-01-07 {
    description
      "IOS XR 5.3.1 revision.";
  }

  augment "/a1:tty/a1:vty-lines/a1:vty-line" {
    description
      "This augment extends the operational data of
       'Cisco-IOS-XR-tty-server-oper'";
    container sessions {
      description
        "Outgoing sessions";
      uses CONN-OUT-TABLE-BAG;
    }
  }
}
