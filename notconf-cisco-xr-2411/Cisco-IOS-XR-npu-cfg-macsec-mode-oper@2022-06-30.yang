module Cisco-IOS-XR-npu-cfg-macsec-mode-oper {
  namespace "http://cisco.com/ns/yang/Cisco-IOS-XR-npu-cfg-macsec-mode-oper";
  prefix npu-cfg-macsec-mode-oper;

  import Cisco-IOS-XR-types {
    prefix xr;
  }
  import cisco-semver {
    prefix semver;
  }

  include Cisco-IOS-XR-npu-cfg-macsec-mode-oper-sub1 {
    revision-date 2022-06-30;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR npu-cfg-macsec-mode package operational data.

     This module contains definitions
     for the following management objects:
       show-macsec-mode: Macsec mode operational data

     Copyright (c) 2013-2022 by Cisco Systems, Inc.
     All rights reserved.";

  revision 2022-06-30 {
    semver:module-version "1.0.0";
    description
      "Yang Schema added MACSEC Mode";
  }
  revision 2019-04-05 {
    description
      "Establish semantic version baseline.";
  }
  revision 2015-11-09 {
    description
      "IOS XR 6.0 revision.";
  }

  container show-macsec-mode {
    config false;
    description
      "Macsec mode operational data";
    container nodes {
      description
        "Table of Nodes";
      list node {
        key "node-name";
        description
          "Information about a particular node";
        container macsec-mode {
          description
            "Macsec Mode for Node";
          uses MACSEC-MODE-INFO;
        }
        leaf node-name {
          type xr:Node-id;
          description
            "Node name";
        }
      }
    }
  }
}
