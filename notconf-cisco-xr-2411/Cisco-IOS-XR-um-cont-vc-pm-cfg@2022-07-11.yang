module Cisco-IOS-XR-um-cont-vc-pm-cfg {
  namespace "http://cisco.com/ns/yang/Cisco-IOS-XR-um-cont-vc-pm-cfg";
  prefix um-cont-vc-pm-cfg;

  import Cisco-IOS-XR-um-interface-cfg {
    prefix a1;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR cont-vc-pm package configuration.

     This YANG module augments the
     modules with configuration data.

     Copyright (c) 2021-2022 by Cisco Systems, Inc.
     All rights reserved.";

  revision 2022-07-11 {
    semver:module-version "1.1.0";
    description
      "Added missing description statement to nodes
       2022-06-01
         Adjusted controller augmentation hierarchy";
  }
  revision 2021-02-22 {
    semver:module-version "1.0.0";
    description
      "Initial release";
  }

  grouping CONT-BODY {
    description
      "Grouping for controller";
    container pm {
      description
        "Configure pm parameters";
      container interval-15-min {
        description
          "Configure pm parameters of 15 minute interval";
        container ho-vc {
          description
            "configure HO_VC performance monitoring";
          container threshold {
            description
              "Configure threshold on ho_vc parameters";
            leaf eb-p {
              type uint32 {
                range "0..8850600" {
                  description
                    "EB-P threshold range";
                }
              }
              description
                "set eb-p threshold";
            }
            leaf es-p {
              type uint32 {
                range "0..900" {
                  description
                    "es-p threshold range";
                }
              }
              description
                "set es-p threshold";
            }
            leaf esr-p {
              type uint32 {
                range "0..100000" {
                  description
                    "esr-p threshold range";
                }
              }
              description
                "set esr-p threshold";
            }
            leaf ses-p {
              type uint32 {
                range "0..900" {
                  description
                    "ses-p threshold range";
                }
              }
              description
                "set ses-p threshold";
            }
            leaf sesr-p {
              type uint32 {
                range "0..100000" {
                  description
                    "sesr-p threshold range";
                }
              }
              description
                "set sesr-p threshold";
            }
            leaf bbe-p {
              type uint32 {
                range "0..8850600" {
                  description
                    "bbe-p threshold range";
                }
              }
              description
                "set bbe-p threshold";
            }
            leaf bber-p {
              type uint32 {
                range "0..100000" {
                  description
                    "bber-p threshold range";
                }
              }
              description
                "set bber-p threshold";
            }
            leaf uas-p {
              type uint32 {
                range "0..900" {
                  description
                    "uas-p threshold range";
                }
              }
              description
                "set uas-p threshold";
            }
          }
          container reports {
            description
              "set ho_vc TCA reporting status";
            list report {
              must "enable or disable";
              key "report-id";
              description
                "set ho_vc TCA reporting status";
              leaf report-id {
                type enumeration {
                  enum "eb-p" {
                    value 33554432;
                    description
                      "set eb TCA reporting status";
                  }
                  enum "es-p" {
                    value 33554433;
                    description
                      "set es TCA reporting status";
                  }
                  enum "esr-p" {
                    value 33554434;
                    description
                      "set esr TCA reporting status";
                  }
                  enum "ses-p" {
                    value 33554435;
                    description
                      "set ses TCA reporting status";
                  }
                  enum "sesr-p" {
                    value 33554436;
                    description
                      "set sesr TCA reporting status";
                  }
                  enum "bbe-p" {
                    value 33554437;
                    description
                      "set bbe TCA reporting status";
                  }
                  enum "bber-p" {
                    value 33554438;
                    description
                      "set bber TCA reporting status";
                  }
                  enum "uas-p" {
                    value 33554439;
                    description
                      "set uas TCA reporting status";
                  }
                }
                description
                  "set ho_vc TCA reporting status";
              }
              container enable {
                must "not(../disable)";
                presence "Indicates a enable node is configured.";
                description
                  "";
              }
              container disable {
                must "not(../enable)";
                presence "Indicates a disable node is configured.";
                description
                  "";
              }
            }
          }
        }
      }
      container interval-24-hour {
        description
          "Configure pm parameters of 24 hour interval";
        container ho-vc {
          description
            "configure HO_VC performance monitoring";
          container threshold {
            description
              "Configure threshold on ho_vc parameters";
            leaf eb-p {
              type uint32 {
                range "0..849657600" {
                  description
                    "EB-P threshold range";
                }
              }
              description
                "set eb-p threshold";
            }
            leaf es-p {
              type uint32 {
                range "0..86400" {
                  description
                    "es-p threshold range";
                }
              }
              description
                "set es-p threshold";
            }
            leaf esr-p {
              type uint32 {
                range "0..100000" {
                  description
                    "esr-p threshold range";
                }
              }
              description
                "set esr-p threshold";
            }
            leaf ses-p {
              type uint32 {
                range "0..86400" {
                  description
                    "ses-p threshold range";
                }
              }
              description
                "set ses-p threshold";
            }
            leaf sesr-p {
              type uint32 {
                range "0..100000" {
                  description
                    "sesr-p threshold range";
                }
              }
              description
                "set sesr-p threshold";
            }
            leaf bbe-p {
              type uint32 {
                range "0..849657600" {
                  description
                    "bbe-p threshold range";
                }
              }
              description
                "set bbe-p threshold";
            }
            leaf bber-p {
              type uint32 {
                range "0..100000" {
                  description
                    "bber-p threshold range";
                }
              }
              description
                "set bber-p threshold";
            }
            leaf uas-p {
              type uint32 {
                range "0..86400" {
                  description
                    "uas-p threshold range";
                }
              }
              description
                "set uas-p threshold";
            }
          }
          container reports {
            description
              "set ho_vc TCA reporting status";
            list report {
              must "enable or disable";
              key "report-id";
              description
                "set ho_vc TCA reporting status";
              leaf report-id {
                type enumeration {
                  enum "eb-p" {
                    value 33554432;
                    description
                      "set eb TCA reporting status";
                  }
                  enum "es-p" {
                    value 33554433;
                    description
                      "set es TCA reporting status";
                  }
                  enum "esr-p" {
                    value 33554434;
                    description
                      "set esr TCA reporting status";
                  }
                  enum "ses-p" {
                    value 33554435;
                    description
                      "set ses TCA reporting status";
                  }
                  enum "sesr-p" {
                    value 33554436;
                    description
                      "set sesr TCA reporting status";
                  }
                  enum "bbe-p" {
                    value 33554437;
                    description
                      "set bbe TCA reporting status";
                  }
                  enum "bber-p" {
                    value 33554438;
                    description
                      "set bber TCA reporting status";
                  }
                  enum "uas-p" {
                    value 33554439;
                    description
                      "set uas TCA reporting status";
                  }
                }
                description
                  "set ho_vc TCA reporting status";
              }
              container enable {
                must "not(../disable)";
                presence "Indicates a enable node is configured.";
                description
                  "";
              }
              container disable {
                must "not(../enable)";
                presence "Indicates a disable node is configured.";
                description
                  "";
              }
            }
          }
        }
      }
    }
  }

  augment "/a1:controllers/a1:controller" {
    description
      "This augment extends active nodes configuration";
    uses CONT-BODY;
  }
  augment "/a1:controllers/a1:controller-preconfigure" {
    description
      "This augment extends preconfigured nodes
       configuration";
    uses CONT-BODY;
  }
}
