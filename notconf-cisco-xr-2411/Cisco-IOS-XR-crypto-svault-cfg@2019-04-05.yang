module Cisco-IOS-XR-crypto-svault-cfg {
  namespace "http://cisco.com/ns/yang/Cisco-IOS-XR-crypto-svault-cfg";
  prefix crypto-svault-cfg;

  import ietf-inet-types {
    prefix inet;
  }
  import Cisco-IOS-XR-types {
    prefix xr;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR crypto-svault package configuration.

     This module contains definitions
     for the following management objects:
       svault: Secure Vault configuration

     Copyright (c) 2013-2019 by Cisco Systems, Inc.
     All rights reserved.";

  revision 2019-04-05 {
    semver:module-version "1.0.0";
    description
      "Establish semantic version baseline.";
  }
  revision 2015-11-09 {
    description
      "IOS XR 6.0 revision.";
  }

  container svault {
    description
      "Secure Vault configuration";
    container svault-server {
      description
        "Secure Vault Server configuration";
      container svault-server-address {
        description
          "Secure Vault server address configuration";
        leaf svault-server-address-port {
          type uint32 {
            range "1024..49151";
          }
          default "8200";
          description
            "Secure Vault server port configuration";
        }
        leaf svault-server-address-ipv4 {
          type inet:ip-address-no-zone;
          description
            "Secure Vault server IPv4 address configuration";
        }
      }
      leaf svault-server-enable {
        type boolean;
        default "false";
        description
          "If set, secure vault server is enabled and
           started";
      }
    }
    container svault-profile-names {
      description
        "Secure Vault profile configuration";
      list svault-profile-name {
        key "svault-profile-name-str";
        description
          "Secure Vault profile name configuration";
        container svault-profile-global {
          description
            "Secure Vault profile global configuration";
          leaf svault-profile-global-path-env {
            type xr:Cisco-ios-xr-string {
              length "1..255";
            }
            description
              "Secure Vault path environment variable tag";
          }
          leaf svault-profile-global-addr-env {
            type xr:Cisco-ios-xr-string {
              length "1..255";
            }
            description
              "Secure Vault address environment variable tag";
          }
          leaf svault-profile-global-token-env {
            type xr:Cisco-ios-xr-string {
              length "1..255";
            }
            description
              "Secure Vault Token environment variable tag";
          }
        }
        container svault-profile-policy-names {
          description
            "Secure Vault Profile Policy tag";
          list svault-profile-policy-name {
            key "svault-policy-name-str";
            description
              "Secure Vault Profile Policy config tag";
            container svault-profile-policy-path-names {
              description
                "Secure Vault Profile Policy Path tag";
              list svault-profile-policy-path-name {
                key "svault-policy-path-name-str";
                description
                  "Secure Vault Profile Policy Path tag";
                container svault-profile-policy-path-cap {
                  presence "enable svault-profile-policy-path-cap";
                  description
                    "Secure Vault Policy Path Capabilities tag";
                  leaf svault-read-cap {
                    type uint32 {
                      range "0..1";
                    }
                    description
                      "Secure Vault Read Capability";
                  }
                  leaf svault-write-cap {
                    type uint32 {
                      range "0..1";
                    }
                    description
                      "Secure Vault Write Capability";
                  }
                  leaf svault-update-cap {
                    type uint32 {
                      range "0..1";
                    }
                    description
                      "Secure Vault Update Capability";
                  }
                  leaf svault-delete-cap {
                    type uint32 {
                      range "0..1";
                    }
                    description
                      "Secure Vault Delete Capability";
                  }
                }
                leaf svault-policy-path-name-str {
                  type xr:Cisco-ios-xr-string {
                    length "1..255";
                  }
                  description
                    "Policy Path Name";
                }
              }
            }
            leaf svault-pro-pol-preserve-data {
              type boolean;
              default "false";
              description
                "If set, path and data will be preserved
                 after policy deletion";
            }
            leaf svault-policy-name-str {
              type xr:Cisco-ios-xr-string {
                length "1..255";
              }
              description
                "Policy Name";
            }
          }
        }
        container svault-profile-auth-method {
          description
            "Secure Vault auth method type";
          container svault-profile-auth-method-token {
            presence "Indicates a svault-profile-auth-method-token node is configured.";
            description
              "Secure Vault auth method token tag";
            leaf svault-profile-auth-method-token-ttl {
              type uint32 {
                range "1..768";
              }
              description
                "Secure Vault auth method token ttl tag";
            }
            leaf svault-profile-auth-method-token-enter {
              type empty;
              mandatory true;
              description
                "This indicates token auth method has been
                 chosen";
            }
          }
        }
        leaf svault-profile-name-str {
          type xr:Cisco-ios-xr-string {
            length "1..255";
          }
          description
            "Profile Name";
        }
      }
    }
  }
}
