submodule Cisco-IOS-XR-controller-odg-oper-sub2 {
  belongs-to Cisco-IOS-XR-controller-odg-oper {
    prefix Cisco-IOS-XR-controller-odg-oper;
  }

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR controller-odg package operational data.

     Copyright (c) 2013-2019 by Cisco Systems, Inc.
     All rights reserved.";

  revision 2019-04-05 {
    semver:module-version "1.0.0";
    description
      "Establish semantic version baseline.";
  }
  revision 2015-11-09 {
    description
      "IOS XR 6.0 revision.";
  }

  typedef Dp-programmed {
    type enumeration {
      enum "dp-not-programmed" {
        description
          "DP not programmed";
      }
      enum "dp-programmed-success" {
        description
          "DP programmed";
      }
      enum "end-pt-first-channel-ized" {
        description
          "ENDPT FIRST CHANNELIZED";
      }
      enum "end-pt-se-cond-channel-ized" {
        description
          "ENDPT SECOND CHANNELIZED";
      }
      enum "end-pt-first-cross-connected" {
        description
          "ENDPT FIRST CROSS CONNECTED";
      }
      enum "end-pt-se-cond-cross-connected" {
        description
          "ENDPT SECOND CROSS CONNECTED";
      }
      enum "end-pt-first-open-connected" {
        description
          "ENDPT FIRST OPEN CONNECTED";
      }
      enum "end-pt-se-cond-open-connected" {
        description
          "ENDPT SECOND OPEN CONNECTED";
      }
      enum "end-pt-first-loop-back-ed" {
        description
          "ENDPT FIRST LOOPBACKED";
      }
      enum "end-pt-se-cond-loop-back-ed" {
        description
          "ENDPT SECOND LOOPBACKED";
      }
      enum "end-pt-odu-type-mismatch" {
        description
          "ENDPT ODU TYPE MISMATCH";
      }
      enum "xc-not-set" {
        description
          "XCONNECT NOT SET";
      }
    }
    description
      "Dp programmed";
  }

  typedef Odg-resource-et {
    type enumeration {
      enum "re-source-free" {
        description
          "ODG Resource Free";
      }
      enum "open-connect-ion" {
        description
          "ODG Open Connection";
      }
      enum "cross-connected" {
        description
          "ODG Cross Connection";
      }
      enum "is-channel-ized" {
        description
          "ODG Channelized";
      }
    }
    description
      "Odg resource et";
  }

  typedef Odg-user-et {
    type enumeration {
      enum "user-mp" {
        description
          "MP ";
      }
      enum "user-gmpls" {
        description
          "GMPLS ";
      }
      enum "user-all" {
        description
          "ALL ";
      }
    }
    description
      "Odg user et";
  }

  typedef Odg-protection-switching-et {
    type enumeration {
      enum "ns" {
        description
          "NO SWITCHOVER";
      }
      enum "ex" {
        description
          "EXERCISE";
      }
      enum "ma" {
        description
          "MANUAL";
      }
      enum "fo" {
        description
          "FORCED";
      }
      enum "lo" {
        description
          "LOCKOUT";
      }
      enum "cl" {
        description
          "CLEAR";
      }
    }
    description
      "Odg protection switching et";
  }

  typedef P-type-et {
    type enumeration {
      enum "no" {
        description
          "No Protection";
      }
      enum "uni" {
        description
          "1+1 Unidirectional Protection";
      }
      enum "bi" {
        description
          "1+1 Bidirectional Protection";
      }
      enum "no-aps" {
        description
          "1+1 Unidirectional Protection(without APS byte)";
      }
      enum "one-n" {
        description
          "1:N Unidirectional Protection";
      }
      enum "one-one-r" {
        description
          "1+1+R Bi-directional APS";
      }
    }
    description
      "P type et";
  }

  typedef Prot-snc-et {
    type enumeration {
      enum "no" {
        description
          "NOT SET";
      }
      enum "i" {
        description
          "SNC I";
      }
      enum "n" {
        description
          "SNC N";
      }
      enum "s" {
        description
          "SNC S";
      }
    }
    description
      "Prot snc et";
  }

  typedef Prot-signal-state-et {
    type enumeration {
      enum "signal-state-ok" {
        description
          "State Ok";
      }
      enum "signal-state-wtr" {
        description
          "Wait to Restore";
      }
      enum "signal-state-degrade" {
        description
          "Signal Degrade";
      }
      enum "signal-state-failure" {
        description
          "Signal Failure";
      }
      enum "signal-state-not-applicable" {
        description
          "Not Applicable";
      }
      enum "signal-state-unsupported" {
        description
          "Unspported";
      }
    }
    description
      "Prot signal state et";
  }

  typedef Prot-state-et {
    type enumeration {
      enum "not-present" {
        description
          "Not present";
      }
      enum "state-active" {
        description
          "Active";
      }
      enum "state-active-tx" {
        description
          "Active tx";
      }
      enum "state-active-rx" {
        description
          "Active rx";
      }
      enum "state-not-active" {
        description
          "Not Active";
      }
      enum "state-failed" {
        description
          "Failed";
      }
      enum "state-extra" {
        description
          "Extra";
      }
      enum "state-unsupported" {
        description
          "Unsupported";
      }
    }
    description
      "Prot state et";
  }

  typedef Otm-mpls-lib-c {
    type enumeration {
      enum "otm-mpls-lib-c-type-null" {
        value 0;
        description
          "NULL";
      }
      enum "otm-mpls-lib-c-type-ipv4" {
        value 1;
        description
          "IPV4";
      }
      enum "otm-mpls-lib-c-type-ipv4-p2p-tunnel" {
        value 7;
        description
          "IPV4 P2P TUNNEL";
      }
      enum "otm-mpls-lib-c-type-ipv6-p2p-tunnel" {
        value 8;
        description
          "IPV6 P2P TUNNEL";
      }
      enum "otm-mpls-lib-c-type-ipv4-uni" {
        value 9;
        description
          "IPV4 UNI";
      }
      enum "otm-mpls-lib-c-type-ipv4-p2mp-tunnel" {
        value 13;
        description
          "IPV4 P2MP TUNNEL";
      }
      enum "otm-mpls-lib-c-type-ipv6-p2mp-tunnel" {
        value 14;
        description
          "IPV6 P2MP TUNNEL";
      }
      enum "otm-mpls-lib-c-type-ipv4-tp-tunnel" {
        value 15;
        description
          "IPV4 TP TUNNEL";
      }
      enum "otm-mpls-lib-c-type-ipv6-tp-tunnel" {
        value 16;
        description
          "IPV6 TP TUNNEL";
      }
    }
    description
      "Otm mpls lib c";
  }

  typedef Otm-te-tunnel-info {
    type enumeration {
      enum "otm-te-info-none" {
        description
          "NONE";
      }
      enum "otm-te-info-s2l" {
        description
          "S2L";
      }
      enum "otm-te-info-tunnel-id" {
        description
          "ID";
      }
      enum "otm-te-info-passive-match" {
        description
          "MAT";
      }
    }
    description
      "Otm te tunnel info";
  }

  typedef Otm-optical-rm-ctxt-rm {
    type enumeration {
      enum "otm-opt-rm-ctxt-rm-none" {
        description
          "NONE";
      }
      enum "otm-opt-rm-ctxt-rm-wdm" {
        description
          "WDM";
      }
      enum "otm-opt-rm-ctxt-rm-fsc" {
        description
          "FSC";
      }
      enum "otm-opt-rm-ctxt-rm-tdm" {
        description
          "TDM";
      }
      enum "otm-opt-rm-ctxt-rm-g709-otn" {
        description
          "G709 OTN";
      }
      enum "otm-optical-rm-ctxt-rm-last" {
        description
          "LAST";
      }
    }
    description
      "Otm optical rm ctxt rm";
  }

  typedef Otm-optical-rm-ctxt {
    type enumeration {
      enum "otm-opt-rm-ctxt-type-none" {
        description
          "NONE";
      }
      enum "otm-opt-rm-ctxt-type-down-stream-rw-add" {
        description
          "DOWNSTREAM RW ADD";
      }
      enum "otm-opt-rm-ctxt-type-up-stream-rw-add" {
        description
          "UPSTREAM RW ADD";
      }
      enum "otm-opt-rm-ctxt-type-down-stream-rw-del" {
        description
          "DOWNSTREAM RW DEL";
      }
      enum "otm-opt-rm-ctxt-type-up-stream-rw-del" {
        description
          "UPSTREAM RW DEL";
      }
      enum "otm-opt-rm-ctxt-type-down-stream-lbl-get" {
        description
          "DOWNSTREAM LBL GET";
      }
      enum "otm-opt-rm-ctxt-type-up-stream-lbl-get" {
        description
          "UPSTREAM LBL GET";
      }
      enum "otm-opt-rm-ctxt-type-down-stream-lbl-rel" {
        description
          "DOWNSTREAM LBL REL";
      }
      enum "otm-opt-rm-ctxt-type-up-stream-lbl-rel" {
        description
          "UPSTREAM LBL REL";
      }
      enum "otm-opt-rm-ctxt-type-end-point-rw-add" {
        description
          "ENDPOINT RW ADD";
      }
      enum "otm-opt-rm-ctxt-type-end-point-rw-del" {
        description
          "ENDPOINT RW DEL";
      }
      enum "otm-opt-rm-ctxt-type-odu-group-add" {
        description
          "ODU GROUP ADD";
      }
      enum "otm-opt-rm-ctxt-type-odu-group-del" {
        description
          "ODU GROUP DEL";
      }
      enum "otm-optical-rm-ctxt-type-last" {
        description
          "LAST";
      }
    }
    description
      "Otm optical rm ctxt";
  }

  typedef Role {
    type enumeration {
      enum "n-o" {
        description
          "NOT SET";
      }
      enum "w" {
        description
          "WORKING";
      }
      enum "p" {
        description
          "PROTECT";
      }
      enum "r" {
        description
          "RESTORE";
      }
    }
    description
      "Role";
  }

  grouping ODG-APS-EDM-ALARM {
    description
      " ODG APS Alarm";
    leaf is-detected {
      type boolean;
      description
        "Flag to indicate if the alarm is detected";
    }
  }

  grouping ODG-APS-ALARM-INFO {
    description
      "ODG APS Alarm";
    container switched-to-restore {
      description
        "Switched To Restore";
      uses ODG-APS-EDM-ALARM;
    }
    container switched-to-protection {
      description
        "Switched To Protection";
      uses ODG-APS-EDM-ALARM;
    }
    container lockout-switch-request {
      description
        "Lockout Switch Request On Controller or
         Equipment or UPSR or SNC";
      uses ODG-APS-EDM-ALARM;
    }
    container force-switch-request {
      description
        "Force Switch Request On Controller or Equipment
         or UPSR or SNC";
      uses ODG-APS-EDM-ALARM;
    }
    container manual-switch-request {
      description
        "Manual Switch Request On Controller or Equipment
         or UPSR or SNC";
      uses ODG-APS-EDM-ALARM;
    }
    container wait-to-restore {
      description
        "Wait To Restore";
      uses ODG-APS-EDM-ALARM;
    }
    container failure-to-switch-to-protection {
      description
        "Failure To Switch To Protection";
      uses ODG-APS-EDM-ALARM;
    }
  }

  grouping ODG-FWD-REF-ODG-INFO {
    description
      "ODG FWD_REFERENCE ODU Information";
    leaf od-guser {
      type Odg-user-et;
      description
        " ODU user Information";
    }
    leaf resource-state {
      type Odg-resource-et;
      description
        "resource state information";
    }
    leaf od-ustate {
      type Prot-state-et;
      description
        "odu state";
    }
    leaf local-failure {
      type boolean;
      description
        "Local Failure";
    }
    leaf remote-failure {
      type boolean;
      description
        "Remote Failure";
    }
  }

  grouping ODG-REST-INFO {
    description
      "restore information";
    leaf rev {
      type boolean;
      description
        "revertive";
    }
  }

  grouping ODG-PROT-INFO {
    description
      "protection params";
    leaf contype {
      type Prot-snc-et;
      description
        "connection type";
    }
    leaf prtype {
      type P-type-et;
      description
        "protection type";
    }
    leaf rev {
      type boolean;
      description
        "revertive";
    }
    leaf wot {
      type uint32;
      description
        "wait off timer";
    }
    leaf hot {
      type uint32;
      description
        "hold off timer";
    }
    leaf tcmid {
      type uint8;
      description
        "tcmid";
    }
  }

  grouping OTM-MTE-VIF-PASSIVE-MATCH-INFO {
    description
      "MTE VIF Passive Match Information";
    leaf src-tid {
      type uint16;
      description
        "Src TId";
    }
    leaf src-rid {
      type uint32;
      description
        "Src RId";
    }
  }

  grouping OTM-S2L-FEC {
    description
      "S2L FEC Information";
    leaf s2l-fec-sub-group-id {
      type uint16;
      description
        "SubGroup Id";
    }
    leaf s2l-fec-lsp-id {
      type uint16;
      description
        "Lsp Id";
    }
    leaf s2l-fec-tunnel-id {
      type uint16;
      description
        "Tunnel Id";
    }
    leaf ext-tunnel-id {
      type uint32;
      description
        "Ext Tunnel Id";
    }
    leaf fec-source {
      type uint32;
      description
        "FEC Source";
    }
    leaf fec-dest {
      type uint32;
      description
        "FEC Dest";
    }
    leaf s2l-fec-p2mp-id {
      type uint32;
      description
        "P2MP Id";
    }
    leaf sub-group-origin-ator {
      type uint32;
      description
        "SubGroup Originator";
    }
    leaf fec-c-type {
      type Otm-mpls-lib-c;
      description
        "Ctype";
    }
  }

  grouping OTM-TE-TUNNEL-INFO-UNION {
    description
      "OTM TE TUNNEL INFO UNION";
    container lb-ctxt {
      when "../info-type = 'otm-te-info-s2l'" {
        description
          "../INFO_TYPE = 'OTM_TE_INFO_S2l'";
      }
      description
        "Lbl Ctxt";
      uses OTM-S2L-FEC;
    }
    container passive-match {
      when "../info-type = 'otm-te-info-passive-match'" {
        description
          "../INFO_TYPE = 'OTM_TE_INFO_PASSIVE_MATCH'";
      }
      description
        "Passive Match";
      uses OTM-MTE-VIF-PASSIVE-MATCH-INFO;
    }
    leaf info-type {
      type Otm-te-tunnel-info;
      description
        "INFO TYPE";
    }
    leaf tunnel-id {
      when "../info-type = 'otm-te-info-tunnel-id'" {
        description
          "../INFO_TYPE = 'OTM_TE_INFO_TUNNEL_ID'";
      }
      type uint32;
      description
        "Tunnel Id";
    }
  }

  grouping OTM-OPTICAL-RM-CTXT-DATA {
    description
      "TE Optical RM CTXT Data Information";
    container te-tunnel-info {
      description
        "Tunnel Information";
      uses OTM-TE-TUNNEL-INFO-UNION;
    }
    leaf gmpls-req-time {
      type uint32;
      description
        "Req Time";
    }
    leaf ctxt-type {
      type Otm-optical-rm-ctxt;
      description
        "Ctxt Type";
    }
    leaf rm-type {
      type Otm-optical-rm-ctxt-rm;
      description
        "Rm Type";
    }
  }

  grouping ODU-CTRL-REFER-ST {
    description
      "odu info";
    container odg-rem-ctx-data {
      description
        "Odu Group Delete Data";
      uses OTM-OPTICAL-RM-CTXT-DATA;
    }
    container odg-add-ctx-data {
      description
        "Odu Group Add Data";
      uses OTM-OPTICAL-RM-CTXT-DATA;
    }
    leaf odu-name {
      type string;
      description
        "odu name";
    }
    leaf odurole {
      type Role;
      description
        "odu role";
    }
    leaf odustate {
      type Prot-state-et;
      description
        "odu state";
    }
    leaf local-failure {
      type Prot-signal-state-et;
      description
        "Local Failure";
    }
    leaf remote-failure {
      type Prot-signal-state-et;
      description
        "Remote Failure";
    }
  }

  grouping ODG-EDM-PORT-INFO {
    description
      "ODG  information";
    container workodu {
      description
        "working odu";
      uses ODU-CTRL-REFER-ST;
    }
    container protodu {
      description
        "protect odu";
      uses ODU-CTRL-REFER-ST;
    }
    container restodu {
      description
        "restore odu";
      uses ODU-CTRL-REFER-ST;
    }
    container protinfo {
      description
        "protection params";
      uses ODG-PROT-INFO;
    }
    container restinfo {
      description
        "restore params";
      uses ODG-REST-INFO;
    }
    container odg-fwd-ref-info {
      description
        "ODG fwd_ref odg Information";
      uses ODG-FWD-REF-ODG-INFO;
    }
    container odg-xc-add-ctx-data {
      description
        "Odu Group Xconnect Add Data";
      uses OTM-OPTICAL-RM-CTXT-DATA;
    }
    container odg-xc-rem-ctx-data {
      description
        "Odu Group Xconnect Delete Data";
      uses OTM-OPTICAL-RM-CTXT-DATA;
    }
    container alarm {
      description
        "Alarm";
      uses ODG-APS-ALARM-INFO;
    }
    leaf odugroupid {
      type uint32;
      description
        "odu group id";
    }
    leaf state {
      type uint32;
      description
        "Admin State";
    }
    leaf last-user-switch-cmd {
      type Odg-protection-switching-et;
      description
        "Last User Protection switchover cmd";
    }
    leaf protect {
      type boolean;
      description
        "is protect set";
    }
    leaf fwd-ref {
      type string {
        length "0..64";
      }
      description
        "fwd_ref information";
    }
    leaf xconnect-name {
      type string;
      description
        "xconnect name information";
    }
    leaf xc-id {
      type uint32;
      description
        "xconnect id information";
    }
    leaf fwd-ref-ifhandle {
      type uint32;
      description
        "fwd_ref ifhandle information";
    }
    leaf xc-resp-code {
      type Dp-programmed;
      description
        "Odu Group Xconnect Response code";
    }
  }
}
