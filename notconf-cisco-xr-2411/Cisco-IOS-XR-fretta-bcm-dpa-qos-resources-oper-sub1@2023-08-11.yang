submodule Cisco-IOS-XR-fretta-bcm-dpa-qos-resources-oper-sub1 {
  belongs-to Cisco-IOS-XR-fretta-bcm-dpa-qos-resources-oper {
    prefix Cisco-IOS-XR-fretta-bcm-dpa-qos-resources-oper;
  }

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR fretta-bcm-dpa-qos-resources package operational data.

     Copyright (c) 2013-2023 by Cisco Systems, Inc.
     All rights reserved.";

  revision 2023-08-11 {
    semver:module-version "1.0.0";
    description
      "Added reserved connector count and per-interface usage to bcmdpa_qos_connectors_info_per_core";
  }
  revision 2023-06-06 {
    description
      "Added schema for qos connectors resource utilization cli";
  }
  revision 2019-04-05 {
    description
      "Establish semantic version baseline.";
  }
  revision 2015-11-09 {
    description
      "IOS XR 6.0 revision.";
  }

  grouping BCMDPA-QOS-CONNECTORS-INFO-PER-CORE {
    description
      "QoS connectors info per core";
    leaf core-id {
      type uint16;
      description
        "Core ID";
    }
    leaf total-count {
      type uint32;
      description
        "Total connectors count";
    }
    leaf used-count {
      type uint32;
      description
        "Number of connectors used";
    }
    leaf free-count {
      type uint32;
      description
        "Number of free connectors";
    }
    leaf reserved-count {
      type uint32;
      description
        "Number of reserved connectors";
    }
    leaf per-interface-count {
      type uint32;
      description
        "Number of connectors used by one interface";
    }
    leaf lowrate-total-count {
      type uint32;
      description
        "Total low-rate connectors count";
    }
    leaf lowrate-used-count {
      type uint32;
      description
        "Number of low-rate connectors used";
    }
    leaf lowrate-free-count {
      type uint32;
      description
        "Number of free low-rate connectors";
    }
  }

  grouping BCMDPA-QOS-CONNECTORS-INFO {
    description
      "QoS connectors info";
    leaf num-cores {
      type uint16;
      description
        "Number of cores supporetd";
    }
    list core {
      key "core-id";
      max-elements 2;
      description
        "bag to store per core info";
      uses BCMDPA-QOS-CONNECTORS-INFO-PER-CORE;
    }
  }
}
