submodule Cisco-IOS-XR-tunnel-vpdn-oper-sub1 {
  belongs-to Cisco-IOS-XR-tunnel-vpdn-oper {
    prefix Cisco-IOS-XR-tunnel-vpdn-oper;
  }

  import ietf-inet-types {
    prefix inet;
  }
  import Cisco-IOS-XR-types {
    prefix xr;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR tunnel-vpdn package operational data.

     Copyright (c) 2013-2023 by Cisco Systems, Inc.
     All rights reserved.";

  revision 2023-07-21 {
    semver:module-version "1.1.0";
    description
      "Added good description for tunnel vpdn yang model.";
  }
  revision 2019-04-05 {
    semver:module-version "1.0.1";
    description
      "Establish semantic version baseline.";
  }
  revision 2015-11-09 {
    description
      "IOS XR 6.0 revision.";
  }

  typedef Vpdn-failcode {
    type enumeration {
      enum "unknown" {
        description
          "Unknown";
      }
      enum "peer-action" {
        description
          "Peer action";
      }
      enum "authentication" {
        description
          "Authentication";
      }
      enum "authentication-error" {
        description
          "Authentication";
      }
      enum "authentication-failed" {
        description
          "Authentication";
      }
      enum "authorization" {
        description
          "Authorization";
      }
      enum "authorization-failed" {
        description
          "Authorization";
      }
      enum "home-gatewayfailure" {
        description
          "No resources available";
      }
      enum "connection-termination" {
        description
          "Connection termination";
      }
      enum "no-resources-available" {
        description
          "No resources available";
      }
      enum "timer-expiry" {
        description
          "Timer expiry";
      }
      enum "session-mid-exceeded" {
        description
          "Session limit";
      }
      enum "soft-shut" {
        description
          "Softshut";
      }
      enum "session-limit-exceeded" {
        description
          "Session limit";
      }
      enum "administrative" {
        description
          "Administrative";
      }
      enum "link-failure" {
        description
          "Link failure";
      }
      enum "security" {
        description
          "Security";
      }
      enum "tunnel-in-resync" {
        description
          "Tunnel in HA resync";
      }
      enum "call-prarmeters" {
        description
          "Call parameters";
      }
    }
    description
      "VPDN failure types";
  }

  typedef Vpdn-state {
    type enumeration {
      enum "initial-state" {
        description
          "Initial state";
      }
      enum "init-sync-in-progress" {
        description
          "Initial Sync in progress";
      }
      enum "steady-state" {
        description
          "Initial Sync Done";
      }
    }
    description
      "Vpdn states";
  }

  typedef Lsg-status {
    type enumeration {
      enum "none" {
        value 0;
        description
          "Member not initialized.";
      }
      enum "active" {
        value 1;
        description
          "Member is active.";
      }
      enum "down" {
        value 2;
        description
          "Member is down, cannot create new sessions.";
      }
      enum "testable" {
        value 3;
        description
          "Member is ready for new sessions.";
      }
      enum "testing" {
        value 4;
        description
          "Member is being tested for new session";
      }
    }
    description
      "LSG Status";
  }

  typedef Tos-mode {
    type enumeration {
      enum "default" {
        value 0;
        description
          "default";
      }
      enum "set" {
        value 1;
        description
          "set";
      }
      enum "reflect" {
        value 2;
        description
          "reflect";
      }
    }
    description
      "TOS modes";
  }

  typedef Session-state {
    type enumeration {
      enum "idle" {
        description
          "Idle state";
      }
      enum "connected" {
        description
          "Connected state";
      }
      enum "established" {
        description
          "Established state";
      }
    }
    description
      "Session states";
  }

  grouping VPDN-HISTORY-ENTRY {
    description
      "VPDN history data";
    leaf username-xr {
      type string;
      description
        "Authentication username";
    }
    leaf domain-name {
      type string;
      description
        "Virtual Private Dialup Network Domain name";
    }
    leaf mid {
      type uint16;
      description
        "Virtual Private Dialup Network user session ID";
    }
    leaf nas {
      type string;
      description
        "Network access server";
    }
    leaf destination-address {
      type inet:ipv4-address;
      description
        "NAS IP address";
    }
    leaf remote-client-id {
      type uint16;
      description
        "Remote client ID";
    }
    leaf home-gateway {
      type string;
      description
        "Home gateway";
    }
    leaf source-address {
      type inet:ipv4-address;
      description
        "Source IP address";
    }
    leaf local-client-id {
      type uint16;
      description
        "Local client ID";
    }
    leaf event-time {
      type string;
      description
        "Event logged time in Ex: Wed Aug  3 10:28:30
         2011";
    }
    leaf error-repeat-count {
      type uint16;
      description
        "Error repeat count";
    }
    leaf failure-type {
      type Vpdn-failcode;
      description
        "Failure type";
    }
  }

  grouping VPDN-REDUNDANCY {
    description
      "vpdn redundancy";
    leaf session-total {
      type uint32;
      description
        "Virtual Private Dialup Network High availability
         Total Number Of Sessions";
    }
    leaf session-synced {
      type uint32;
      description
        "Virtual Private Dialup Network High availability
         Num of Sessions Synced";
    }
    leaf state {
      type Vpdn-state;
      description
        "Virtual Private Dialup Network High availability
         Status";
    }
    leaf start-time {
      type uint64;
      units "second";
      description
        "Virtual Private Dialup Network High availability
         Init Sync Start time in seconds";
    }
    leaf finish-time {
      type uint64;
      units "second";
      description
        "Virtual Private Dialup Network High availability
         Init Sync Finished time in seconds";
    }
    leaf abort-time {
      type uint64;
      units "second";
      description
        "Virtual Private Dialup Network High availability
         Init Aync Abort time in seconds";
    }
  }

  grouping L2TP-NSR-QAD-STATS-RECV {
    description
      "L2TP NSR QAD receive statistics";
    leaf msgs-recvd {
      type uint32;
      description
        "Layer Two Tunneling Protocol Nsr QAD Messages
         Received";
    }
    leaf acks-recvd {
      type uint32;
      description
        "Layer Two Tunneling Protocol Nsr QAD
         Acknowledgement Received";
    }
    leaf recvd-acks-failed {
      type uint32;
      description
        "Layer Two Tunneling Protocol Nsr QAD Received
         Acknowledgement Failed";
    }
    leaf init-drops {
      type uint32;
      description
        "Layer Two Tunneling Protocol Nsr QAD Init Drops";
    }
    leaf msg-drops {
      type uint32;
      description
        "Layer Two Tunneling Protocol Nsr QAD Message
         Drops";
    }
    leaf ooo-drops {
      type uint32;
      description
        "Layer Two Tunneling Protocol Nsr QAD Out Of
         Order Drops";
    }
    leaf stale-msgs {
      type uint32;
      description
        "Layer Two Tunneling Protocol Nsr QAD Stale
         Messages";
    }
  }

  grouping L2TP-NSR-QAD-STATS-SEND {
    description
      "L2TP NSR QAD send statistics";
    leaf msgs-sent {
      type uint32;
      description
        "Layer Two Tunneling Protocol Nsr QAD Message
         Sent";
    }
    leaf acks-sent {
      type uint32;
      description
        "Layer Two Tunneling Protocol Nsr QAD Acks Sent";
    }
    leaf no-partner {
      type uint32;
      description
        "Layer Two Tunneling Protocol Nsr QAD No Partner";
    }
    leaf sends-failed {
      type uint32;
      description
        "Layer Two Tunneling Protocol Nsr QAD Sends
         Failed";
    }
    leaf acks-failed {
      type uint32;
      description
        "Layer Two Tunneling Protocol Nsr QAD
         Acknowledgement Failed";
    }
    leaf pending-acks {
      type uint32;
      description
        "Layer Two Tunneling Protocol Nsr QAD Pending
         Acknowledgement Count";
    }
    leaf timeouts {
      type uint32;
      description
        "Layer Two Tunneling Protocol Nsr QAD Timeouts";
    }
    leaf suspends {
      type uint32;
      description
        "Layer Two Tunneling Protocol Nsr QAD Suspended
         packet count";
    }
    leaf resumes {
      type uint32;
      description
        "Layer Two Tunneling Protocol Nsr QAD Resumed
         packet count";
    }
    leaf sends-fragment {
      type uint32;
      description
        "Layer Two Tunneling Protocol Nsr QAD Sent
         fragment packet count";
    }
    leaf qad-last-seq-number {
      type uint32;
      description
        "Layer Two Tunneling Protocol Nsr QAD Last
         sequency number";
    }
    leaf qad-frag-count {
      type uint32;
      description
        "Layer Two Tunneling Protocol Nsr QAD Fragment
         Count";
    }
    leaf qad-ack-count {
      type uint32;
      description
        "Layer Two Tunneling Protocol Nsr QAD
         Acknowledgement Count";
    }
    leaf qad-unknown-acks {
      type uint32;
      description
        "Layer Two Tunneling Protocol Nsr QAD Number of
         Unknown Acknowledgement";
    }
    leaf qad-timeouts {
      type uint32;
      description
        "Layer Two Tunneling Protocol Nsr QAD Timeouts";
    }
    leaf qad-rx-count {
      type uint32;
      description
        "Layer Two Tunneling Protocol Nsr QAD received
         count";
    }
    leaf qad-rx-list-count {
      type uint32;
      description
        "Layer Two Tunneling Protocol Nsr QAD received
         list count";
    }
    leaf qad-rx-list-q-size {
      type uint32;
      description
        "Layer Two Tunneling Protocol Nsr QAD Received
         List Queue Size";
    }
    leaf qad-rx-first-seq-number {
      type uint32;
      description
        "Layer Two Tunneling Protocol Nsr QAD First
         Sequence Number";
    }
  }

  grouping VPDN-MIRRORING-STATS {
    description
      "VPDN mirroring stats";
    container qad-send-stats {
      description
        "High availability QAD Sent Statistics";
      uses L2TP-NSR-QAD-STATS-SEND;
    }
    container qad-recv-stats {
      description
        "High availability QAD Receive Statistics";
      uses L2TP-NSR-QAD-STATS-RECV;
    }
    container qad-send-stats-last-clear {
      description
        "High availability QAD Send Statistics Since Last
         Clear";
      uses L2TP-NSR-QAD-STATS-SEND;
    }
    container qad-recv-stats-last-clear {
      description
        "High availability QAD Receive Statistics Since
         Last Clear";
      uses L2TP-NSR-QAD-STATS-RECV;
    }
    leaf sync-not-conn-cnt {
      type uint32;
      description
        "High availability Sync not connected count";
    }
    leaf sso-err-cnt {
      type uint32;
      description
        "High availability SSO error count";
    }
    leaf sso-batch-err-cnt {
      type uint32;
      description
        "High availability SSO batch error count";
    }
    leaf alloc-err-cnt {
      type uint32;
      description
        "High availability memory alloc error count";
    }
    leaf alloc-cnt {
      type uint32;
      description
        "High availability memory alloc count";
    }
  }

  grouping VPDN-LSG-NODE {
    description
      "VPDN LSG member";
    leaf vrf-name-xr {
      type string;
      description
        "VRF name";
    }
    leaf load {
      type uint32;
      description
        "Current load on LNS";
    }
    leaf status {
      type Lsg-status;
      description
        "Status of LNS";
    }
    leaf connects {
      type uint32;
      description
        "Total count of tunnels connected";
    }
    leaf disconnects {
      type uint32;
      description
        "Total count of tunnels disconnected";
    }
    leaf retry {
      type uint32;
      description
        "Retries";
    }
    leaf status-change-time {
      type uint32;
      units "second";
      description
        "Seconds since last status change";
    }
  }

  grouping VPDN-VPN-ID {
    description
      "VPDN ID";
    leaf oui {
      type uint32;
      description
        "OUI";
    }
    leaf index {
      type uint32;
      description
        "Index";
    }
  }

  grouping VPDN-CONFIG {
    description
      "VPDN user configuration data";
    container vpn-id {
      description
        "VPN ID";
      uses VPDN-VPN-ID;
    }
    leaf template-name {
      type string;
      description
        "Virtual Private Dialup Network Template name";
    }
    leaf vrf-name {
      type string;
      description
        "VRF name";
    }
    leaf l2tp-busy-timeout {
      type uint16;
      units "second";
      description
        "L2TP busy timeout in seconds";
    }
    leaf tos-mode {
      type Tos-mode;
      description
        "TOS mode";
    }
    leaf tos {
      type uint8;
      description
        "TOS setting value";
    }
    leaf dsl-line-forwarding {
      type boolean;
      description
        "True if DSL line info forwarding is enabled";
    }
  }

  grouping VPDN-SUBSCRIBER {
    description
      "VPDN session subscriber data";
    leaf nas-port-id-val {
      type string;
      description
        "NAS port ID Val";
    }
    leaf nas-port-type {
      type string;
      description
        "NAS port type";
    }
    leaf physical-channel-id {
      type uint32;
      description
        "Virtual Private Dialup Network Physical channel
         ID";
    }
    leaf receive-connect-speed {
      type uint64;
      units "nanosecond";
      description
        "Receive connect speed in nanoseconds";
    }
    leaf transmit-connect-speed {
      type uint64;
      units "nanosecond";
      description
        "Transmit connect speed in nanoseconds";
    }
  }

  grouping VPDN-L2TP {
    description
      "VPDN session L2TP data";
    leaf local-endpoint {
      type inet:ipv4-address;
      description
        "Local endpoint IP address";
    }
    leaf remote-endpoint {
      type inet:ipv4-address;
      description
        "Remote endpoint IP address";
    }
    leaf call-serial-number {
      type uint32;
      description
        "Virtual Private Dialup Network Call serial
         number";
    }
    leaf is-l2tp-class-attribute-mask-set {
      type boolean;
      description
        "True if L2TP class attribute mask is set";
    }
    leaf local-tunnel-id {
      type uint16;
      description
        "Local tunnel ID assigned to this tunnel";
    }
    leaf remote-tunnel-id {
      type uint16;
      description
        "Layer Two Tunneling Protocol tunnel ID assigned
         to remote peer";
    }
    leaf local-session-id {
      type uint16;
      description
        "Local session ID assigned to this session";
    }
    leaf remote-session-id {
      type uint16;
      description
        "Layer Two Tunneling Protocol session ID assigned
         to remote peer";
    }
    leaf remote-port {
      type uint16;
      description
        "Remote port number";
    }
    leaf tunnel-client-authentication-id {
      type string;
      description
        "Layer Two Tunneling Protocol Access Concentrator
         authentication ID";
    }
    leaf tunnel-server-authentication-id {
      type string;
      description
        "Layer Two Tunneling Protocol Network Server
         authentication ID";
    }
    leaf tunnel-assignment-id {
      type string;
      description
        "Tunnel assignment ID to this tunnel";
    }
    leaf is-tunnel-authentication-enabled {
      type boolean;
      description
        "Tunnel authentication status";
    }
  }

  grouping VPDN-EDM-SHOW-SESSION-BR {
    description
      "VPDN session brief information";
    leaf last-change {
      type string;
      description
        "Elapsed time since last change in hh:mm:ss
         format";
    }
    leaf interface-name {
      type xr:Interface-name;
      description
        "Session interface name";
    }
    leaf username {
      type string;
      description
        "Authentication username";
    }
    leaf domain-name {
      type string;
      description
        "Virtual Private Dialup Network Domain name";
    }
    leaf state {
      type Session-state;
      description
        "Session state";
    }
    leaf l2tp-session-id {
      type uint16;
      description
        "Layer Two Tunneling Protocol session ID";
    }
    leaf l2tp-tunnel-id {
      type uint16;
      description
        "Layer Two Tunneling Protocol tunnel ID";
    }
    leaf srg-slave {
      type boolean;
      description
        "Session SRG Slave";
    }
  }

  grouping VPDN-EDM-SHOW-SESSION-DET {
    description
      "VPDN session detail";
    container session {
      description
        "Session data";
      uses VPDN-EDM-SHOW-SESSION-BR;
    }
    container l2tp {
      description
        "L2TP data";
      uses VPDN-L2TP;
    }
    container subscriber {
      description
        "Subscriber data";
      uses VPDN-SUBSCRIBER;
    }
    container configuration {
      description
        "Configuration data";
      uses VPDN-CONFIG;
    }
    leaf setup-time {
      type uint32;
      description
        "Time to setup session in sec:msec";
    }
    leaf parent-interface-name {
      type xr:Interface-name;
      description
        "Subscriber Parent interface name";
    }
  }
}
