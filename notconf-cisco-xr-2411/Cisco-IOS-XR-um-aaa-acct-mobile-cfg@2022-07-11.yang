module Cisco-IOS-XR-um-aaa-acct-mobile-cfg {
  namespace "http://cisco.com/ns/yang/Cisco-IOS-XR-um-aaa-acct-mobile-cfg";
  prefix um-aaa-acct-mobile-cfg;

  import Cisco-IOS-XR-types {
    prefix xr;
  }
  import Cisco-IOS-XR-um-aaa-cfg {
    prefix a1;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR aaa-acct-mobile package configuration.

     This YANG module augments the
     modules with configuration data.

     Copyright (c) 2020-2022 by Cisco Systems, Inc.
     All rights reserved.";

  revision 2022-07-11 {
    semver:module-version "1.0.0";
    description
      "Added missing description statement to nodes";
  }
  revision 2020-12-14 {
    semver:module-version "1.0.0";
    description
      "Initial release";
  }

  augment "/a1:aaa/a1:accounting" {
    description
      "This augment extends aaa accounting nodes
       configuration";
    container mobile {
      description
        "Set account lists for mobile subscriber";
      container default {
        presence "Indicates a default node is configured.";
        description
          "Default list name for AAA accounting";
        container broadcast {
          presence "Indicates a broadcast node is configured.";
          description
            "Set broadcast accounting for Subscriber";
        }
        container groups {
          description
            "Use Server-group";
          container group1 {
            description
              "Use Server-group";
            leaf all-hosts {
              type enumeration {
                enum "radius" {
                  value 3;
                  description
                    "Use list of all RADIUS hosts";
                }
                enum "diameter" {
                  value 15;
                  description
                    "Use list of all DIAMETER peers";
                }
              }
              must "not(../server-group)";
              description
                "configure this node";
            }
            leaf server-group {
              type xr:Cisco-ios-xr-string {
                length "1..1024" {
                  description
                    "server-group name";
                }
              }
              must "not(../all-hosts)";
              description
                "server-group name";
            }
          }
          container group2 {
            description
              "Use Server-group";
            leaf all-hosts {
              type enumeration {
                enum "radius" {
                  value 3;
                  description
                    "Use list of all RADIUS hosts";
                }
                enum "diameter" {
                  value 15;
                  description
                    "Use list of all DIAMETER peers";
                }
              }
              must
                "not(../server-group) and
                 (../../group1/all-hosts or ../../group1/server-group)";
              description
                "configure this node";
            }
            leaf server-group {
              type xr:Cisco-ios-xr-string {
                length "1..1024" {
                  description
                    "server-group name";
                }
              }
              must
                "not(../all-hosts) and
                 (../../group1/all-hosts or ../../group1/server-group)";
              description
                "server-group name";
            }
          }
          container group3 {
            description
              "Use Server-group";
            leaf all-hosts {
              type enumeration {
                enum "radius" {
                  value 3;
                  description
                    "Use list of all RADIUS hosts";
                }
                enum "diameter" {
                  value 15;
                  description
                    "Use list of all DIAMETER peers";
                }
              }
              must
                "not(../server-group) and
                 (../../group2/all-hosts or ../../group2/server-group)";
              description
                "configure this node";
            }
            leaf server-group {
              type xr:Cisco-ios-xr-string {
                length "1..1024" {
                  description
                    "server-group name";
                }
              }
              must
                "not(../all-hosts) and
                 (../../group2/all-hosts or ../../group2/server-group)";
              description
                "server-group name";
            }
          }
          container group4 {
            description
              "Use Server-group";
            leaf all-hosts {
              type enumeration {
                enum "radius" {
                  value 3;
                  description
                    "Use list of all RADIUS hosts";
                }
                enum "diameter" {
                  value 15;
                  description
                    "Use list of all DIAMETER peers";
                }
              }
              must
                "not(../server-group) and
                 (../../group3/all-hosts or ../../group3/server-group)";
              description
                "configure this node";
            }
            leaf server-group {
              type xr:Cisco-ios-xr-string {
                length "1..1024" {
                  description
                    "server-group name";
                }
              }
              must
                "not(../all-hosts) and
                 (../../group3/all-hosts or ../../group3/server-group)";
              description
                "server-group name";
            }
          }
        }
      }
      container accounting-lists {
        description
          "List name for AAA accounting";
        list accounting-list {
          key "list-name";
          description
            "List name for AAA accounting";
          leaf list-name {
            type xr:Cisco-ios-xr-string {
              length "1..800" {
                description
                  "List name for AAA accounting";
              }
            }
            description
              "List name for AAA accounting";
          }
          container broadcast {
            presence "Indicates a broadcast node is configured.";
            description
              "Set broadcast accounting for Subscriber";
          }
          container groups {
            description
              "Use Server-group";
            container group1 {
              description
                "Use Server-group";
              leaf all-hosts {
                type enumeration {
                  enum "radius" {
                    value 3;
                    description
                      "Use list of all RADIUS hosts";
                  }
                  enum "diameter" {
                    value 15;
                    description
                      "Use list of all DIAMETER peers";
                  }
                }
                must "not(../server-group)";
                description
                  "configure this node";
              }
              leaf server-group {
                type xr:Cisco-ios-xr-string {
                  length "1..1024" {
                    description
                      "server-group name";
                  }
                }
                must "not(../all-hosts)";
                description
                  "server-group name";
              }
            }
            container group2 {
              description
                "Use Server-group";
              leaf all-hosts {
                type enumeration {
                  enum "radius" {
                    value 3;
                    description
                      "Use list of all RADIUS hosts";
                  }
                  enum "diameter" {
                    value 15;
                    description
                      "Use list of all DIAMETER peers";
                  }
                }
                must
                  "not(../server-group) and
                   (../../group1/all-hosts or ../../group1/server-group)";
                description
                  "configure this node";
              }
              leaf server-group {
                type xr:Cisco-ios-xr-string {
                  length "1..1024" {
                    description
                      "server-group name";
                  }
                }
                must
                  "not(../all-hosts) and
                   (../../group1/all-hosts or ../../group1/server-group)";
                description
                  "server-group name";
              }
            }
            container group3 {
              description
                "Use Server-group";
              leaf all-hosts {
                type enumeration {
                  enum "radius" {
                    value 3;
                    description
                      "Use list of all RADIUS hosts";
                  }
                  enum "diameter" {
                    value 15;
                    description
                      "Use list of all DIAMETER peers";
                  }
                }
                must
                  "not(../server-group) and
                   (../../group2/all-hosts or ../../group2/server-group)";
                description
                  "configure this node";
              }
              leaf server-group {
                type xr:Cisco-ios-xr-string {
                  length "1..1024" {
                    description
                      "server-group name";
                  }
                }
                must
                  "not(../all-hosts) and
                   (../../group2/all-hosts or ../../group2/server-group)";
                description
                  "server-group name";
              }
            }
            container group4 {
              description
                "Use Server-group";
              leaf all-hosts {
                type enumeration {
                  enum "radius" {
                    value 3;
                    description
                      "Use list of all RADIUS hosts";
                  }
                  enum "diameter" {
                    value 15;
                    description
                      "Use list of all DIAMETER peers";
                  }
                }
                must
                  "not(../server-group) and
                   (../../group3/all-hosts or ../../group3/server-group)";
                description
                  "configure this node";
              }
              leaf server-group {
                type xr:Cisco-ios-xr-string {
                  length "1..1024" {
                    description
                      "server-group name";
                  }
                }
                must
                  "not(../all-hosts) and
                   (../../group3/all-hosts or ../../group3/server-group)";
                description
                  "server-group name";
              }
            }
          }
        }
      }
    }
  }
}
