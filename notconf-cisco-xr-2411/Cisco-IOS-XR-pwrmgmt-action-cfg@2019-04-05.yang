module Cisco-IOS-XR-pwrmgmt-action-cfg {
  namespace "http://cisco.com/ns/yang/Cisco-IOS-XR-pwrmgmt-action-cfg";
  prefix pwrmgmt-action-cfg;

  import cisco-semver {
    prefix semver;
  }
  import Cisco-IOS-XR-pwrmgmt-cfg {
    prefix a1;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR pwrmgmt-action package configuration.

     This YANG module augments the
       Cisco-IOS-XR-pwrmgmt-cfg
     module with configuration data.

     Copyright (c) 2013-2019 by Cisco Systems, Inc.
     All rights reserved.";

  revision 2019-04-05 {
    semver:module-version "1.0.0";
    description
      "Establish semantic version baseline.";
  }
  revision 2015-11-09 {
    description
      "IOS XR 6.0 revision.";
  }

  augment "/a1:power-management" {
    description
      "This augment extends the configuration data of
       'Cisco-IOS-XR-pwrmgmt-cfg'";
    leaf action-disable {
      type boolean;
      description
        "Config for controlling power budget to not
         exceed power capacity";
    }
  }
}
