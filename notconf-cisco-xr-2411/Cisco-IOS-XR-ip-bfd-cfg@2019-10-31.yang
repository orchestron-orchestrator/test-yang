module Cisco-IOS-XR-ip-bfd-cfg {
  namespace "http://cisco.com/ns/yang/Cisco-IOS-XR-ip-bfd-cfg";
  prefix ip-bfd-cfg;

  import ietf-inet-types {
    prefix inet;
  }
  import Cisco-IOS-XR-types {
    prefix xr;
  }
  import cisco-semver {
    prefix semver;
  }
  import Cisco-IOS-XR-snmp-agent-cfg {
    prefix a1;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ip-bfd package configuration.

     This module contains definitions
     for the following management objects:
       bfd: BFD Configuration

     This YANG module augments the
       Cisco-IOS-XR-snmp-agent-cfg
     module with configuration data.

     Copyright (c) 2013-2019 by Cisco Systems, Inc.
     All rights reserved.";

  revision 2019-10-31 {
    semver:module-version "2.0.0";
    description
      "Added mandary modes and presence containers.";
  }
  revision 2019-04-05 {
    semver:module-version "1.0.0";
    description
      "Establish semantic version baseline.";
  }
  revision 2015-11-09 {
    description
      "IOS XR 6.0 revision.";
  }

  typedef Bfd-echo-startup-validate {
    type enumeration {
      enum "off" {
        value 0;
        description
          "Disable echo startup validation";
      }
      enum "on" {
        value 1;
        description
          "Enable echo startup validation";
      }
      enum "force" {
        value 2;
        description
          "Force echo startup validation";
      }
    }
    description
      "Bfd echo startup validate";
  }

  typedef Bfd-bundle-coexistence-bob-blb {
    type enumeration {
      enum "inherited" {
        value 1;
        description
          "Inherited coexistence mode";
      }
      enum "logical" {
        value 2;
        description
          "Logical coexistence mode";
      }
    }
    description
      "Bfd bundle coexistence bob blb";
  }

  typedef Bfd-if-echo-usage {
    type enumeration {
      enum "enable" {
        value 0;
        description
          "Enable echo";
      }
      enum "disable" {
        value 1;
        description
          "Disable echo";
      }
    }
    description
      "Bfd if echo usage";
  }

  typedef Bfd-if-ipv6-checksum-usage {
    type enumeration {
      enum "disable" {
        value 0;
        description
          "Disable IPv6 checksum";
      }
      enum "enable" {
        value 1;
        description
          "Enable IPv6 checksum";
      }
    }
    description
      "Bfd if ipv6 checksum usage";
  }

  container bfd {
    description
      "BFD Configuration";
    container flap-damp {
      description
        "Flapping class container";
      container bundle-member {
        description
          "Bundle per member feature class container";
        leaf initial-delay {
          type uint32 {
            range "1..518400000";
          }
          units "millisecond";
          default "16000";
          description
            "Initial delay before bringing up session";
        }
        leaf maximum-delay {
          type uint32 {
            range "1..518400000";
          }
          units "millisecond";
          default "600000";
          description
            "Maximum delay before bringing up session";
        }
        leaf secondary-delay {
          type uint32 {
            range "1..518400000";
          }
          units "millisecond";
          default "20000";
          description
            "Secondary delay before bringing up session";
        }
        leaf l3-only-mode {
          type empty;
          description
            "Apply immediate dampening and only when
             failure is L3 specific";
        }
      }
      container extensions {
        description
          "Extensions to the BFD dampening feature";
        leaf down-monitor {
          type empty;
          description
            "If set, DOWN state monitoring mode is enabled";
        }
      }
      leaf threshold {
        type uint32 {
          range "60000..3600000";
        }
        units "millisecond";
        default "120000";
        description
          "Stability threshold to enable dampening";
      }
      leaf initial-delay {
        type uint32 {
          range "1..3600000";
        }
        units "millisecond";
        default "2000";
        description
          "Initial delay before bringing up session";
      }
      leaf maximum-delay {
        type uint32 {
          range "1..3600000";
        }
        units "millisecond";
        default "120000";
        description
          "Maximum delay before bringing up session";
      }
      leaf dampen-disable {
        type empty;
        description
          "Dampening Enable/Disable";
      }
      leaf secondary-delay {
        type uint32 {
          range "1..3600000";
        }
        units "millisecond";
        default "5000";
        description
          "Secondary delay before bringing up session";
      }
    }
    container echo-latency {
      description
        "BFD echo latency feature class container";
      container detect {
        description
          "BFD echo latency detection";
        leaf latency-detect-enabled {
          type boolean;
          description
            "If set, echo latency detect is enabled";
        }
        leaf latency-detect-percentage {
          type uint32 {
            range "100..250";
          }
          units "percentage";
          description
            "Echo latency detect percentage";
        }
        leaf latency-detect-count {
          type uint32 {
            range "1..10";
          }
          description
            "Echo latency detect count";
        }
      }
    }
    container echo-startup {
      presence "Contains mandatory nodes that used to set default values";
      description
        "BFD echo startup feature class container";
      leaf validate {
        type Bfd-echo-startup-validate;
        mandatory true;
        description
          "BFD echo validation prior to session bringup";
      }
    }
    container interfaces {
      description
        "Interface configuration";
      list interface {
        key "interface-name";
        description
          "Single interface configuration";
        leaf interface-bfd-multiplier {
          type uint32 {
            range "2..50";
          }
          description
            "BFD Multiplier for this Interface";
        }
        leaf interface-echo-usage {
          type Bfd-if-echo-usage;
          default "enable";
          description
            "Echo usage for this interface";
        }
        leaf interface-bfd-rx-interval {
          type uint32 {
            range "3000..30000000";
          }
          units "microsecond";
          description
            "BFD RxInterval for this Interface";
        }
        leaf interface-bfd {
          type empty;
          description
            "Enable/Disable BFD for this interface";
        }
        leaf ipv6-checksum {
          type Bfd-if-ipv6-checksum-usage;
          default "enable";
          description
            "IPv6 checksum usage for this interface -
             Interface config will always take precedence
             over global config";
        }
        leaf interface-ipv4-echo-source {
          type inet:ip-address-no-zone;
          description
            "Interface IPv4 echo source address
             configuration";
        }
        leaf interface-bfd-local-addr {
          type inet:ip-address-no-zone;
          description
            "BFD LocalAddr for this Interface";
        }
        leaf interface-bfd-tx-interval {
          type uint32 {
            range "3000..30000000";
          }
          units "microsecond";
          description
            "BFD TxInterval for this Interface";
        }
        leaf interface-name {
          type xr:Interface-name;
          description
            "Interface Name";
        }
      }
    }
    container multi-path-includes {
      description
        "Multipath Include configuration";
      list multi-path-include {
        key "location";
        description
          "Location configuration";
        leaf location {
          type xr:Node-id;
          description
            "Location";
        }
      }
    }
    container bundle {
      description
        "Configuration related to BFD over Bundle";
      container coexistence {
        description
          "Coexistence mode for BFD on bundle feature";
        leaf bob-blb {
          type Bfd-bundle-coexistence-bob-blb;
          description
            "Coexistence mode for BoB and BLB feature";
        }
      }
    }
    leaf global-echo-usage {
      type empty;
      description
        "Echo configuration";
    }
    leaf ipv6-checksum-disable {
      type empty;
      description
        "To disable IPv6 checksum configuration";
    }
    leaf global-echo-min-interval {
      type uint32 {
        range "15..2000";
      }
      units "millisecond";
      default "15";
      description
        "Configure echo min-interval for bundle interface";
    }
    leaf ttl-drop-threshold {
      type uint32 {
        range "0..254";
      }
      description
        "Multihop TTL Drop Threshold";
    }
    leaf single-hop-trap {
      type empty;
      description
        "Single hop trap configuration";
    }
    leaf global-ipv4-echo-source {
      type inet:ip-address-no-zone;
      description
        "IPv4 echo source address configuration";
    }
  }

  augment "/a1:snmp/a1:notification" {
    description
      "This augment extends the configuration data of
       'Cisco-IOS-XR-snmp-agent-cfg'";
    container bfd {
      description
        "CISCO-IETF-BFD-MIB notification configuration";
      leaf enable {
        type empty;
        description
          "Enable CISCO-IETF-BFD-MIB notifications";
      }
    }
  }
}
