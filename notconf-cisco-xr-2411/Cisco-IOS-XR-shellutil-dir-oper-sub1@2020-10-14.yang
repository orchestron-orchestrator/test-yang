submodule Cisco-IOS-XR-shellutil-dir-oper-sub1 {
  belongs-to Cisco-IOS-XR-shellutil-dir-oper {
    prefix Cisco-IOS-XR-shellutil-dir-oper;
  }

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR shellutil-dir package operational data.

     Copyright (c) 2013-2020 by Cisco Systems, Inc.
     All rights reserved.";

  revision 2020-10-14 {
    semver:module-version "1.0.0";
    description
      "Initial version.";
  }
  revision 2019-04-05 {
    description
      "Establish semantic version baseline.";
  }
  revision 2015-11-09 {
    description
      "IOS XR 6.0 revision.";
  }

  grouping SHELLUTIL-DIR-LAST-MODIFIED {
    description
      "last modified time";
    leaf date {
      type uint32;
      description
        "Modified Date";
    }
    leaf month {
      type string;
      description
        "Modified Month";
    }
    leaf year {
      type uint32;
      description
        "Modified Year";
    }
    leaf hour {
      type uint32;
      description
        "Modified Hour";
    }
    leaf min {
      type uint32;
      description
        "Modified Minute";
    }
    leaf sec {
      type uint32;
      units "second";
      description
        "Modified Seconds";
    }
  }

  grouping SHELLUTIL-DIR-CONTENT {
    description
      "file Info";
    leaf inode {
      type uint32;
      description
        "Inode number";
    }
    leaf permission {
      type string;
      description
        "File permission";
    }
    leaf links {
      type uint32;
      description
        "Links";
    }
    leaf size {
      type string;
      description
        "File size";
    }
    leaf name {
      type string;
      description
        "File name";
    }
    leaf link-name {
      type string;
      description
        "Link name";
    }
    list last-modified {
      description
        "Last modified time";
      uses SHELLUTIL-DIR-LAST-MODIFIED;
    }
  }

  grouping SHELLUTIL-DIR-UTIL {
    description
      "Directories Info";
    leaf path {
      type string;
      description
        "Directory path";
    }
    list content {
      description
        "List of directory contents";
      uses SHELLUTIL-DIR-CONTENT;
    }
  }

  grouping SHELLUTIL-DIR {
    description
      "List of directories";
    leaf total-size {
      type string;
      description
        "Total size";
    }
    leaf free-size {
      type string;
      description
        "Free size";
    }
    list directory {
      description
        "Available directories";
      uses SHELLUTIL-DIR-UTIL;
    }
  }
}
