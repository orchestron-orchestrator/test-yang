module Cisco-IOS-XR-subscriber-session-mon-oper {
  namespace "http://cisco.com/ns/yang/Cisco-IOS-XR-subscriber-session-mon-oper";
  prefix subscriber-session-mon-oper;

  import Cisco-IOS-XR-types {
    prefix xr;
  }
  import cisco-semver {
    prefix semver;
  }

  include Cisco-IOS-XR-subscriber-session-mon-oper-sub1 {
    revision-date 2023-02-15;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR subscriber-session-mon package operational data.

     This module contains definitions
     for the following management objects:
       session-mon: Sessionmon

     Copyright (c) 2013-2023 by Cisco Systems, Inc.
     All rights reserved.";

  revision 2023-02-15 {
    semver:module-version "1.0.1";
    description
      "Added subscriber session detail info.";
  }
  revision 2019-04-05 {
    semver:module-version "1.0.1";
    description
      "Establish semantic version baseline.";
  }
  revision 2015-11-09 {
    description
      "IOS XR 6.0 revision.";
  }

  container session-mon {
    config false;
    description
      "Sessionmon";
    container nodes {
      description
        "Subscriber Sessionmon list of nodes";
      list node {
        key "node-id";
        description
          "Subscriber sessionmon operational data for a
           particular node";
        container session-mon-statistics {
          description
            "Session Mon Statistics";
          uses SHOW-SESSIONMON-STAT;
        }
        container interface-all-statistics {
          description
            "Statistics Table";
          list interface-all-statistic {
            key "interface-name";
            description
              "Statistics";
            leaf interface-name {
              type xr:Interface-name;
              description
                "Interface Name";
            }
            uses SHOW-SESSIONMON-STAT;
          }
        }
        container license-statistics {
          description
            "Smart license";
          uses SHOW-SESSIONMON-STAT;
        }
        leaf node-id {
          type xr:Node-id;
          description
            "Nodeid location ";
        }
      }
    }
  }
}
