module Cisco-IOS-XR-controller-t1e1-oper {
  namespace "http://cisco.com/ns/yang/Cisco-IOS-XR-controller-t1e1-oper";
  prefix controller-t1e1-oper;

  import Cisco-IOS-XR-types {
    prefix xr;
  }
  import cisco-semver {
    prefix semver;
  }

  include Cisco-IOS-XR-controller-t1e1-oper-sub1 {
    revision-date 2022-01-12;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR controller-t1e1 package operational data.

     This module contains definitions
     for the following management objects:
       t1e1-oper: T1E1NV operational data

     Copyright (c) 2013-2022 by Cisco Systems, Inc.
     All rights reserved.";

  revision 2022-01-12 {
    semver:module-version "1.0.0";
    description
      "Added Oper Schema for T1E1";
  }
  revision 2019-04-05 {
    description
      "Establish semantic version baseline.";
  }
  revision 2015-11-09 {
    description
      "IOS XR 6.0 revision.";
  }

  container t1e1-oper {
    config false;
    description
      "T1E1NV operational data";
    container t1e1-ports {
      description
        "All T1E1 Port operational data";
      list t1e1-port {
        key "name";
        description
          "Optics operational data";
        container t1e1-info {
          description
            "T1E1 operational data";
          uses T1E1-INFO;
        }
        leaf name {
          type xr:Interface-name;
          description
            "Port name";
        }
      }
    }
  }
}
