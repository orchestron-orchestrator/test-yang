module Cisco-IOS-XR-mpls-te-cfg {
  namespace "http://cisco.com/ns/yang/Cisco-IOS-XR-mpls-te-cfg";
  prefix mpls-te-cfg;

  import ietf-inet-types {
    prefix inet;
  }
  import Cisco-IOS-XR-types {
    prefix xr;
  }
  import cisco-semver {
    prefix semver;
  }
  import Cisco-IOS-XR-ifmgr-cfg {
    prefix a1;
  }
  import Cisco-IOS-XR-snmp-agent-cfg {
    prefix a2;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR mpls-te package configuration.

     This model is deprecated and is replaced by
     Cisco-IOS-XR-um-mpls-te-cfg.yang which will provide the
     compatible functionalities.

     This module contains definitions
     for the following management objects:
       mpls-te: The root of MPLS TE configuration

     This YANG module augments the
       Cisco-IOS-XR-ifmgr-cfg,
       Cisco-IOS-XR-snmp-agent-cfg
     modules with configuration data.

     Copyright (c) 2013-2023 by Cisco Systems, Inc.
     All rights reserved.";

  revision 2023-10-10 {
    semver:module-version "4.0.0";
    description
      "Added source to named tunnel
       2023-08-02
         Changes for soft-preemption over p2mp
       2023-07-05
         Add knob to configure Autoroute Announce exclude all SR traffic
       2023-02-02
         Remove hidden commands
       2022-11-17
         Added leaf sr-traffic-pct, and retry-timer
       2022-11-07
         Add TE++ over numbered tunnel feature
       2022-10-20
         Decreased BFD min interval value to 3ms
       2022-03-18
         Added self-ping under named-tunnels
       2021-11-18
         Added attribute sets for path-option under named-tunnels
       2021-10-13
         Added BFD and path protection support for named tunnels.";
  }
  revision 2021-06-10 {
    semver:module-version "3.0.0";
    description
      "Removal of leaf oor-recovery-duration and add back as grouping OOR-RECOVERY-DURATION, the grouping is used by multiple parents. add OOR-AVAILABLE-BANDWIDTH-PERCENTAGE add OOR-ACCEPT-LSP-MIN-BANDWIDTH add OOR-ACCEPT-REOPT-LSP add OOR-METRIC-TE-PENALTY add container lsp-oor-green-state add container backoff-timer add grouping OOR-RECOVERY-DURATION";
  }
  revision 2021-03-24 {
    semver:module-version "2.2.0";
    description
      "Added enhancement of auto-tunnel backup capabilities to prevent circuit congestion
       2020-06-11
           new leaf mpls.traffic-eng.timers.backoff-timer";
  }
  revision 2020-03-28 {
    semver:module-version "2.1.0";
    description
      "Added path retry timeout and path error message.
       2020-03-27
         Added PCE redundancy PCC-centric model support.";
  }
  revision 2019-10-31 {
    semver:module-version "2.0.0";
    description
      "Added mandatory nodes
       2019-09-30
         extra leaves in mpls.traffic-eng.attribute-set.auto-backup.logging.events.lsp-status
       2019-05-12
         Deprecated the native model, replaced by UM model.";
  }
  revision 2019-04-05 {
    semver:module-version "1.0.0";
    description
      "Establish semantic version baseline.";
  }
  revision 2017-09-07 {
    description
      "Fixed type translation error.";
  }
  revision 2017-05-01 {
    description
      "Fixing backward compatibility error in module.";
  }
  revision 2015-11-09 {
    description
      "IOS XR 6.0 revision.";
  }

  typedef Mpls-tesrlg-exclude {
    type enumeration {
      enum "mandatory" {
        value 1;
        description
          "SRLG Mandatory Exclude";
      }
      enum "preferred" {
        value 2;
        description
          "SRLG Preferred Exclude";
      }
      enum "weighted" {
        value 3;
        description
          "SRLG Weighted Exclude";
      }
    }
    description
      "Mpls tesrlg exclude";
  }

  typedef Mpls-te-affinity-value {
    type enumeration {
      enum "hex-value" {
        value 1;
        description
          "Affinity value in Hex number";
      }
      enum "bit-position" {
        value 2;
        description
          "Affinity value by Bit-Position";
      }
    }
    description
      "Mpls te affinity value";
  }

  typedef Mpls-te-uni-in-place-bit {
    type enumeration {
      enum "not-set" {
        value 0;
        description
          "NOT SET";
      }
      enum "set" {
        value 8;
        description
          "SET";
      }
    }
    description
      "Mpls te uni in place bit";
  }

  typedef Destination-list-name-length {
    type string {
      length "1..32";
    }
    description
      "Destination list name length";
  }

  typedef Route-priority-role {
    type enumeration {
      enum "route-priority-role-head-back-up" {
        value 0;
        description
          "TE Route Priority Role Head Backup";
      }
      enum "route-priority-role-head-primary" {
        value 1;
        description
          "TE Route Priority Role Head Primary";
      }
      enum "route-priority-role-middle" {
        value 2;
        description
          "TE Route Priority Role Middle";
      }
    }
    description
      "Route priority role";
  }

  typedef Mpls-percent-range {
    type uint32 {
      range "0..100";
    }
    description
      "Mpls percent range";
  }

  typedef Otn-signaled-bandwidth-flex-framing {
    type enumeration {
      enum "cbr" {
        value 20;
        description
          "CBR";
      }
      enum "framed-gfp-fixed" {
        value 21;
        description
          "GFP fixed framing type";
      }
      enum "framed-gfp-resize" {
        value 22;
        description
          "GFP resizeable framing type";
      }
    }
    description
      "Otn signaled bandwidth flex framing";
  }

  typedef Mpls-te-path-selection-tiebreaker {
    type enumeration {
      enum "min-fill" {
        value 1;
        description
          "Prefer the path with the least-utilized links";
      }
      enum "max-fill" {
        value 2;
        description
          "Prefer the path with the most-utilized links";
      }
      enum "random" {
        value 3;
        description
          "Prefer a path with links utilized randomly";
      }
    }
    description
      "Mpls te path selection tiebreaker";
  }

  typedef Attribute-set-name-length {
    type string {
      length "1..64";
    }
    description
      "Attribute set name length";
  }

  typedef Mpls-te-otn-aps-protection {
    type enumeration {
      enum "1plus1-unidir-no-aps" {
        value 4;
        description
          "1PLUS1 UNIDIR NO APS";
      }
      enum "1plus1-unidir-aps" {
        value 8;
        description
          "1PLUS1 UNIDIR APS";
      }
      enum "1plus1-bdir-aps" {
        value 16;
        description
          "1PLUS1 BIDIR APS";
      }
    }
    description
      "Mpls te otn aps protection";
  }

  typedef Ospf-area-mode {
    type enumeration {
      enum "ospf-int" {
        value 0;
        description
          "OSPF area in integer format";
      }
      enum "ospfip-addr" {
        value 1;
        description
          "OSPF area in IP address format";
      }
    }
    description
      "Ospf area mode";
  }

  typedef Mpls-te-path-option-property {
    type enumeration {
      enum "none" {
        value 0;
        description
          "No property";
      }
      enum "lockdown" {
        value 1;
        description
          "Path is not a candidate for reoptimization";
      }
      enum "verbatim" {
        value 4;
        description
          "Explicit path does not require topology
           database";
      }
      enum "pce" {
        value 8;
        description
          "Dynamic path found by PCE server";
      }
      enum "segment-routing" {
        value 16;
        description
          "Segment Routing path";
      }
      enum "sticky" {
        value 32;
        description
          "Force tunnel to remain on same path";
      }
    }
    description
      "Mpls te path option property";
  }

  typedef Mpls-te-path-computation-method {
    type enumeration {
      enum "not-set" {
        value 0;
        description
          "NotSet";
      }
      enum "dynamic" {
        value 1;
        description
          "Dynamic";
      }
      enum "pce" {
        value 2;
        description
          "PCE";
      }
      enum "explicit" {
        value 3;
        description
          "Explicit";
      }
    }
    description
      "Mpls te path computation method";
  }

  typedef Mpls-te-signaled-label {
    type enumeration {
      enum "not-set" {
        value 0;
        description
          "Not Set";
      }
      enum "dwdm" {
        value 1;
        description
          "DWDM Label (RFC 6205), 50GHz channel spacing";
      }
    }
    description
      "Mpls te signaled label";
  }

  typedef Mpls-tebfd-session {
    type enumeration {
      enum "regular-bfd" {
        value 1;
        description
          "Regular BFD";
      }
      enum "sbfd" {
        value 2;
        description
          "Seamless BFD";
      }
      enum "redundant-sbfd" {
        value 3;
        description
          "Redundant SBFD";
      }
    }
    description
      "Mpls tebfd session";
  }

  typedef Mpls-te-lsp-switch {
    type enumeration {
      enum "dcsc" {
        value 0;
        description
          "Data channel switch capable";
      }
      enum "lsc" {
        value 1;
        description
          "Lambda switch capable";
      }
      enum "fsc" {
        value 2;
        description
          "Fiber switch capable";
      }
    }
    description
      "Mpls te lsp switch";
  }

  typedef Mpls-te-path-option-xro {
    type enumeration {
      enum "not-set" {
        value 0;
        description
          "Not Set";
      }
      enum "xro-attribute-set-type" {
        value 1;
        description
          "Defined as attribute-set";
      }
    }
    description
      "Mpls te path option xro";
  }

  typedef Otn-destination {
    type enumeration {
      enum "number-ed" {
        value 0;
        description
          "Destination numbered";
      }
      enum "un-number-ed" {
        value 1;
        description
          "Destination unnumbered";
      }
    }
    description
      "Otn destination";
  }

  typedef Mpls-te-tunnel-affinity {
    type enumeration {
      enum "include" {
        value 1;
        description
          "Include Affinity";
      }
      enum "include-strict" {
        value 2;
        description
          "Strictly Include Affinity";
      }
      enum "exclude" {
        value 3;
        description
          "Exclude Affinity";
      }
      enum "exclude-all" {
        value 4;
        description
          "Exclude All Affinities";
      }
      enum "ignore" {
        value 5;
        description
          "Ignore Affinity";
      }
      enum "include-any" {
        value 6;
        description
          "Include Any Affinity";
      }
    }
    description
      "Mpls te tunnel affinity";
  }

  typedef Otn-static-uni {
    type enumeration {
      enum "unknown" {
        value 0;
        description
          "Uni-Type None";
      }
      enum "xc" {
        value 1;
        description
          "Uni-Type XC";
      }
      enum "termination" {
        value 2;
        description
          "Uni-Type Termination";
      }
    }
    description
      "Otn static uni";
  }

  typedef Mpls-te-lsp-enc {
    type enumeration {
      enum "ethernet-type1" {
        value 0;
        description
          "Ethernet Type1";
      }
      enum "ethernet-type2" {
        value 1;
        description
          "Ethernet Type2";
      }
      enum "lambda" {
        value 2;
        description
          "Lambda";
      }
      enum "fiber" {
        value 3;
        description
          "Fiber";
      }
    }
    description
      "Mpls te lsp enc";
  }

  typedef Mpls-te-switching-cap {
    type enumeration {
      enum "psc1" {
        value 1;
        description
          "PSC1";
      }
      enum "lsc" {
        value 150;
        description
          "LSC";
      }
      enum "fsc" {
        value 200;
        description
          "FSC";
      }
    }
    description
      "Mpls te switching cap";
  }

  typedef Mpls-te-otn-aps-protection-mode {
    type enumeration {
      enum "revertive" {
        value 1;
        description
          "Revertive";
      }
      enum "non-revertive" {
        value 2;
        description
          "Non Revertive";
      }
    }
    description
      "Mpls te otn aps protection mode";
  }

  typedef Mpls-te-config-tunnel {
    type enumeration {
      enum "p2p" {
        value 0;
        description
          "P2P";
      }
      enum "p2mp" {
        value 1;
        description
          "P2MP";
      }
    }
    description
      "Mpls te config tunnel";
  }

  typedef Mpls-te-bfd-session-down-action {
    type enumeration {
      enum "re-setup" {
        value 1;
        description
          "Tear down and resetup";
      }
    }
    description
      "Mpls te bfd session down action";
  }

  typedef Mpls-te-log-frr-protection {
    type enumeration {
      enum "frr-active-primary" {
        value 1;
        description
          "Track only FRR active on primary LSP";
      }
      enum "backup" {
        value 256;
        description
          "backup tunnel";
      }
      enum "frr-ready-primary" {
        value 512;
        description
          "Track only FRR ready on primary LSP";
      }
      enum "primary" {
        value 513;
        description
          "primary LSP";
      }
      enum "all" {
        value 769;
        description
          "all";
      }
    }
    description
      "Mpls te log frr protection";
  }

  typedef Link-next-hop {
    type enumeration {
      enum "none" {
        value 1;
        description
          "No next hop";
      }
      enum "ipv4-address" {
        value 2;
        description
          "IPv4 next-hop address";
      }
    }
    description
      "Link next hop";
  }

  typedef Mpls-lcac-bandwidth-hold-timer-range {
    type uint32 {
      range "1..300";
    }
    description
      "Mpls lcac bandwidth hold timer range";
  }

  typedef Mpls-te-uni-required-bit {
    type enumeration {
      enum "not-set" {
        value 0;
        description
          "NOT SET";
      }
      enum "set" {
        value 4;
        description
          "SET";
      }
    }
    description
      "Mpls te uni required bit";
  }

  typedef Mpls-te-autoroute-metric {
    type enumeration {
      enum "relative" {
        value 1;
        description
          "Relative";
      }
      enum "absolute" {
        value 2;
        description
          "Absolute";
      }
      enum "constant" {
        value 3;
        description
          "Constant";
      }
    }
    description
      "Mpls te autoroute metric";
  }

  typedef Bandwidth-constraint {
    type enumeration {
      enum "bandwidth-constraint-maximum-allocation-model" {
        value 1;
        description
          "Maximum Allocation Bandwidth Constaints Model";
      }
    }
    description
      "Bandwidth constraint";
  }

  typedef Otn-payload {
    type enumeration {
      enum "unknown" {
        value 0;
        description
          "Payload unknown";
      }
      enum "bmp" {
        value 50;
        description
          "Bmp Payload";
      }
      enum "gfp-f" {
        value 54;
        description
          "Gfp_F Payload";
      }
      enum "gmp" {
        value 55;
        description
          "GMP Payload";
      }
      enum "gfp-f-ext" {
        value 70;
        description
          "Gfp_F_EXT Payload";
      }
    }
    description
      "Otn payload";
  }

  typedef Mpls-te-otn-snc-mode {
    type enumeration {
      enum "snc-n" {
        value 1;
        description
          "SNC N";
      }
      enum "snc-i" {
        value 2;
        description
          "SNC I";
      }
      enum "snc-s" {
        value 3;
        description
          "SNC S";
      }
    }
    description
      "Mpls te otn snc mode";
  }

  typedef Bfd-reverse-path {
    type enumeration {
      enum "bfd-reverse-path-binding-label" {
        value 1;
        description
          "BindingLabel";
      }
    }
    description
      "Bfd reverse path";
  }

  typedef Mpls-te-path-selection-metric {
    type enumeration {
      enum "igp" {
        value 1;
        description
          "IGP Metric";
      }
      enum "te" {
        value 2;
        description
          "TE Metric";
      }
      enum "delay" {
        value 4;
        description
          "DELAY Metric";
      }
    }
    description
      "Mpls te path selection metric";
  }

  typedef Mpls-te-path-option {
    type enumeration {
      enum "not-set" {
        value 0;
        description
          "Not Set";
      }
      enum "dynamic" {
        value 1;
        description
          "Dynamic";
      }
      enum "explicit-name" {
        value 3;
        description
          "Explicit, identified by name";
      }
      enum "explicit-number" {
        value 4;
        description
          "Explicit, identified by number";
      }
      enum "no-ero" {
        value 5;
        description
          "No ERO";
      }
      enum "sr" {
        value 6;
        description
          "Deprecated";
      }
    }
    description
      "Mpls te path option";
  }

  typedef Mpls-lcac-flooding-igp {
    type enumeration {
      enum "ospf" {
        value 0;
        description
          "OSPF";
      }
    }
    description
      "Mpls lcac flooding igp";
  }

  typedef Otn-protection-switch-lockout {
    type enumeration {
      enum "none" {
        value 0;
        description
          "No Lockout";
      }
      enum "working" {
        value 1;
        description
          "Lockout Working";
      }
    }
    description
      "Otn protection switch lockout";
  }

  typedef Mpls-te-tunnel-id {
    type enumeration {
      enum "auto" {
        value 0;
        description
          "Auto";
      }
      enum "explicit" {
        value 1;
        description
          "Explicit";
      }
    }
    description
      "Mpls te tunnel id";
  }

  typedef Otn-signaled-bandwidth {
    type enumeration {
      enum "odu1" {
        value 1;
        description
          "Signalled BW for ODU1";
      }
      enum "odu2" {
        value 2;
        description
          "Signalled BW for ODU2";
      }
      enum "odu3" {
        value 3;
        description
          "Signalled BW for ODU3";
      }
      enum "odu4" {
        value 4;
        description
          "Signalled BW for ODU4";
      }
      enum "odu0" {
        value 10;
        description
          "Signalled BW for ODU0";
      }
      enum "odu2e" {
        value 11;
        description
          "Signalled BW for ODU2e";
      }
      enum "od-uflex-cbr" {
        value 20;
        description
          "Signalled BW for ODUflex CBR";
      }
      enum "od-uflex-gfp-resize" {
        value 21;
        description
          "Signalled BW for ODUflex GFP Resizable";
      }
      enum "od-uflex-gfp-not-resize" {
        value 22;
        description
          "Signalled BW for ODUflex GFP not Resizable";
      }
      enum "odu1e" {
        value 23;
        description
          "Signalled BW for ODU1e";
      }
      enum "odu1f" {
        value 24;
        description
          "Signalled BW for ODU1f";
      }
      enum "odu2f" {
        value 25;
        description
          "Signalled BW for ODU2f";
      }
      enum "odu3e1" {
        value 26;
        description
          "Signalled BW for ODU3e1";
      }
      enum "odu3e2" {
        value 27;
        description
          "Signalled BW for ODU3e2";
      }
    }
    description
      "Otn signaled bandwidth";
  }

  typedef Mpls-te-bandwidth-dste {
    type enumeration {
      enum "standard-dste" {
        value 0;
        description
          "IETF-Standard DSTE";
      }
      enum "pre-standard-dste" {
        value 1;
        description
          "Pre-Standard DSTE";
      }
    }
    description
      "Mpls te bandwidth dste";
  }

  typedef Mpls-te-path-selection-invalidation-timer-expire {
    type enumeration {
      enum "tunnel-action-tear" {
        value 1;
        description
          "Tear down tunnel.";
      }
      enum "tunnel-action-drop" {
        value 2;
        description
          "Drop tunnel traffic.";
      }
    }
    description
      "Mpls te path selection invalidation timer expire";
  }

  typedef Attribute-set-affinity-name-length {
    type xr:Cisco-ios-xr-string {
      length "1..64";
    }
    description
      "Attribute set affinity name length";
  }

  typedef Mpls-te-path-diversity-conformance {
    type enumeration {
      enum "strict" {
        value 0;
        description
          "Strict";
      }
      enum "best-effort" {
        value 1;
        description
          "Best effort";
      }
    }
    description
      "Mpls te path diversity conformance";
  }

  typedef Mpls-te-uni-lsp-seg-flag {
    type enumeration {
      enum "unprotected" {
        value 0;
        description
          "UNPROTECTED";
      }
      enum "rerouting" {
        value 1;
        description
          "REROUTING";
      }
      enum "rerouting-no-et" {
        value 2;
        description
          "REROUTING NO ET";
      }
      enum "rerouting-one-to-n-et" {
        value 4;
        description
          "REROUTING ONE TO N ET";
      }
      enum "rerouting-one-plus-one-uni" {
        value 8;
        description
          "REROUTING ONE PLUS ONE UNI";
      }
      enum "rerouting-one-plus-one-bi" {
        value 16;
        description
          "REROUTING ONE PLUS ONE BI";
      }
    }
    description
      "Mpls te uni lsp seg flag";
  }

  typedef Mpls-lcac-flooding-threshold-percent-range {
    type uint32 {
      range "0..100";
    }
    description
      "Mpls lcac flooding threshold percent range";
  }

  typedef Ietf-mode {
    type enumeration {
      enum "standard" {
        value 3;
        description
          "IETF Standard";
      }
    }
    description
      "Ietf mode";
  }

  typedef Mpls-te-otn-aps-restoration-style {
    type enumeration {
      enum "keep-failed-lsp" {
        value 1;
        description
          "Keep Failed Lsp";
      }
      enum "delete-failed-lsp" {
        value 2;
        description
          "Delete Failed Lsp";
      }
    }
    description
      "Mpls te otn aps restoration style";
  }

  typedef Gmplstti-mode {
    type enumeration {
      enum "sm" {
        value 1;
        description
          "Section Monitoring";
      }
      enum "pm" {
        value 2;
        description
          "Path Monitoring";
      }
      enum "tcm" {
        value 3;
        description
          "Tandem Connection";
      }
    }
    description
      "Gmplstti mode";
  }

  typedef Mpls-te-switching-encoding {
    type enumeration {
      enum "packet" {
        value 1;
        description
          "Packet";
      }
      enum "ethernet" {
        value 2;
        description
          "Ethernet";
      }
      enum "sondet-sdh" {
        value 5;
        description
          "SONET SDH";
      }
    }
    description
      "Mpls te switching encoding";
  }

  typedef Mpls-te-sig-name-option {
    type enumeration {
      enum "none" {
        value 0;
        description
          "None";
      }
      enum "address" {
        value 1;
        description
          "Address";
      }
      enum "name" {
        value 2;
        description
          "Name";
      }
    }
    description
      "Mpls te sig name option";
  }

  typedef Mpls-te-policy-class-range {
    type uint32 {
      range "1..8";
    }
    description
      "Mpls te policy class range";
  }

  typedef Mesh-group-id {
    type uint32 {
      range "0..4294967295";
    }
    description
      "Mesh group id";
  }

  typedef Path-invalidation-action {
    type enumeration {
      enum "tear" {
        value 1;
        description
          "Tear";
      }
      enum "drop" {
        value 2;
        description
          "Drop";
      }
    }
    description
      "Path invalidation action";
  }

  typedef Mpls-te-switching-index {
    type union {
      type enumeration {
        enum "link" {
          value 255;
          description
            "Link";
        }
      }
      type uint32 {
        range "1..255";
      }
    }
    description
      "Mpls te switching index";
  }

  typedef Mpls-te-igp-protocol {
    type enumeration {
      enum "none" {
        value 0;
        description
          "Not set";
      }
      enum "isis" {
        value 1;
        description
          "IS IS";
      }
      enum "ospf" {
        value 2;
        description
          "OSPF";
      }
    }
    description
      "Mpls te igp protocol";
  }

  typedef Binding-segment-id {
    type enumeration {
      enum "any-label" {
        value 1;
        description
          "AnyLabel";
      }
      enum "specified-label" {
        value 2;
        description
          "SpecifiedLabel";
      }
    }
    description
      "Binding segment id";
  }

  typedef Mpls-te-backup-bandwidth-pool {
    type enumeration {
      enum "any-pool" {
        value 1;
        description
          "Any Pool";
      }
      enum "global-pool" {
        value 2;
        description
          "Global Pool";
      }
      enum "sub-pool" {
        value 4;
        description
          "Sub Pool";
      }
    }
    description
      "Mpls te backup bandwidth pool";
  }

  typedef Mpls-te-switching-encode {
    type enumeration {
      enum "none" {
        value 0;
        description
          "None";
      }
      enum "packet" {
        value 1;
        description
          "Packet";
      }
      enum "ethernet" {
        value 2;
        description
          "Ethernet";
      }
      enum "sondet-sdh" {
        value 5;
        description
          "SONET SDH";
      }
    }
    description
      "Mpls te switching encode";
  }

  typedef Mpls-te-backup-bandwidth-class {
    type enumeration {
      enum "class0" {
        value 0;
        description
          "Class 0";
      }
      enum "class1" {
        value 1;
        description
          "Class 1";
      }
      enum "any-class" {
        value 9;
        description
          "Any Class";
      }
    }
    description
      "Mpls te backup bandwidth class";
  }

  typedef Mpls-te-path-option-protection {
    type enumeration {
      enum "active" {
        value 0;
        description
          "Active path";
      }
      enum "protecting" {
        value 1;
        description
          "Protecting Path";
      }
    }
    description
      "Mpls te path option protection";
  }

  typedef Mpls-te-bandwidth-limit {
    type enumeration {
      enum "unlimited" {
        value 64;
        description
          "Unlimited";
      }
      enum "limited" {
        value 128;
        description
          "Limited";
      }
    }
    description
      "Mpls te bandwidth limit";
  }

  grouping OOR-ACCEPT-REOPT-LSP {
    description
      "Common node of oor-green-state, oor-yellow-state,
       oor-red-state, lsp-oor-green-state,
       lsp-oor-yellow-state, lsp-oor-red-state";
    leaf oor-accept-reopt-lsp {
      type empty;
      description
        "Allow the setup of reoptimized LSPs over the
         link in this OOR State";
    }
  }

  grouping MULTIPLIER {
    description
      "Common node of bfd-over-lsp, bfd-over-named-lsp";
    leaf multiplier {
      type uint32 {
        range "3..10";
      }
      description
        "Specify the multiplier for BFD failure detection";
    }
  }

  grouping PATH-ERROR-MESSAGE {
    description
      "Common node of logging, auto-mesh-logging";
    leaf path-error-message {
      type empty;
      description
        "Log tunnel messages for path error";
    }
  }

  grouping PCALC-FAILURE-MESSAGE {
    description
      "Common node of logging, auto-mesh-logging";
    leaf pcalc-failure-message {
      type empty;
      description
        "Enable logging for path-calculation failures";
    }
  }

  grouping REOPTIMIZE-TIMER-FREQUENCY {
    description
      "Common node of tunnel-te-attributes,
       tunnel-attributes";
    leaf reoptimize-timer-frequency {
      type uint32 {
        range "0..65535";
      }
      units "second";
      description
        "Tunnel reoptimize timers period in seconds";
    }
  }

  grouping POLICY-CLASSES {
    description
      "Common node of tunnel-te-attributes,
       auto-mesh-attribute, auto-backup-attribute";
    container policy-classes {
      description
        "Policy classes for PBTS";
      leaf-list policy-class {
        type Mpls-te-policy-class-range;
        max-elements 7;
        description
          "Array of Policy class";
      }
    }
  }

  grouping MINIMUM-INTERVAL {
    description
      "Common node of bfd-over-lsp, bfd-over-named-lsp";
    leaf minimum-interval {
      type uint32 {
        range "3..30000";
      }
      units "millisecond";
      description
        "Specify the minimum interval in milliseconds for
         BFD failure detection";
    }
  }

  grouping UNPROTECTED-TRANSIT-LSP-THRESHOLD {
    description
      "Common node of lsp-oor-yellow-state,
       lsp-oor-red-state";
    leaf unprotected-transit-lsp-threshold {
      type uint32;
      description
        "Threshold for unprotected transit LSPs";
    }
  }

  grouping AFFINITY-MASK {
    description
      "Common node of tunnel-te-attributes,
       tunnel-attributes, auto-mesh-attribute,
       auto-backup-attribute, path-option-attribute,
       p2mpte-attribute, p2p-te-attribute";
    container affinity-mask {
      presence "Indicates a affinity-mask node is configured.";
      description
        "Set the affinity flags and mask";
      leaf affinity {
        type xr:Hex-integer;
        mandatory true;
        description
          "Affinity flags";
      }
      leaf mask {
        type xr:Hex-integer;
        mandatory true;
        description
          "Affinity mask";
      }
    }
  }

  grouping BANDWIDTH-CHANGE-MESSAGE {
    description
      "Common node of logging, auto-backup-logging,
       auto-mesh-logging";
    leaf bandwidth-change-message {
      type empty;
      description
        "Log tunnel messages for bandwidth change";
    }
  }

  grouping REOPTIMIZE-ATTEMPTS-MESSAGE {
    description
      "Common node of logging, auto-backup-logging,
       auto-mesh-logging";
    leaf reoptimize-attempts-message {
      type empty;
      description
        "Log tunnel reoptimization attempts messages";
    }
  }

  grouping OOR-AVAILABLE-BANDWIDTH-PERCENTAGE {
    description
      "Common node of oor-green-state, oor-yellow-state,
       oor-red-state, lsp-oor-green-state,
       lsp-oor-yellow-state, lsp-oor-red-state";
    leaf oor-available-bandwidth-percentage {
      type uint32 {
        range "0..100";
      }
      units "percentage";
      default "100";
      description
        "Flood a specific percentage of the available
         bandwidth";
    }
  }

  grouping TIMERS {
    description
      "Common node of backup, mesh";
    container timers {
      description
        "Configure auto-tunnel backup timers value";
      container removal {
        description
          "Configure auto-tunnel backup removal timers
           value";
        leaf unused {
          type uint32 {
            range "0..10080";
          }
          units "minute";
          default "3600";
          description
            "Auto-tunnel backup unused timeout in minutes
             (0=never timeout)";
        }
      }
    }
  }

  grouping TUNNEL-PATH-SELECTION {
    description
      "Common node of tunnel-te-attributes,
       tunnel-attributes";
    container tunnel-path-selection {
      description
        "Configure path selection properties";
      leaf tiebreaker {
        type Mpls-te-path-selection-tiebreaker;
        description
          "CSPF tiebreaker to use in path calculation";
      }
      leaf path-selection-hop-limit {
        type uint32 {
          range "1..255";
        }
        description
          "Path selection hop limit configuration for this
           specific tunnel";
      }
      uses PATH-SELECTION-DELAY-LIMIT;
      uses INVALIDATION;
      uses PATH-SELECTION-COST-LIMIT;
    }
  }

  grouping INVALIDATION {
    description
      "Common node of tunnel-te-attributes,
       tunnel-attributesCommon node of
       tunnel-path-selection,
       att-path-option-path-selection";
    container invalidation {
      presence "enable invalidation";
      description
        "Deprecated";
      leaf path-invalidation-timeout {
        type uint32 {
          range "0..60000";
        }
        description
          "Path Invalidation Timeout";
      }
      leaf path-invalidation-action {
        type Path-invalidation-action;
        description
          "Path Invalidation Action";
      }
    }
  }

  grouping PRECEDENCE {
    description
      "Common node of peer, pce-attributes";
    leaf precedence {
      type uint32 {
        range "0..255";
      }
      description
        "Precedence order";
    }
  }

  grouping SOFT-PREEMPTION {
    description
      "Common node of tunnel-attributes,
       tunnel-te-attributes, auto-mesh-attribute,
       auto-backup-attribute, p2mp-auto-tunnel,
       p2p-auto-tunnel";
    leaf soft-preemption {
      type empty;
      description
        "Enable the soft-preemption feature on the tunnel";
    }
  }

  grouping PATH-SELECTION-COST-LIMIT {
    description
      "Common node of tunnel-path-selection,
       att-path-option-path-selection";
    leaf path-selection-cost-limit {
      type uint32 {
        range "1..4294967295";
      }
      description
        "Path selection cost limit configuration for this
         specific tunnel";
    }
  }

  grouping AUTO-BANDWIDTH {
    description
      "Common node of tunnel-attributes,
       tunnel-te-attributes";
    container auto-bandwidth {
      description
        "Tunnel Interface Auto-bandwidth configuration
         data";
      container underflow {
        presence "Indicates a underflow node is configured.";
        description
          "Configuring the tunnel underflow detection";
        leaf underflow-threshold-percent {
          type uint32 {
            range "1..100";
          }
          units "percentage";
          mandatory true;
          description
            "Bandwidth change percent to trigger an
             underflow";
        }
        leaf underflow-threshold-value {
          type uint32 {
            range "10..4294967295";
          }
          units "kbit/s";
          mandatory true;
          description
            "Bandwidth change value to trigger an underflow
             (kbps)";
        }
        leaf underflow-threshold-limit {
          type uint32 {
            range "1..10";
          }
          mandatory true;
          description
            "Number of consecutive collections exceeding
             threshold";
        }
      }
      container overflow {
        presence "Indicates a overflow node is configured.";
        description
          "Configuring the tunnel overflow detection";
        leaf overflow-threshold-percent {
          type uint32 {
            range "1..100";
          }
          units "percentage";
          mandatory true;
          description
            "Bandwidth change percent to trigger an
             overflow";
        }
        leaf overflow-threshold-value {
          type uint32 {
            range "10..4294967295";
          }
          units "kbit/s";
          mandatory true;
          description
            "Bandwidth change value to trigger an overflow
             (kbps)";
        }
        leaf overflow-threshold-limit {
          type uint32 {
            range "1..10";
          }
          mandatory true;
          description
            "Number of consecutive collections exceeding
             threshold";
        }
      }
      container bandwidth-limits {
        presence "Indicates a bandwidth-limits node is configured.";
        description
          "Set min/max bandwidth auto-bw can apply on a
           tunnel";
        leaf bandwidth-min-limit {
          type uint32 {
            range "0..4294967295";
          }
          mandatory true;
          description
            "Set minimum bandwidth auto-bw can apply on a
             tunnel";
        }
        leaf bandwidth-max-limit {
          type uint32 {
            range "0..4294967295";
          }
          mandatory true;
          description
            "Set maximum bandwidth auto-bw can apply on a
             tunnel";
        }
      }
      container adjustment-threshold {
        presence "Indicates a adjustment-threshold node is configured.";
        description
          "Set the bandwidth change threshold to trigger
           adjustment";
        leaf adjustment-threshold-percent {
          type uint32 {
            range "1..100";
          }
          units "percentage";
          mandatory true;
          description
            "Bandwidth change percent to trigger adjustment";
        }
        leaf adjustment-threshold-value {
          type uint32 {
            range "10..4294967295";
          }
          units "kbit/s";
          mandatory true;
          description
            "Bandwidth change value to trigger adjustment
             (kbps)";
        }
      }
      container auto-capacity {
        description
          "Tunnel auto-capacity configuration data";
        leaf nominal-bandwidth {
          type uint32 {
            range "0..4294967295";
          }
          units "kbit/s";
          description
            "Bandwidth value used to compute the desired
             number of tunnels for auto-capacity";
        }
        leaf enable {
          type boolean;
          description
            "Enable auto-capacityThe object must be set
             before any other auto capacity configuration
             is supplied for the tunnel,and must be the
             last auto-capacity configuration object to be
             removed.";
        }
        leaf clones-minimum {
          type uint32 {
            range "0..63";
          }
          default "0";
          description
            "Lower limit on the number of clones can be
             created for the tunnel";
        }
        leaf split-bandwidth {
          type uint32 {
            range "0..4294967295";
          }
          units "kbit/s";
          description
            "Upper bandwidth limit that causes the tunnel
             to be split";
        }
        leaf merge-bandwidth {
          type uint32 {
            range "0..4294967295";
          }
          units "kbit/s";
          description
            "Lower bandwidth limit that causes the tunnel
             to be merged";
        }
        leaf clones-maximum {
          type uint32 {
            range "0..63";
          }
          default "63";
          description
            "Upper limit on the number of clones can be
             created for the tunnel";
        }
      }
      leaf underflow-enable {
        type boolean;
        description
          "Enable auto bandwidth underflow detection";
      }
      leaf resignal-last-bandwidth-time-out {
        type uint32 {
          range "1..3600000";
        }
        units "second";
        description
          "Set the tunnel auto-bw resignal last bandwidth
           time-out in seconds";
      }
      leaf enabled {
        type boolean;
        description
          "This object is only valid for tunnel interfaces
           and it controls whether that interface has
           auto-bw enabled on it or not.The object must be
           set before any other auto-bw configuration is
           supplied for the interface, and must be the
           last auto-bw configuration object to be removed
           .";
      }
      leaf application-frequency {
        type uint32 {
          range "5..10080";
        }
        units "minute";
        description
          "Set the tunnel auto-bw application frequency in
           minutes";
      }
      leaf overflow-enable {
        type boolean;
        description
          "Enable auto bandwidth overflow detection";
      }
      uses COLLECTION-ONLY;
    }
  }

  grouping RECORD-ROUTE {
    description
      "Common node of tunnel-attributes,
       tunnel-te-attributes, auto-mesh-attribute,
       auto-backup-attribute, gmpls-unitunnel-head,
       p2mpte-attribute, tunnel-head";
    leaf record-route {
      type empty;
      description
        "Record the route used by the tunnel";
    }
  }

  grouping OOR-RECOVERY-DURATION {
    description
      "Common node of oor-green-state,
       lsp-oor-green-state";
    leaf oor-recovery-duration {
      type uint32 {
        range "0..10080";
      }
      units "minute";
      default "0";
      description
        "Period of time (minutes) during which the action
         in Green state are applied. After this period,
         the processing in TE goes back to normal state";
    }
  }

  grouping SRLG-DIVERSE {
    description
      "Common node of tunnel-path-protection,
       named-tunnel-path-protection";
    leaf srlg-diverse {
      type empty;
      description
        "Enforce SRLG diversity for protection LSP";
    }
  }

  grouping OOR-ACCEPT-LSP-MIN-BANDWIDTH {
    description
      "Common node of oor-green-state, oor-yellow-state,
       oor-red-state, lsp-oor-green-state,
       lsp-oor-yellow-state, lsp-oor-red-state";
    leaf oor-accept-lsp-min-bandwidth {
      type uint32;
      units "kbit/s";
      default "0";
      description
        "Only accept LSPs with at least the specified
         bandwidth (in kbps).";
    }
  }

  grouping LOGGING {
    description
      "Common node of tunnel-te-attributes,
       tunnel-attributes, p2p-te-attribute";
    container logging {
      description
        "Log tunnel LSP messages";
      leaf lsp-switch-over-change-message {
        type empty;
        description
          "Log tunnel messages for bandwidth change";
      }
      leaf all {
        type empty;
        description
          "Log all events for a tunnel";
      }
      leaf record-route-messsage {
        type empty;
        description
          "Log tunnel record-route messages";
      }
      leaf bfd-state-message {
        type empty;
        description
          "Enable BFD session state change alarm";
      }
      uses BANDWIDTH-CHANGE-MESSAGE;
      uses REOPTIMIZE-ATTEMPTS-MESSAGE;
      uses REROUTE-MESSSAGE;
      uses STATE-MESSAGE;
      uses PATH-ERROR-MESSAGE;
      uses INSUFFICIENT-BW-MESSAGE;
      uses REOPTIMIZED-MESSAGE;
      uses PCALC-FAILURE-MESSAGE;
    }
  }

  grouping MPLS-MTE-TUNNEL-CFG-LOGGING {
    description
      "Common node of tunnel-te-attributes,
       tunnel-attributes, p2p-te-attributeCommon node of
       mte-tunnel-attributes, p2mpte-attribute";
    container logging {
      description
        "Log tunnel LSP messages";
      leaf insufficient-bw-message {
        type empty;
        description
          "Log tunnel messages for insufficient bandwidth";
      }
      leaf reoptimized-message {
        type empty;
        description
          "Log tunnel reoptimized messages";
      }
      leaf bandwidth-change-message {
        type empty;
        description
          "Log tunnel bandwidth change messages";
      }
      leaf all {
        type empty;
        description
          "Log all events for a tunnel";
      }
      leaf pcalc-failure-message {
        type empty;
        description
          "Enable logging for path-calculation failures";
      }
      leaf state-message {
        type empty;
        description
          "Log tunnel state messages";
      }
      leaf reoptimize-attempts-message {
        type empty;
        description
          "Log tunnel reoptimization attempts messages";
      }
      leaf sub-lsp-state-message {
        type empty;
        description
          "Log all tunnel sub-LSP state messages";
      }
      leaf reroute-messsage {
        type empty;
        description
          "Log tunnel rereoute messages";
      }
    }
  }

  grouping COLLECTION-ONLY {
    description
      "Common node of auto-bandwidth,
       auto-mesh-attribute";
    leaf collection-only {
      type empty;
      description
        "Enable bandwidth collection only, no auto-bw
         adjustment";
    }
  }

  grouping PCE {
    description
      "Common node of path-option-attribute,
       p2p-te-attribute";
    container pce {
      description
        "Configure pce properties";
      container bidirectional {
        presence "Indicates a bidirectional node is configured.";
        description
          "Bidirectional parameters";
        leaf bd-source-address {
          type inet:ipv4-address-no-zone;
          mandatory true;
          description
            "Bidirectional Source IP Address";
        }
        leaf bd-group-id {
          type uint32 {
            range "1..4294967295";
          }
          mandatory true;
          description
            "Bidirectional Group ID";
        }
      }
      container disjoint-path {
        presence "Indicates a disjoint-path node is configured.";
        description
          "Disjoint path parameters";
        leaf dp-source-address {
          type inet:ipv4-address-no-zone;
          mandatory true;
          description
            "Disjoint Path Source IP Address";
        }
        leaf dp-type {
          type uint32 {
            range "1..3";
          }
          mandatory true;
          description
            "Disjoint Path Type";
        }
        leaf dp-group-id {
          type uint32 {
            range "1..4294967295";
          }
          mandatory true;
          description
            "Disjoint Path Group ID";
        }
      }
      leaf enable {
        type empty;
        description
          "Always set to true";
      }
    }
  }

  grouping DESTINATION {
    description
      "Common node of tunnel-te-attributes,
       tunnel-attributes";
    leaf destination {
      type inet:ipv4-address-no-zone;
      description
        "Set the destination of the tunnel";
    }
  }

  grouping STATE-MESSAGE {
    description
      "Common node of logging, logging,
       auto-backup-logging, auto-mesh-logging";
    leaf state-message {
      type empty;
      description
        "Log tunnel state messages";
    }
  }

  grouping LOAD-SHARE {
    description
      "Common node of tunnel-attributes,
       tunnel-te-attributes, auto-mesh-attribute";
    leaf load-share {
      type uint32 {
        range "1..4294967295";
      }
      description
        "Tunnel loadsharing metric";
    }
  }

  grouping PATH-SELECTION {
    description
      "Common node of auto-mesh-attribute, xro-attribute
       , auto-backup-attribute, p2mpte-attribute,
       otn-pp-attribute, uni-p-attribute";
    container path-selection {
      description
        "Configure path selection properties";
      leaf enable {
        type empty;
        description
          "Enable path selection";
      }
    }
  }

  grouping SIGNALLED-NAME {
    description
      "Common node of tunnel-te-attributes,
       gmpls-unitunnel-head, tunnel-head";
    leaf signalled-name {
      type string {
        length "1..254";
      }
      description
        "The name of the tunnel to be included in
         signalling messages";
    }
  }

  grouping REOPTIMIZED-MESSAGE {
    description
      "Common node of logging, auto-backup-logging,
       auto-mesh-logging";
    leaf reoptimized-message {
      type empty;
      description
        "Log tunnel reoptimized messages";
    }
  }

  grouping NEW-STYLE-AFFINITY-TABLE {
    description
      "Common node of logging, auto-backup-logging,
       auto-mesh-loggingCommon node of tunnel-attributes
       , tunnel-te-attributes, path-option-attribute,
       auto-backup-attribute, auto-mesh-attribute,
       p2mpte-attribute, p2p-te-attribute";
    container new-style-affinity-affinity-types {
      description
        "Tunnel new style affinity attributes table";
      list new-style-affinity-affinity-type {
        key "affinity-type";
        description
          "Tunnel new style affinity attribute";
        leaf affinity-type {
          type Mpls-te-tunnel-affinity;
          description
            "The type of the affinity entry";
        }
      }
      list new-style-affinity-affinity-type-affinity1 {
        key "affinity-type affinity1";
        description
          "Tunnel new style affinity attribute";
        leaf affinity-type {
          type Mpls-te-tunnel-affinity;
          description
            "The type of the affinity entry";
        }
        leaf affinity1 {
          type xr:Cisco-ios-xr-string;
          description
            "The name of the first affinity";
        }
      }
      list new-style-affinity-affinity-type-affinity1-affinity2 {
        key "affinity-type affinity1 affinity2";
        description
          "Tunnel new style affinity attribute";
        leaf affinity-type {
          type Mpls-te-tunnel-affinity;
          description
            "The type of the affinity entry";
        }
        leaf affinity1 {
          type xr:Cisco-ios-xr-string;
          description
            "The name of the first affinity";
        }
        leaf affinity2 {
          type xr:Cisco-ios-xr-string;
          description
            "The name of the second affinity";
        }
      }
      list new-style-affinity-affinity-type-affinity1-affinity2-affinity3 {
        key "affinity-type affinity1 affinity2 affinity3";
        description
          "Tunnel new style affinity attribute";
        leaf affinity-type {
          type Mpls-te-tunnel-affinity;
          description
            "The type of the affinity entry";
        }
        leaf affinity1 {
          type xr:Cisco-ios-xr-string;
          description
            "The name of the first affinity";
        }
        leaf affinity2 {
          type xr:Cisco-ios-xr-string;
          description
            "The name of the second affinity";
        }
        leaf affinity3 {
          type xr:Cisco-ios-xr-string;
          description
            "The name of the third affinity";
        }
      }
      list new-style-affinity-affinity-type-affinity1-affinity2-affinity3-affinity4 {
        key "affinity-type affinity1 affinity2 affinity3 affinity4";
        description
          "Tunnel new style affinity attribute";
        leaf affinity-type {
          type Mpls-te-tunnel-affinity;
          description
            "The type of the affinity entry";
        }
        leaf affinity1 {
          type xr:Cisco-ios-xr-string;
          description
            "The name of the first affinity";
        }
        leaf affinity2 {
          type xr:Cisco-ios-xr-string;
          description
            "The name of the second affinity";
        }
        leaf affinity3 {
          type xr:Cisco-ios-xr-string;
          description
            "The name of the third affinity";
        }
        leaf affinity4 {
          type xr:Cisco-ios-xr-string;
          description
            "The name of the fourth affinity";
        }
      }
      list new-style-affinity-affinity-type-affinity1-affinity2-affinity3-affinity4-affinity5 {
        key "affinity-type affinity1 affinity2 affinity3 affinity4 affinity5";
        description
          "Tunnel new style affinity attribute";
        leaf affinity-type {
          type Mpls-te-tunnel-affinity;
          description
            "The type of the affinity entry";
        }
        leaf affinity1 {
          type xr:Cisco-ios-xr-string;
          description
            "The name of the first affinity";
        }
        leaf affinity2 {
          type xr:Cisco-ios-xr-string;
          description
            "The name of the second affinity";
        }
        leaf affinity3 {
          type xr:Cisco-ios-xr-string;
          description
            "The name of the third affinity";
        }
        leaf affinity4 {
          type xr:Cisco-ios-xr-string;
          description
            "The name of the fourth affinity";
        }
        leaf affinity5 {
          type xr:Cisco-ios-xr-string;
          description
            "The name of the fifth affinity";
        }
      }
      list new-style-affinity-affinity-type-affinity1-affinity2-affinity3-affinity4-affinity5-affinity6 {
        key "affinity-type affinity1 affinity2 affinity3 affinity4 affinity5 affinity6";
        description
          "Tunnel new style affinity attribute";
        leaf affinity-type {
          type Mpls-te-tunnel-affinity;
          description
            "The type of the affinity entry";
        }
        leaf affinity1 {
          type xr:Cisco-ios-xr-string;
          description
            "The name of the first affinity";
        }
        leaf affinity2 {
          type xr:Cisco-ios-xr-string;
          description
            "The name of the second affinity";
        }
        leaf affinity3 {
          type xr:Cisco-ios-xr-string;
          description
            "The name of the third affinity";
        }
        leaf affinity4 {
          type xr:Cisco-ios-xr-string;
          description
            "The name of the fourth affinity";
        }
        leaf affinity5 {
          type xr:Cisco-ios-xr-string;
          description
            "The name of the fifth affinity";
        }
        leaf affinity6 {
          type xr:Cisco-ios-xr-string;
          description
            "The name of the sixth affinity";
        }
      }
      list new-style-affinity-affinity-type-affinity1-affinity2-affinity3-affinity4-affinity5-affinity6-affinity7 {
        key "affinity-type affinity1 affinity2 affinity3 affinity4 affinity5 affinity6 affinity7";
        description
          "Tunnel new style affinity attribute";
        leaf affinity-type {
          type Mpls-te-tunnel-affinity;
          description
            "The type of the affinity entry";
        }
        leaf affinity1 {
          type xr:Cisco-ios-xr-string;
          description
            "The name of the first affinity";
        }
        leaf affinity2 {
          type xr:Cisco-ios-xr-string;
          description
            "The name of the second affinity";
        }
        leaf affinity3 {
          type xr:Cisco-ios-xr-string;
          description
            "The name of the third affinity";
        }
        leaf affinity4 {
          type xr:Cisco-ios-xr-string;
          description
            "The name of the fourth affinity";
        }
        leaf affinity5 {
          type xr:Cisco-ios-xr-string;
          description
            "The name of the fifth affinity";
        }
        leaf affinity6 {
          type xr:Cisco-ios-xr-string;
          description
            "The name of the sixth affinity";
        }
        leaf affinity7 {
          type xr:Cisco-ios-xr-string;
          description
            "The name of the seventh affinity";
        }
      }
      list new-style-affinity-affinity-type-affinity1-affinity2-affinity3-affinity4-affinity5-affinity6-affinity7-affinity8 {
        key "affinity-type affinity1 affinity2 affinity3 affinity4 affinity5 affinity6 affinity7 affinity8";
        description
          "Tunnel new style affinity attribute";
        leaf affinity-type {
          type Mpls-te-tunnel-affinity;
          description
            "The type of the affinity entry";
        }
        leaf affinity1 {
          type xr:Cisco-ios-xr-string;
          description
            "The name of the first affinity";
        }
        leaf affinity2 {
          type xr:Cisco-ios-xr-string;
          description
            "The name of the second affinity";
        }
        leaf affinity3 {
          type xr:Cisco-ios-xr-string;
          description
            "The name of the third affinity";
        }
        leaf affinity4 {
          type xr:Cisco-ios-xr-string;
          description
            "The name of the fourth affinity";
        }
        leaf affinity5 {
          type xr:Cisco-ios-xr-string;
          description
            "The name of the fifth affinity";
        }
        leaf affinity6 {
          type xr:Cisco-ios-xr-string;
          description
            "The name of the sixth affinity";
        }
        leaf affinity7 {
          type xr:Cisco-ios-xr-string;
          description
            "The name of the seventh affinity";
        }
        leaf affinity8 {
          type xr:Cisco-ios-xr-string;
          description
            "The name of the eighth affinity";
        }
      }
      list new-style-affinity-affinity-type-affinity1-affinity2-affinity3-affinity4-affinity5-affinity6-affinity7-affinity8-affinity9 {
        key "affinity-type affinity1 affinity2 affinity3 affinity4 affinity5 affinity6 affinity7 affinity8 affinity9";
        description
          "Tunnel new style affinity attribute";
        leaf affinity-type {
          type Mpls-te-tunnel-affinity;
          description
            "The type of the affinity entry";
        }
        leaf affinity1 {
          type xr:Cisco-ios-xr-string;
          description
            "The name of the first affinity";
        }
        leaf affinity2 {
          type xr:Cisco-ios-xr-string;
          description
            "The name of the second affinity";
        }
        leaf affinity3 {
          type xr:Cisco-ios-xr-string;
          description
            "The name of the third affinity";
        }
        leaf affinity4 {
          type xr:Cisco-ios-xr-string;
          description
            "The name of the fourth affinity";
        }
        leaf affinity5 {
          type xr:Cisco-ios-xr-string;
          description
            "The name of the fifth affinity";
        }
        leaf affinity6 {
          type xr:Cisco-ios-xr-string;
          description
            "The name of the sixth affinity";
        }
        leaf affinity7 {
          type xr:Cisco-ios-xr-string;
          description
            "The name of the seventh affinity";
        }
        leaf affinity8 {
          type xr:Cisco-ios-xr-string;
          description
            "The name of the eighth affinity";
        }
        leaf affinity9 {
          type xr:Cisco-ios-xr-string;
          description
            "The name of the nineth affinity";
        }
      }
      list new-style-affinity-affinity-type-affinity1-affinity2-affinity3-affinity4-affinity5-affinity6-affinity7-affinity8-affinity9-affinity10 {
        key "affinity-type affinity1 affinity2 affinity3 affinity4 affinity5 affinity6 affinity7 affinity8 affinity9 affinity10";
        description
          "Tunnel new style affinity attribute";
        leaf affinity-type {
          type Mpls-te-tunnel-affinity;
          description
            "The type of the affinity entry";
        }
        leaf affinity1 {
          type xr:Cisco-ios-xr-string;
          description
            "The name of the first affinity";
        }
        leaf affinity2 {
          type xr:Cisco-ios-xr-string;
          description
            "The name of the second affinity";
        }
        leaf affinity3 {
          type xr:Cisco-ios-xr-string;
          description
            "The name of the third affinity";
        }
        leaf affinity4 {
          type xr:Cisco-ios-xr-string;
          description
            "The name of the fourth affinity";
        }
        leaf affinity5 {
          type xr:Cisco-ios-xr-string;
          description
            "The name of the fifth affinity";
        }
        leaf affinity6 {
          type xr:Cisco-ios-xr-string;
          description
            "The name of the sixth affinity";
        }
        leaf affinity7 {
          type xr:Cisco-ios-xr-string;
          description
            "The name of the seventh affinity";
        }
        leaf affinity8 {
          type xr:Cisco-ios-xr-string;
          description
            "The name of the eighth affinity";
        }
        leaf affinity9 {
          type xr:Cisco-ios-xr-string;
          description
            "The name of the nineth affinity";
        }
        leaf affinity10 {
          type xr:Cisco-ios-xr-string;
          description
            "The name of the tenth affinity";
        }
      }
    }
  }

  grouping FAST-REROUTE {
    description
      "Common node of tunnel-attributes,
       tunnel-te-attributes, auto-mesh-attribute,
       p2mpte-attribute";
    container fast-reroute {
      presence "Indicates a fast-reroute node is configured.";
      description
        "Specify MPLS tunnel can be fast-rerouted";
      leaf bandwidth-protection {
        type uint32 {
          range "0..1";
        }
        mandatory true;
        description
          "Bandwidth Protection";
      }
      leaf node-protection {
        type uint32 {
          range "0..1";
        }
        mandatory true;
        description
          "Node Protection";
      }
    }
  }

  grouping TUNNEL-RANGE {
    description
      "Common node of backup, mesh, p2mp-auto-tunnel,
       p2p-auto-tunnel, pcc";
    container tunnel-range {
      presence "Indicates a tunnel-range node is configured.";
      description
        "Configure tunnel ID range for auto-tunnel
         features";
      leaf min-tunnel-id {
        type uint32 {
          range "0..65535";
        }
        mandatory true;
        description
          "Minimum tunnel ID for auto-tunnels";
      }
      leaf max-tunnel-id {
        type uint32 {
          range "0..65535";
        }
        mandatory true;
        description
          "Maximum tunnel ID for auto-tunnels";
      }
    }
  }

  grouping DELAY-MEASUREMENT {
    description
      "Common node of tunnel-attributes,
       tunnel-te-attributes";
    leaf delay-measurement {
      type empty;
      description
        "Enable the delay-measurement feature on the
         tunnel";
    }
  }

  grouping ENABLE {
    description
      "Common node of path-selection,
       att-path-option-path-selection";
    leaf enable {
      type empty;
      description
        "Enter path selection configuration";
    }
  }

  grouping MPLS-TE-TUNNEL-CFG-ENABLE {
    description
      "Common node of path-selection,
       att-path-option-path-selectionCommon node of
       bfd-over-lsp, bfd-over-named-lsp";
    leaf enable {
      type empty;
      description
        "Always set to true";
    }
  }

  grouping MPLS-TE-TUNNEL-CFG-ENABLE-MP {
    description
      "Common node of path-selection,
       att-path-option-path-selectionCommon node of
       bfd-over-lsp, bfd-over-named-lspCommon node of
       tunnel-path-protection,
       named-tunnel-path-protection";
    leaf enable {
      type empty;
      description
        "Enable Path Protection";
    }
  }

  grouping AUTOROUTE {
    description
      "Common node of tunnel-attributes,
       tunnel-te-attributes";
    container autoroute {
      description
        "Parameters for IGP routing over tunnel";
      container autoroute-announce {
        description
          "Announce tunnel to IGP";
        container exclude-traffic {
          description
            "Exclude traffic on autorouted tunnel";
          leaf segment-routing-all {
            type uint32 {
              range "0..2";
            }
            description
              "Traffic type to exclude (0 - none, 1 - SR, 2
               - all)";
          }
          leaf segment-routing {
            type empty;
            description
              "Exclude tunnel in IGP for SR prefixes";
          }
        }
        container metric {
          description
            "Specify MPLS tunnel metric";
          leaf metric-type {
            type Mpls-te-autoroute-metric;
            description
              "Autoroute tunnel metric type";
          }
          leaf absolute-metric {
            when "../metric-type = 'absolute'" {
              description
                "../MetricType = Absolute";
            }
            type uint32 {
              range "1..2147483647";
            }
            description
              "The absolute metric value";
          }
          leaf relative-metric {
            when "../metric-type = 'relative'" {
              description
                "../MetricType = Relative";
            }
            type int32 {
              range "-10..10";
            }
            description
              "The value of the adjustment";
          }
          leaf constant-metric {
            when "../metric-type = 'constant'" {
              description
                "../MetricType = Constant";
            }
            type uint32 {
              range "1..2147483647";
            }
            description
              "The constant metric value";
          }
        }
        leaf enable {
          type empty;
          description
            "Enable autoroute announce";
        }
        leaf include-ipv6 {
          type empty;
          description
            "Specify that the tunnel should be an IPv6
             autoroute announce also";
        }
      }
      container destinations {
        description
          "Tunnel Autoroute Destination(s)";
        list destination {
          key "destination-address";
          description
            "Destination address to add in RIB";
          leaf destination-address {
            type inet:ipv4-address-no-zone;
            description
              "IP address of destination";
          }
        }
      }
    }
  }

  grouping OOR-NODE-PROTECTION-DISABLE {
    description
      "Common node of oor-green-state, oor-yellow-state,
       oor-red-state";
    leaf oor-node-protection-disable {
      type empty;
      description
        "Disable FRR node-protection when the link is in
         this OOR State";
    }
  }

  grouping FAST-DETECT {
    description
      "Common node of bfd-over-lsp, bfd-over-named-lsp";
    leaf fast-detect {
      type Mpls-tebfd-session;
      description
        "Enable BFD Fast Detect On the tunnel";
    }
  }

  grouping REROUTE-MESSSAGE {
    description
      "Common node of logging, auto-mesh-logging";
    leaf reroute-messsage {
      type empty;
      description
        "Log tunnel rereoute messages";
    }
  }

  grouping CACHE-TIMER {
    description
      "Common node of mpls-te-mib, mpls-frr-mib,
       mpls-p2mp-mib, mpls-te-ext-mib,
       mpls-te-ext-std-mib";
    leaf cache-timer {
      type uint32 {
        range "0..600";
      }
      units "second";
      default "60";
      description
        "Configure the cache time for the mib.";
    }
  }

  grouping PATH-SELECTION-METRIC {
    description
      "Common node of tunnel-attributes,
       tunnel-te-attributes";
    leaf path-selection-metric {
      type Mpls-te-path-selection-metric;
      description
        "Path selection metric to use in path calculation";
    }
  }

  grouping PASSWORD {
    description
      "Common node of peer, pce-attributes";
    leaf password {
      type xr:Proprietary-password;
      description
        "MD5 password";
    }
  }

  grouping BANDWIDTH {
    description
      "Common node of tunnel-attributes,
       tunnel-te-attributes, auto-mesh-attribute,
       auto-backup-attribute, path-option-attribute,
       p2mpte-attribute";
    container bandwidth {
      presence "Indicates a bandwidth node is configured.";
      description
        "Tunnel bandwidth requirement";
      leaf dste-type {
        type Mpls-te-bandwidth-dste;
        mandatory true;
        description
          "DSTE-standard flag";
      }
      leaf class-or-pool-type {
        type uint32 {
          range "0..1";
        }
        mandatory true;
        description
          "Class type for the bandwidth allocation";
      }
      leaf bandwidth {
        type uint32 {
          range "0..4294967295";
        }
        units "kbit/s";
        mandatory true;
        description
          "The value of the bandwidth reserved by this
           tunnel in kbps";
      }
    }
  }

  grouping INTERFACE-BANDWIDTH {
    description
      "Common node of auto-mesh-attribute,
       p2mpte-attribute";
    leaf interface-bandwidth {
      type uint32 {
        range "0..4294967295";
      }
      units "kbit/s";
      description
        "The bandwidth of the interface in kbps";
    }
  }

  grouping FORWARD-CLASS {
    description
      "Common node of tunnel-attributes,
       tunnel-te-attributes, auto-mesh-attribute";
    leaf forward-class {
      type uint32 {
        range "0..7";
      }
      description
        "Forward class value";
    }
  }

  grouping INSUFFICIENT-BW-MESSAGE {
    description
      "Common node of logging, auto-mesh-logging";
    leaf insufficient-bw-message {
      type empty;
      description
        "Log tunnel messages for insufficient bandwidth";
    }
  }

  grouping PATH-SELECTION-DELAY-LIMIT {
    description
      "Common node of tunnel-path-selection,
       att-path-option-path-selection";
    leaf path-selection-delay-limit {
      type uint32 {
        range "1..4294967295";
      }
      description
        "Path selection delay limit (usec) configuration
         for this specific tunnel";
    }
  }

  grouping OOR-METRIC-TE-PENALTY {
    description
      "Common node of oor-green-state, oor-yellow-state,
       oor-red-state, lsp-oor-green-state,
       lsp-oor-yellow-state, lsp-oor-red-state";
    leaf oor-metric-te-penalty {
      type uint32;
      default "0";
      description
        "Penalty applied to the TE metric of a link in
         OOR state";
    }
  }

  grouping DESCRIPTION {
    description
      "Common node of tunnel-te-attributes,
       tunnel-attributes";
    leaf description {
      type string;
      description
        "Describing the named tunnel - div";
    }
  }

  grouping KEYCHAIN {
    description
      "Common node of peer, pce-attributes";
    leaf keychain {
      type string {
        length "1..32";
      }
      description
        "Keychain based authentication";
    }
  }

  grouping FORWARDING-ADJACENCY {
    description
      "Common node of tunnel-attributes,
       tunnel-te-attributes";
    container forwarding-adjacency {
      description
        "Forwarding adjacency announcement to IGP";
      leaf enable {
        type empty;
        description
          "Enable forwarding adjacency";
      }
      leaf include-ipv6 {
        type empty;
        description
          "Specify that the tunnel should be an IPv6
           forwarding adjacency also";
      }
      leaf hold-time {
        type uint32 {
          range "0..20000";
        }
        description
          "Specify the holdtime for the tunnel as
           forwarding adjacency";
      }
    }
  }

  grouping ALL-TRANSIT-LSP-THRESHOLD {
    description
      "Common node of lsp-oor-yellow-state,
       lsp-oor-red-state";
    leaf all-transit-lsp-threshold {
      type uint32;
      description
        "Threshold for all transit LSPs";
    }
  }

  grouping PRIORITY {
    description
      "Common node of tunnel-te-attributes,
       tunnel-attributes, auto-mesh-attribute,
       gmpls-unitunnel-head, auto-backup-attribute,
       p2mpte-attribute";
    container priority {
      presence "Indicates a priority node is configured.";
      description
        "Tunnel Setup and Hold Priorities";
      leaf setup-priority {
        type uint32 {
          range "0..7";
        }
        mandatory true;
        description
          "Setup Priority";
      }
      leaf hold-priority {
        type uint32 {
          range "0..7";
        }
        mandatory true;
        description
          "Hold Priority";
      }
    }
  }

  container mpls-te {
    status deprecated;
    description
      "This model is deprecated and is replaced by
       Cisco-IOS-XR-um-mpls-te-cfg.yang which will
       provide the compatible functionalities.  The root
       of MPLS TE configuration";
    container diff-serv-traffic-engineering {
      description
        "Configure Diff-Serv Traffic-Engineering";
      container classes {
        description
          "Configure Diff-Serv Traffic-Engineering Classes";
        list class {
          key "class-number";
          description
            "DSTE class number";
          leaf class-number {
            type uint32 {
              range "0..7";
            }
            description
              "DS-TE class number";
          }
          leaf class-type {
            when "../unused = 'false'" {
              description
                "../Unused = 'false'";
            }
            type uint32 {
              range "0..1";
            }
            mandatory true;
            description
              "Class type number";
          }
          leaf class-priority {
            when "../unused = 'false'" {
              description
                "../Unused = 'false'";
            }
            type uint32 {
              range "0..7";
            }
            mandatory true;
            description
              "Class-type priority";
          }
          leaf unused {
            type boolean;
            description
              "TRUE to skip classtype and class priority
               provisioning FALSE to provision them";
          }
        }
      }
      leaf bandwidth-constraint-model {
        type Bandwidth-constraint;
        description
          "Diff-Serv Traffic-Engineering Bandwidth
           Constraint Model";
      }
      leaf mode-ietf {
        type Ietf-mode;
        description
          "Diff-Serv Traffic-Engineering IETF mode";
      }
    }
    container named-tunnels {
      description
        "Configure MPLS TE tunnel";
      container tunnels {
        description
          "Configure MPLS TE tunnel";
        list tunnel {
          key "tunnel-name tunnel-type";
          description
            "Configure a MPLS TE tunnel";
          container tunnel-attributes {
            description
              "MPLS tunnel attributes";
            container path-setups {
              description
                "Tunnel path setup table";
              list path-setup {
                key "path-setup-name";
                description
                  "Tunnel path setup";
                container path-computation {
                  presence "Indicates a path-computation node is configured.";
                  description
                    "Path computation method";
                  leaf path-computation-method {
                    type Mpls-te-path-computation-method;
                    mandatory true;
                    description
                      "Path computation method";
                  }
                  leaf explicit-path-name {
                    type string;
                    description
                      "Explicit Path Name";
                  }
                  leaf path-computation-server {
                    type inet:ipv4-address-no-zone;
                    default "0.0.0.0";
                    description
                      "Path Computation Server Address";
                  }
                }
                leaf preference {
                  type uint32 {
                    range "0..255";
                  }
                  description
                    "Path preference level";
                }
                leaf attribute-set {
                  type string;
                  description
                    "Attribute set to be applied to this path";
                }
                leaf s2l-retry-timer {
                  type uint32 {
                    range "1..600";
                  }
                  units "second";
                  description
                    "S2L retry timer timeout value (seconds)";
                }
                leaf path-setup-name {
                  type xr:Cisco-ios-xr-string;
                  description
                    "Path Name";
                }
              }
            }
            container self-ping {
              description
                "Tunnel self ping configuration data";
              leaf enable {
                type boolean;
                description
                  "Enable self-pingThe object must be set
                   before any other self-ping configuration is
                   supplied for the tunnel,and must be the
                   last self-ping configuration object to be
                   removed.";
              }
              leaf max-count {
                type uint32 {
                  range "1..900";
                }
                description
                  "Configure maximum number of self-ping
                   probes";
              }
            }
            container bfd-over-named-lsp {
              description
                "BFD over Named TE LSP";
              uses FAST-DETECT;
              uses MPLS-TE-TUNNEL-CFG-ENABLE;
              uses MULTIPLIER;
              uses MINIMUM-INTERVAL;
            }
            container named-tunnel-path-protection {
              description
                "MPLS named tunnel path protected configs";
              uses MPLS-TE-TUNNEL-CFG-ENABLE-MP;
              uses SRLG-DIVERSE;
            }
            leaf source {
              type inet:ipv4-address-no-zone;
              description
                "Set the source of the tunnel";
            }
            leaf shutdown {
              type empty;
              description
                "shutdown the tunnel";
            }
            uses DELAY-MEASUREMENT;
            uses REOPTIMIZE-TIMER-FREQUENCY;
            uses FORWARD-CLASS;
            uses TUNNEL-PATH-SELECTION;
            uses AUTO-BANDWIDTH;
            uses PRIORITY;
            uses DESTINATION;
            uses RECORD-ROUTE;
            uses AFFINITY-MASK;
            uses FORWARDING-ADJACENCY;
            uses LOGGING;
            uses BANDWIDTH;
            uses AUTOROUTE;
            uses PATH-SELECTION-METRIC;
            uses NEW-STYLE-AFFINITY-TABLE;
            uses SOFT-PREEMPTION;
            uses FAST-REROUTE;
            uses LOAD-SHARE;
            uses DESCRIPTION;
          }
          container tunnel-id {
            presence "Indicates a tunnel-id node is configured.";
            description
              "Set the tunnel ID";
            leaf tunnel-id-type {
              type Mpls-te-tunnel-id;
              mandatory true;
              description
                "Tunnel ID Type";
            }
            leaf tunnel-id {
              type uint32 {
                range "0..65535";
              }
              description
                "Tunnel ID";
            }
          }
          leaf tunnel-name {
            type xr:Cisco-ios-xr-string {
              length "1..64";
            }
            description
              "Tunnel name";
          }
          leaf tunnel-type {
            type Mpls-te-config-tunnel;
            description
              "Tunnel Type";
          }
        }
      }
      leaf enable {
        type empty;
        description
          "Enable Named Tunnels";
      }
    }
    container gmpls-uni {
      description
        "GMPLS-UNI configuration";
      container timers {
        description
          "GMPLS-UNI timer configuration";
        container path-option-timers {
          description
            "GMPLS-UNI path-option timer configuration";
          container holddown {
            description
              "GMPLS-UNI path-option holddown timer
               configuration";
            leaf minimum {
              type uint32 {
                range "5..3600";
              }
              units "second";
              description
                "Minimum holddown (seconds)";
            }
            leaf maximum {
              type uint32 {
                range "5..3600";
              }
              units "second";
              description
                "Maximum holddown (seconds)";
            }
          }
        }
      }
      container controllers {
        description
          "GMPLS-UNI controllers";
        list controller {
          key "controller-name";
          description
            "Configure a GMPLS controller";
          container announce {
            description
              "Announce discovered tunnel properties to
               system";
            leaf srl-gs {
              type empty;
              description
                "Enable announcement of discovered SRLGs";
            }
          }
          container controller-logging {
            description
              "Controller logging";
            leaf discovered-srlg-change-logging {
              type empty;
              description
                "Enable logging of changes to of discovered
                 SRLGs";
            }
          }
          container gmpls-unitunnel-head {
            description
              "GMPLS-UNI tunnel-head properties";
            container path-options {
              description
                "Path-option configuration";
              list path-option {
                key "preference-level";
                description
                  "A Path-option";
                leaf preference-level {
                  type uint32 {
                    range "1..1000";
                  }
                  description
                    "Preference level for this path option";
                }
                leaf path-type {
                  type Mpls-te-path-option;
                  mandatory true;
                  description
                    "The type of the path option";
                }
                leaf path-id {
                  type uint32 {
                    range "1..65535";
                  }
                  default "1";
                  description
                    "The ID of the explicit path associated
                     with this option";
                }
                leaf path-name {
                  type string;
                  description
                    "The name of the explicit path associated
                     with this option";
                }
                leaf xro-type {
                  type Mpls-te-path-option-xro;
                  mandatory true;
                  description
                    "The route-exclusion type";
                }
                leaf xro-attribute-set-name {
                  type Attribute-set-name-length;
                  description
                    "The name of the XRO attribute set to be
                     used for this path-option";
                }
                leaf lockdown {
                  type Mpls-te-path-option-property;
                  mandatory true;
                  description
                    "Path option properties: must be Lockdown";
                }
                leaf verbatim {
                  type Mpls-te-path-option-property;
                  default "none";
                  description
                    "Path option properties: must be verbatim
                     if set";
                }
                leaf signaled-label {
                  type Mpls-te-signaled-label;
                  default "not-set";
                  description
                    "Signaled label type";
                }
                leaf dwdm-channel {
                  type uint32 {
                    range "1..89";
                  }
                  default "1";
                  description
                    "DWDM channel number";
                }
              }
            }
            container recording {
              description
                "Tunnel property recording";
              leaf srlg {
                type empty;
                description
                  "Enable SRLG-recording during signaling";
              }
            }
            container logging {
              description
                "Tunnel event logging";
              uses STATE-MESSAGE;
            }
            leaf enc-type {
              type Mpls-te-lsp-enc;
              description
                "UNI LSP Encoding type";
            }
            leaf tunnel-id {
              type uint32 {
                range "0..65535";
              }
              description
                "GMPLS-UNI head tunnel-id";
            }
            leaf protection-attribute-set {
              type xr:Cisco-ios-xr-string {
                length "1..64";
              }
              description
                "The name of the path-protection profile to
                 be included in signalling messages";
            }
            leaf enable {
              type empty;
              description
                "Set link as a GMPLS tunnel head";
            }
            leaf gpid {
              type uint32 {
                range "0..255";
              }
              description
                "Generalized Payload type";
            }
            leaf destination {
              type inet:ipv4-address-no-zone;
              description
                "Set the destination of the tunnel";
            }
            uses PRIORITY;
            uses RECORD-ROUTE;
            uses SIGNALLED-NAME;
          }
          leaf switching-type {
            type Mpls-te-lsp-switch;
            description
              "Link Switching type";
          }
          leaf mtu {
            type uint32 {
              range "64..65535";
            }
            units "byte";
            description
              "MTU on a controller";
          }
          leaf enable {
            type empty;
            description
              "Enable GMPLS-UNI on the link";
          }
          leaf controller-name {
            type xr:Interface-name;
            description
              "Controller name";
          }
        }
      }
    }
    container global-attributes {
      description
        "Configure MPLS TE global attributes";
      container auto-tunnel {
        description
          "Configure auto-tunnels feature";
        container pcc {
          description
            "Configure auto-tunnel PCC (Path Computation
             Client) feature";
          uses TUNNEL-RANGE;
        }
        container p2p-auto-tunnel {
          description
            "Configure P2P auto-tunnel feature";
          uses TUNNEL-RANGE;
          uses SOFT-PREEMPTION;
        }
        container backup {
          description
            "Configure auto-tunnel backup feature";
          leaf affinity-ignore {
            type empty;
            description
              "Ignore affinity during CSPF for auto backup
               tunnels";
          }
          uses TIMERS;
          uses TUNNEL-RANGE;
        }
        container mesh {
          description
            "Configure auto-tunnel mesh feature";
          container mesh-groups {
            description
              "Configure auto-tunnel mesh group";
            list mesh-group {
              key "mesh-group-id";
              description
                "Auto-mesh group identifier";
              leaf destination-list {
                type Destination-list-name-length;
                description
                  "The name of prefix-list to be applied to
                   this destination-list";
              }
              leaf disable {
                type empty;
                description
                  "Disables mesh group";
              }
              leaf attribute-set {
                type Attribute-set-name-length;
                description
                  "The name of auto-mesh attribute set to be
                   applied to this group";
              }
              leaf one-hop {
                type empty;
                description
                  "Automatically create tunnel to all
                   next-hops";
              }
              leaf mesh-group-id {
                type Mesh-group-id;
                description
                  "Mesh group ID";
              }
            }
          }
          uses TIMERS;
          uses TUNNEL-RANGE;
        }
        container p2mp-auto-tunnel {
          description
            "Configure P2MP auto-tunnel feature";
          uses TUNNEL-RANGE;
          uses SOFT-PREEMPTION;
        }
      }
      container hardware-out-of-resource {
        description
          "Configure HW OOR processing in MPLS-TE";
        container oor-red-state {
          description
            "Configuration for HW OOR Red State";
          uses OOR-NODE-PROTECTION-DISABLE;
          uses OOR-AVAILABLE-BANDWIDTH-PERCENTAGE;
          uses OOR-ACCEPT-LSP-MIN-BANDWIDTH;
          uses OOR-ACCEPT-REOPT-LSP;
          uses OOR-METRIC-TE-PENALTY;
        }
        container oor-yellow-state {
          description
            "Configuration for HW OOR Yellow State";
          uses OOR-NODE-PROTECTION-DISABLE;
          uses OOR-AVAILABLE-BANDWIDTH-PERCENTAGE;
          uses OOR-ACCEPT-LSP-MIN-BANDWIDTH;
          uses OOR-ACCEPT-REOPT-LSP;
          uses OOR-METRIC-TE-PENALTY;
        }
        container oor-green-state {
          description
            "Configuration for HW OOR Green State";
          uses OOR-RECOVERY-DURATION;
          uses OOR-NODE-PROTECTION-DISABLE;
          uses OOR-AVAILABLE-BANDWIDTH-PERCENTAGE;
          uses OOR-ACCEPT-LSP-MIN-BANDWIDTH;
          uses OOR-ACCEPT-REOPT-LSP;
          uses OOR-METRIC-TE-PENALTY;
        }
      }
      container secondary-router-ids {
        description
          "Configure MPLS TE Secondary Router ID";
        list secondary-router-id {
          key "secondary-router-id-value";
          description
            "Secondary Router ID";
          leaf secondary-router-id-value {
            type inet:ipv4-address-no-zone;
            description
              "Secondary TE Router ID";
          }
        }
      }
      container srlg {
        description
          "Configure SRLG values and MPLS-TE properties";
        container names {
          description
            "Configure SRLG identified by names";
          list name {
            key "srlg-name";
            description
              "SRLG name and its MPLS-TE properties";
            container static-srlg-members {
              description
                "Configure static SRLG members list";
              list static-srlg-member {
                key "from-address";
                description
                  "A mapping of the local static SRLG member";
                leaf from-address {
                  type inet:ipv4-address-no-zone;
                  description
                    "From address";
                }
                leaf to-address {
                  type inet:ipv4-address-no-zone;
                  mandatory true;
                  description
                    "To Addres";
                }
              }
            }
            leaf admin-weight {
              type uint32;
              description
                "Administrative weight for the SRLG value";
            }
            leaf srlg-name {
              type xr:Cisco-ios-xr-string {
                length "1..64";
              }
              description
                "SRLG membership name";
            }
          }
        }
        leaf default-admin-weight {
          type uint32;
          default "1";
          description
            "Default Admin weight any SRLG value that does
             not have one";
        }
        leaf enable {
          type empty;
          description
            "Enter SRLG property configuration";
        }
      }
      container queues {
        description
          "Configure MPLS TE route priority";
        list queue {
          key "role";
          description
            "Configure route priority queue value";
          leaf role {
            type Route-priority-role;
            description
              "Route Priority Tunnel Role";
          }
          leaf value {
            type uint32 {
              range "0..12";
            }
            mandatory true;
            description
              "Route priority queue value";
          }
        }
      }
      container backoff-timer {
        description
          "Backoff timer for delaying sending LSP requests
           on the same path after receving path errors";
        leaf initial-interval {
          type uint32 {
            range "0..600";
          }
          units "second";
          default "3";
          description
            "Initial interval in seconds";
        }
        leaf final-interval {
          type uint32 {
            range "0..600";
          }
          units "second";
          default "300";
          description
            "Final interval in seconds";
        }
      }
      container mib {
        description
          "MPLS-TE MIB properties";
        leaf midpoint-lsp-stats-collection-disable {
          type empty;
          description
            "Disables mib midpoint LSP traffic stats
             collection";
        }
      }
      container attribute-set {
        description
          "Attribute AttributeSets";
        container path-option-attributes {
          description
            "Path Option Attribute-Set Table";
          list path-option-attribute {
            key "attribute-set-name";
            description
              "Path Option Attribute";
            container bfd-reverse-path {
              presence "Indicates a bfd-reverse-path node is configured.";
              description
                "Configure BFD reverse path";
              leaf bfd-reverse-path-type {
                type Bfd-reverse-path;
                description
                  "BFD reverse path type";
              }
              leaf binding-label {
                type uint32 {
                  range "0..1048575";
                }
                mandatory true;
                description
                  "BFD reverse path binding label";
              }
            }
            container att-path-option-path-selection {
              description
                "Configure path selection properties";
              leaf path-selection-exclude-list {
                type string {
                  length "1..64";
                }
                description
                  "Path selection exclude list name
                   configuration";
              }
              uses ENABLE;
              uses PATH-SELECTION-DELAY-LIMIT;
              uses INVALIDATION;
              uses PATH-SELECTION-COST-LIMIT;
            }
            leaf attribute-set-name {
              type Attribute-set-name-length;
              description
                "Attribute Set Name";
            }
            uses PCE;
            uses AFFINITY-MASK;
            uses BANDWIDTH;
            uses NEW-STYLE-AFFINITY-TABLE;
          }
        }
        container p2mpte-attributes {
          description
            "P2MP-TE Tunnel AttributeSets Table";
          list p2mpte-attribute {
            key "attribute-set-name";
            description
              "P2MP-TE Tunnel Attribute";
            leaf attribute-set-name {
              type Attribute-set-name-length;
              description
                "Attribute Set Name";
            }
            uses INTERFACE-BANDWIDTH;
            uses PRIORITY;
            uses RECORD-ROUTE;
            uses AFFINITY-MASK;
            uses BANDWIDTH;
            uses PATH-SELECTION;
            uses NEW-STYLE-AFFINITY-TABLE;
            uses FAST-REROUTE;
            uses MPLS-MTE-TUNNEL-CFG-LOGGING;
          }
        }
        container p2p-te-attributes {
          description
            "P2P-TE Tunnel AttributeSets Table";
          list p2p-te-attribute {
            key "attribute-set-name";
            description
              "P2P-TE Tunnel Attribute";
            container path-selection {
              description
                "Configure path selection properties";
              container invalidation {
                description
                  "Deprecated";
                leaf invalidation-timer {
                  type uint32 {
                    range "0..60000";
                  }
                  units "millisecond";
                  description
                    "Path selection invalidation timer value
                     (milliseconds)";
                }
                leaf invalidation-timer-expire-type {
                  type Mpls-te-path-selection-invalidation-timer-expire;
                  default "tunnel-action-tear";
                  description
                    "Path selection invalidation timer expire
                     type";
                }
              }
              leaf path-selection-metric {
                type Mpls-te-path-selection-metric;
                description
                  "Path selection metric to use in path
                   calculation";
              }
              uses ENABLE;
            }
            leaf attribute-set-name {
              type Attribute-set-name-length;
              description
                "Attribute Set Name";
            }
            uses PCE;
            uses AFFINITY-MASK;
            uses LOGGING;
            uses NEW-STYLE-AFFINITY-TABLE;
          }
        }
        container auto-backup-attributes {
          description
            "Auto-backup Tunnel Attribute Table";
          list auto-backup-attribute {
            key "attribute-set-name";
            description
              "Auto-backup Tunnel Attribute";
            container signalled-name {
              description
                "Signalled name";
              leaf name {
                type string;
                description
                  "Signalled name";
              }
              leaf source-type {
                type Mpls-te-sig-name-option;
                description
                  "Source address or name";
              }
              leaf protected-interface-type {
                type Mpls-te-sig-name-option;
                description
                  "Protected-interface address or name";
              }
              leaf mp-address {
                type boolean;
                description
                  "Set if merge-point address is to be
                   appended";
              }
            }
            container auto-backup-logging {
              description
                "Log tunnel LSP messages";
              uses BANDWIDTH-CHANGE-MESSAGE;
              uses REOPTIMIZE-ATTEMPTS-MESSAGE;
              uses STATE-MESSAGE;
              uses REOPTIMIZED-MESSAGE;
            }
            leaf attribute-set-name {
              type Attribute-set-name-length;
              description
                "Attribute Set Name";
            }
            uses PRIORITY;
            uses RECORD-ROUTE;
            uses AFFINITY-MASK;
            uses BANDWIDTH;
            uses PATH-SELECTION;
            uses POLICY-CLASSES;
            uses NEW-STYLE-AFFINITY-TABLE;
            uses SOFT-PREEMPTION;
          }
        }
        container otn-pp-attributes {
          description
            "OTN Path Protection Attributes table";
          list otn-pp-attribute {
            key "attribute-set-name";
            description
              "OTN Path Protection Attribute";
            container revert-schedule-names {
              description
                "Specify APS revert schedule";
              list revert-schedule-name {
                key "schedule-name";
                description
                  "Name Identifier for revert schedule";
                container schedule-duration {
                  presence "Indicates a schedule-duration node is configured.";
                  description
                    "Set duration in format hh:mm";
                  leaf hour {
                    type uint32 {
                      range "0..167";
                    }
                    mandatory true;
                    description
                      "Hour of day";
                  }
                  leaf minutes {
                    type uint32 {
                      range "0..59";
                    }
                    mandatory true;
                    description
                      "Minute of the hour";
                  }
                }
                container schedule-date {
                  presence "Indicates a schedule-date node is configured.";
                  description
                    "Set date in format hh:mm MMM DD YYYY";
                  leaf hour {
                    type uint32 {
                      range "0..23";
                    }
                    mandatory true;
                    description
                      "Hour of day";
                  }
                  leaf minutes {
                    type uint32 {
                      range "0..59";
                    }
                    mandatory true;
                    description
                      "Minute of the hour";
                  }
                  leaf month {
                    type uint32 {
                      range "0..11";
                    }
                    mandatory true;
                    description
                      "Month of the year";
                  }
                  leaf day {
                    type uint32 {
                      range "1..31";
                    }
                    mandatory true;
                    description
                      "Day of the month";
                  }
                  leaf year {
                    type uint32 {
                      range "2015..2035";
                    }
                    mandatory true;
                    description
                      "Year";
                  }
                }
                leaf revert-schedule-max-tries {
                  type uint32 {
                    range "1..2016";
                  }
                  description
                    "Revert Schedule Max tries";
                }
                leaf sch-name-enable {
                  type empty;
                  description
                    "Schedule name enable object";
                }
                leaf revert-schedule-frequency {
                  type uint32 {
                    range "1..3";
                  }
                  description
                    "Frequency set as Once, Daily, Weekly";
                }
                leaf schedule-name {
                  type xr:Cisco-ios-xr-string {
                    length "1..254";
                  }
                  description
                    "Enter 64 characters for revert schedule
                     name";
                }
              }
            }
            container sub-network-connection-mode {
              description
                "Sub-network connection mode";
              leaf connection-mode {
                type Mpls-te-otn-snc-mode;
                description
                  "The sub-network connection mode";
              }
              leaf connection-monitoring-mode {
                type uint32 {
                  range "1..6";
                }
                description
                  "Tandem Connection Monitoring ID for the
                   interface";
              }
            }
            container timers {
              description
                "Timers";
              leaf aps-wait-to-restore {
                type uint32 {
                  range "0..720";
                }
                units "second";
                description
                  "G.709 OTN path protection wait to restore
                   timer in seconds";
              }
              leaf aps-hold-off {
                type uint32 {
                  range "100..10000";
                }
                units "millisecond";
                description
                  "G.709 OTN path protection hold-off timer in
                   milliseconds";
              }
            }
            leaf aps-protection-mode {
              type Mpls-te-otn-aps-protection-mode;
              description
                "The APS protecion mode";
            }
            leaf aps-restoration-style {
              type Mpls-te-otn-aps-restoration-style;
              description
                "The APS restoration style";
            }
            leaf aps-protection-type {
              type Mpls-te-otn-aps-protection;
              description
                "The APS protecion type";
            }
            leaf attribute-set-name {
              type Attribute-set-name-length;
              description
                "Attribute Set Name";
            }
            uses PATH-SELECTION;
          }
        }
        container uni-p-attributes {
          description
            "UNI Protection Attributes table";
          list uni-p-attribute {
            key "attribute-set-name";
            description
              "UNI Protection Attribute";
            leaf seg-flag {
              type Mpls-te-uni-lsp-seg-flag;
              description
                "The Seg flag value for uni-protection";
            }
            leaf lsp-flag {
              type Mpls-te-uni-lsp-seg-flag;
              description
                "The Lsp flag value for uni-protection";
            }
            leaf required-bit {
              type Mpls-te-uni-required-bit;
              description
                "Set Required bit for uni-protection";
            }
            leaf in-place-bit {
              type Mpls-te-uni-in-place-bit;
              description
                "Set in place bit for uni-protection";
            }
            leaf attribute-set-name {
              type Attribute-set-name-length;
              description
                "Attribute Set Name";
            }
            uses PATH-SELECTION;
          }
        }
        container auto-mesh-attributes {
          description
            "Auto-mesh Tunnel AttributeSets Table";
          list auto-mesh-attribute {
            key "attribute-set-name";
            description
              "Auto-mesh Tunnel Attribute";
            container auto-mesh-logging {
              description
                "Log tunnel LSP messages";
              uses BANDWIDTH-CHANGE-MESSAGE;
              uses REOPTIMIZE-ATTEMPTS-MESSAGE;
              uses REROUTE-MESSSAGE;
              uses STATE-MESSAGE;
              uses PATH-ERROR-MESSAGE;
              uses INSUFFICIENT-BW-MESSAGE;
              uses REOPTIMIZED-MESSAGE;
              uses PCALC-FAILURE-MESSAGE;
            }
            leaf autoroute-announce {
              type empty;
              description
                "Enable autoroute announce";
            }
            leaf attribute-set-name {
              type Attribute-set-name-length;
              description
                "Attribute Set Name";
            }
            uses INTERFACE-BANDWIDTH;
            uses FORWARD-CLASS;
            uses PRIORITY;
            uses RECORD-ROUTE;
            uses AFFINITY-MASK;
            uses BANDWIDTH;
            uses PATH-SELECTION;
            uses COLLECTION-ONLY;
            uses POLICY-CLASSES;
            uses NEW-STYLE-AFFINITY-TABLE;
            uses SOFT-PREEMPTION;
            uses FAST-REROUTE;
            uses LOAD-SHARE;
          }
        }
        container xro-attributes {
          description
            "XRO Tunnel Attributes table";
          list xro-attribute {
            key "attribute-set-name";
            description
              "XRO Attribute";
            container path-diversity {
              description
                "Path diversity";
              container srlgs {
                description
                  "SRLG-based path diversity";
                list srlg {
                  key "srlg";
                  description
                    "SRLG-based path-diversity element";
                  leaf srlg {
                    type uint32 {
                      range "0..4294967295";
                    }
                    description
                      "SRLG";
                  }
                  leaf conformance {
                    type Mpls-te-path-diversity-conformance;
                    mandatory true;
                    description
                      "The diversity conformance requirements";
                  }
                }
              }
              container lsp {
                description
                  "LSP-based path diversity";
                container fecs {
                  description
                    "FEC LSP-based path diversity";
                  list fec {
                    key "source destination tunnel-id extended-tunnel-id lsp-id";
                    description
                      "LSP-based path-diversity, referenced by
                       FEC";
                    leaf source {
                      type inet:ipv4-address-no-zone;
                      description
                        "Source address";
                    }
                    leaf destination {
                      type inet:ipv4-address-no-zone;
                      description
                        "Destination address";
                    }
                    leaf tunnel-id {
                      type uint32 {
                        range "0..65535";
                      }
                      description
                        "Tunnel id";
                    }
                    leaf extended-tunnel-id {
                      type inet:ipv4-address-no-zone;
                      description
                        "Extended tunnel-id";
                    }
                    leaf lsp-id {
                      type uint32 {
                        range "0..65535";
                      }
                      description
                        "LSP id";
                    }
                    leaf conformance {
                      type Mpls-te-path-diversity-conformance;
                      mandatory true;
                      description
                        "The diversity conformance requirements";
                    }
                  }
                }
              }
            }
            leaf attribute-set-name {
              type Attribute-set-name-length;
              description
                "Attribute Set Name";
            }
            uses PATH-SELECTION;
          }
        }
      }
      container bfd-over-lsp {
        description
          "BFD over MPLS TE Global Configurations";
        container tail {
          description
            "BFD over LSP Tail Global Configurations";
          leaf multiplier {
            type uint32 {
              range "3..10";
            }
            description
              "Specify BFD over LSP tail multiplier";
          }
          leaf minimum-interval {
            type uint32 {
              range "3..30000";
            }
            description
              "Specify BFD over LSP tail minimum interval";
          }
        }
        container head {
          description
            "BFD over LSP Head Global Configurations";
          leaf reopt-timeout {
            type uint32 {
              range "120..4294967295";
            }
            description
              "BFD session down reopt timeout";
          }
          leaf down-action {
            type Mpls-te-bfd-session-down-action;
            description
              "Specify BFD session down action";
          }
        }
      }
      container bandwidth-accounting {
        description
          "Bandwidth accounting configuration data";
        container application {
          description
            "Bandwidth accounting application configuration
             data";
          leaf application-enforced {
            type boolean;
            default "false";
            description
              "This object enables the application";
          }
          leaf application-interval {
            type uint32 {
              range "30..1800";
            }
            units "second";
            default "180";
            description
              "This object sets the application interval in
               seconds for bandwidth accounting. Default to
               180 seconds.";
          }
        }
        container account-flooding-threshold {
          description
            "This object sets the flooding threshold as
             percentage of total link bandwidth for
             bandwidth accounting. Default to 10%, 10%";
          leaf up-threshold {
            type Mpls-percent-range;
            units "percentage";
            default "10";
            description
              "Upward flooding Threshold in percentages of
               total bandwidth";
          }
          leaf down-threshold {
            type Mpls-percent-range;
            units "percentage";
            default "10";
            description
              "Downward flooding Threshold in percentages of
               total bandwidth";
          }
        }
        leaf sampling-interval {
          type uint32 {
            range "10..600";
          }
          units "second";
          default "60";
          description
            "This object sets the sampling interval in
             seconds for bandwidth accounting. Default to
             60 seconds.";
        }
        leaf account-flooding-sr-traffic-pct {
          type Mpls-percent-range;
          units "percentage";
          description
            "This object sets the flooding threshold as
             percentage of total Segment Routing traffic
             for bandwidth accounting. ";
        }
        leaf adjustment-factor {
          type uint32 {
            range "0..200";
          }
          units "percentage";
          default "100";
          description
            "This object sets the percentage adjustment
             factor for the non RSVP-TE bandwidth
             accounting.  Default is 100%.";
        }
        leaf collection-type-rsvp-te {
          type boolean;
          default "false";
          description
            "This object enables the bandwidth accounting
             RSVP-TE sample collection.";
        }
        leaf enable {
          type empty;
          description
            "This object controls whether BW accounting is
             enabled. This object must be set before
             setting any other objects  under the
             BandwidthAccounting class.";
        }
      }
      container pce-attributes {
        description
          "Configuration MPLS TE PCE attributes";
        container pce-stateful {
          description
            "PCE Stateful";
          container stateful-timers {
            description
              "Configure Stateful PCE (Path Computation
               Element) timers";
            leaf redelegation-timeout {
              type uint32 {
                range "0..1576800000";
              }
              units "second";
              default "180";
              description
                "Timer for static tunnel redelegation in
                 seconds, default is 180 seconds";
            }
            leaf state-timeout {
              type uint32 {
                range "0..3600";
              }
              units "second";
              default "180";
              description
                "State timeout for LSPs without delegation in
                 seconds, zero means immediate removal,
                 default is 180 seconds";
            }
            leaf delegation-delay {
              type uint32 {
                range "20..1800";
              }
              units "second";
              default "60";
              description
                "Time duration before LSP is delegated to PCE
                 in seconds, default is 60 seconds. Caution
                 :LSP can be removed if value is smaller than
                 request timeout";
            }
          }
          container redundancy {
            description
              "Configure PCE (Path Computation Element)
               redundancy";
            leaf pcc-centric {
              type empty;
              description
                "Enable PCC (Path Computation Client) centric
                 model";
            }
          }
          leaf fast-repair {
            type empty;
            description
              "Enable reoptimization by PCC after path
               failures";
          }
          leaf instantiation {
            type empty;
            description
              "PCE stateful instantiation capability";
          }
          leaf cisco-extension {
            type empty;
            description
              "Enable processing of PCEP Cisco extension";
          }
          leaf autobw-object-type {
            type uint32 {
              range "0..255";
            }
            default "5";
            description
              "BW Object type for auto-bw feature";
          }
          leaf delegation {
            type empty;
            description
              "Delegate all statically configured tunnels";
          }
          leaf autoroute-announce {
            type empty;
            description
              "Enable autoroute announce for PCE
               instantiated tunnels";
          }
          leaf report {
            type empty;
            description
              "Report all statically configured tunnels";
          }
          leaf fast-reoptimization {
            type empty;
            description
              "Enable head-end to react to path failures";
          }
          leaf enable {
            type empty;
            description
              "PCE stateful capability";
          }
        }
        container peers {
          description
            "Configure PCE peers";
          list peer {
            key "pce-peer-address";
            description
              "PCE peer";
            leaf pce-peer-address {
              type inet:ipv4-address-no-zone;
              description
                "Address of PCE Peer";
            }
            uses PASSWORD;
            uses KEYCHAIN;
            uses PRECEDENCE;
          }
        }
        container logging {
          description
            "Configure PCE (Path Computation Element)
             logging feature";
          container events {
            description
              "Configure logging events";
            leaf peer-status {
              type empty;
              description
                "Peer status changes logging";
            }
          }
        }
        leaf request-timeout {
          type uint32 {
            range "5..100";
          }
          units "second";
          default "10";
          description
            "Request timeout value in seconds";
        }
        leaf reoptimize-period {
          type uint32 {
            range "60..604800";
          }
          units "second";
          default "60";
          description
            "PCE reoptimization period for PCE-based paths";
        }
        leaf address {
          type inet:ipv4-address-no-zone;
          description
            "Address of this PCE";
        }
        leaf deadtimer {
          type uint32 {
            range "0..255";
          }
          units "second";
          default "120";
          description
            "Deadtimer interval in seconds";
        }
        leaf keepalive {
          type uint32 {
            range "0..255";
          }
          units "second";
          default "30";
          description
            "Keepalive interval in seconds";
        }
        leaf keepalive-tolerance {
          type uint32 {
            range "0..255";
          }
          units "second";
          default "10";
          description
            "Keepalive interval tolerance in seconds";
        }
        leaf peer-source-addr {
          type inet:ipv4-address-no-zone;
          description
            "PCE Peer Source Address";
        }
        leaf speaker-entity-id {
          type string {
            length "1..256";
          }
          description
            "PCE speaker entity identifier";
        }
        leaf segment-routing {
          type empty;
          description
            "Always set to true";
        }
        uses PASSWORD;
        uses KEYCHAIN;
        uses PRECEDENCE;
      }
      container lsp-out-of-resource {
        description
          "Configure LSP OOR attributes in MPLS-TE";
        container lsp-oor-red-state {
          description
            "Configuration for LSP OOR Red/Major State";
          uses OOR-AVAILABLE-BANDWIDTH-PERCENTAGE;
          uses OOR-ACCEPT-LSP-MIN-BANDWIDTH;
          uses ALL-TRANSIT-LSP-THRESHOLD;
          uses UNPROTECTED-TRANSIT-LSP-THRESHOLD;
          uses OOR-ACCEPT-REOPT-LSP;
          uses OOR-METRIC-TE-PENALTY;
        }
        container lsp-oor-green-state {
          description
            "Configuration for LSP OOR Green/Normal State";
          uses OOR-RECOVERY-DURATION;
          uses OOR-AVAILABLE-BANDWIDTH-PERCENTAGE;
          uses OOR-ACCEPT-LSP-MIN-BANDWIDTH;
          uses OOR-ACCEPT-REOPT-LSP;
          uses OOR-METRIC-TE-PENALTY;
        }
        container lsp-oor-yellow-state {
          description
            "Configuration for LSP OOR Yellow/Minor State";
          uses OOR-AVAILABLE-BANDWIDTH-PERCENTAGE;
          uses OOR-ACCEPT-LSP-MIN-BANDWIDTH;
          uses ALL-TRANSIT-LSP-THRESHOLD;
          uses UNPROTECTED-TRANSIT-LSP-THRESHOLD;
          uses OOR-ACCEPT-REOPT-LSP;
          uses OOR-METRIC-TE-PENALTY;
        }
      }
      container soft-preemption {
        description
          "Soft preemption configuration data";
        leaf timeout {
          type uint32 {
            range "1..300";
          }
          units "second";
          default "60";
          description
            "This object sets the timeout in seconds before
             hard preemption is triggered.";
        }
        leaf frr-rewrite {
          type empty;
          description
            "This object controls whether FRR rewrite
             during soft preemption is enabled.";
        }
        leaf enable {
          type boolean;
          description
            "This object controls whether soft preemption
             is enabled. This object must be set before
             setting any other objects under the
             SoftPreemption class.";
        }
      }
      container fast-reroute {
        description
          "Configure fast reroute attributes";
        container timers {
          description
            "Configure fast reroute timers";
          leaf hold-backup {
            type uint32 {
              range "0..604800";
            }
            units "second";
            description
              "Seconds before backup declared UP (0 disables
               hold-timer)";
          }
          leaf promotion {
            type uint32 {
              range "0..604800";
            }
            units "second";
            description
              "The value of the promotion timer in seconds";
          }
        }
      }
      container path-selection {
        description
          "Path selection configuration";
        container loose-metrics {
          description
            "Path selection Loose ERO Metric Class
             configuration";
          list loose-metric {
            key "class-type";
            description
              "Path selection Loose ERO Metric configuration";
            leaf class-type {
              type uint32 {
                range "0..7";
              }
              description
                "Path Selection class Type";
            }
            leaf metric-type {
              type Mpls-te-path-selection-metric;
              mandatory true;
              description
                "Metric to use for ERO Expansion";
            }
          }
        }
        container invalidation {
          description
            "Deprecated";
          leaf path-invalidation-timeout {
            type uint32 {
              range "0..60000";
            }
            description
              "Path Invalidation Timeout";
          }
          leaf path-invalidation-action {
            type Path-invalidation-action;
            description
              "Path Invalidation Action";
          }
        }
        container ignore-overload-role {
          description
            "Path selection to ignore overload node during
             CSPF";
          leaf head {
            type boolean;
            description
              "Set if the OL-bit is to be applied to tunnel
               heads";
          }
          leaf mid {
            type boolean;
            description
              "Set if the OL-bit is to be applied to tunnel
               midpoints";
          }
          leaf tail {
            type boolean;
            description
              "Set if the OL-bit is to be applied to tunnel
               tails";
          }
        }
        container loose-affinities {
          description
            "Path selection Loose ERO Affinity Class
             configuration";
          list loose-affinity {
            key "class-type";
            description
              "Path selection Loose ERO Affinity
               configuration";
            leaf class-type {
              type uint32 {
                range "0..7";
              }
              description
                "Path Selection class Type";
            }
            leaf affinity {
              type xr:Hex-integer;
              description
                "Affinity flags";
            }
            leaf mask {
              type xr:Hex-integer;
              description
                "Affinity mask";
            }
          }
        }
        leaf cost-limit {
          type uint32 {
            range "1..4294967295";
          }
          description
            "Path selection cost limit configuration for
             all tunnels";
        }
        leaf tiebreaker {
          type Mpls-te-path-selection-tiebreaker;
          description
            "CSPF tiebreaker to use in path calculation";
        }
        leaf metric {
          type Mpls-te-path-selection-metric;
          description
            "Metric to use in path calculation";
        }
        leaf loose-domain-match {
          type boolean;
          description
            "Use only the IGP instance of the incoming
             interface";
        }
        leaf delay-limit {
          type uint32 {
            range "1..4294967295";
          }
          description
            "Path selection delay limit configuration for
             p2p tunnels (usec)";
        }
      }
      container affinity-mappings {
        description
          "Affinity Mapping Table configuration";
        list affinity-mapping {
          key "affinity-name";
          description
            "Affinity Mapping configuration";
          leaf affinity-name {
            type xr:Cisco-ios-xr-string {
              length "1..32";
            }
            description
              "Affinity Name";
          }
          leaf value-type {
            type Mpls-te-affinity-value;
            description
              "Affinity value type";
          }
          leaf value {
            type xr:Hex-integer;
            description
              "Affinity Value in Hex number or by Bit
               position";
          }
        }
      }
      leaf log-nsr-status {
        type empty;
        description
          "Log NSR status messages";
      }
      leaf log-issu-status {
        type empty;
        description
          "Log ISSU status messages";
      }
      leaf reoptimize-link-up {
        type empty;
        description
          "Enable reoptimization based on link-up events";
      }
      leaf reoptimize-delay-cleanup-timer {
        type uint32 {
          range "0..300";
        }
        units "second";
        description
          "Reoptimization Delay Cleanup Value (seconds)";
      }
      leaf disable-reoptimize-affinity-failure {
        type empty;
        description
          "Disable reoptimization after affinity failures";
      }
      leaf maximum-tunnels {
        type uint32 {
          range "1..65536";
        }
        default "4096";
        description
          "The maximum number of tunnel heads that will be
           allowed.";
      }
      leaf link-holddown-timer {
        type uint32 {
          range "0..300";
        }
        units "second";
        default "10";
        description
          "Holddown time for links which had Path Errors
           in seconds";
      }
      leaf fault-oam {
        type empty;
        description
          "Enable Fault-OAM functionality for
           bidirectional tunnels";
      }
      leaf path-retry-timeout {
        type uint32 {
          range "30..600";
        }
        units "second";
        description
          "Path message timeout in seconds before a path
           retry is attempted";
      }
      leaf enable-unequal-load-balancing {
        type empty;
        description
          "Enable unequal load-balancing over tunnels to
           the same destination";
      }
      leaf log-tail {
        type empty;
        description
          "Log all tail tunnel events";
      }
      leaf reoptimize-delay-after-frr-timer {
        type uint32 {
          range "0..120";
        }
        units "second";
        description
          "Reoptimization Delay After FRR Value (seconds)";
      }
      leaf auto-bandwidth-collect-frequency {
        type uint32 {
          range "1..10080";
        }
        units "minute";
        default "5";
        description
          "Auto-bandwidth global collection frequency in
           minutes";
      }
      leaf reopt-delay-path-protect-switchover-timer {
        type uint32 {
          range "0..604800";
        }
        units "second";
        default "180";
        description
          "Seconds between path protect switchover and
           tunnel re-optimization. Set to 0 to disable";
      }
      leaf log-all {
        type empty;
        description
          "Always set to true";
      }
      leaf loose-path-retry-period {
        type uint32 {
          range "30..600";
        }
        default "120";
        description
          "Signalling retry for tunnels terminating
           outside the headend area";
      }
      leaf reoptimize-load-balancing {
        type empty;
        description
          "Load balance bandwidth during reoptimization";
      }
      leaf log-head {
        type empty;
        description
          "Log all head tunnel events";
      }
      leaf path-selection-ignore-overload {
        type empty;
        description
          "Deprecated - do not use";
      }
      leaf graceful-preemption-on-bandwidth-reduction {
        type empty;
        description
          "Enable graceful preemption when there is a
           bandwidth reduction";
      }
      leaf pce-reoptimize-period {
        type uint32 {
          range "60..604800";
        }
        units "second";
        default "60";
        description
          "PCE reoptimization period for PCE-based paths";
      }
      leaf advertise-explicit-nulls {
        type empty;
        description
          "Enable explicit-null advertising to PHOP";
      }
      leaf reoptimize-delay-install-timer {
        type uint32 {
          range "0..3600";
        }
        units "second";
        description
          "Reoptimization Delay Install Value (seconds)";
      }
      leaf reoptimize-delay-after-affinity-failure-timer {
        type uint32 {
          range "1..604800";
        }
        units "second";
        description
          "Delay reoptimizing current LSP after affinity
           failures";
      }
      leaf log-frr-protection {
        type Mpls-te-log-frr-protection;
        description
          "Log FRR Protection messages";
      }
      leaf reoptimize-timer-frequency {
        type uint32 {
          range "0..604800";
        }
        units "second";
        default "3600";
        description
          "Reoptimize timers period in seconds";
      }
      leaf log-mid {
        type empty;
        description
          "Log all mid tunnel events";
      }
      leaf pce-request-timeout {
        type uint32 {
          range "5..100";
        }
        units "second";
        default "10";
        description
          "Request timeout value in seconds";
      }
      leaf log-preemption {
        type empty;
        description
          "Log tunnel preemption messages";
      }
    }
    container transport-profile {
      description
        "MPLS transport profile configuration data";
      container fault {
        description
          "Fault management";
        container protection-trigger {
          description
            "OAM events that trigger protection switching";
          container ldi {
            description
              "Protection switching due to LDI event";
            leaf disable {
              type empty;
              description
                "Disable protection switching due to LDI
                 event";
            }
          }
          container lkr {
            description
              "Protection switching due to LKR event";
            leaf disable {
              type empty;
              description
                "Disable protection switching due to LKR
                 event";
            }
          }
          leaf ais {
            type empty;
            description
              "Enable protection switching due to AIS event";
          }
        }
        leaf wait-to-restore-interval {
          type uint32 {
            range "0..2147483647";
          }
          units "second";
          default "0";
          description
            "Waiting time before restoring working LSP";
        }
        leaf refresh-interval {
          type uint32 {
            range "1..20";
          }
          units "second";
          default "20";
          description
            "Periodic refresh interval for fault OAM
             messages";
        }
      }
      container alarm {
        description
          "Alarm management";
        container suppress-event {
          description
            "Suppress all tunnel/LSP alarms";
          leaf disable {
            type empty;
            description
              "Disable alarm suppression";
          }
        }
        leaf soak-time {
          type uint32 {
            range "0..10";
          }
          units "second";
          default "3";
          description
            "Duration of soaking alarms";
        }
        leaf enable-alarm {
          type empty;
          description
            "Enable Transport Profile Alarm";
        }
      }
      container bfd {
        description
          "Configure BFD parameters";
        container min-interval-standby {
          description
            "Hello interval for standby transport profile
             LSPs, either in milli-seconds or in
             micro-seconds";
          leaf interval-standby-ms {
            type uint32 {
              range "3..5000";
            }
            units "millisecond";
            description
              "Hello interval in milli-seconds";
          }
          leaf interval-standby-us {
            type uint32 {
              range "3000..5000000";
            }
            units "microsecond";
            description
              "Hello interval in micro-seconds";
          }
        }
        container min-interval {
          description
            "Hello interval, either in milli-seconds or in
             micro-seconds";
          leaf interval-ms {
            type uint32 {
              range "3..5000";
            }
            units "millisecond";
            description
              "Hello interval in milli-seconds";
          }
          leaf interval-us {
            type uint32 {
              range "3000..5000000";
            }
            units "microsecond";
            description
              "Hello interval in micro-seconds";
          }
        }
        leaf detection-multiplier-standby {
          type uint32 {
            range "2..10";
          }
          description
            "Detect multiplier for standby transport
             profile LSP";
        }
        leaf detection-multiplier {
          type uint32 {
            range "2..10";
          }
          description
            "Detect multiplier";
        }
      }
      container midpoints {
        description
          "MPLS-TP tunnel mid-point table";
        list midpoint {
          key "midpoint-name";
          description
            "Transport profile mid-point identifier";
          container source {
            presence "Indicates a source node is configured.";
            description
              "Node identifier, tunnel identifier and
               optional global identifier of the source of
               the LSP";
            leaf node-id {
              type inet:ipv4-address-no-zone;
              description
                "Node identifier in IPv4 address format";
            }
            leaf tunnel-id {
              type uint32 {
                range "0..65535";
              }
              mandatory true;
              description
                "Tunnel identifier in numeric value";
            }
            leaf global-id {
              type uint32 {
                range "1..65535";
              }
              description
                "Global identifier in numeric value";
            }
          }
          container destination {
            presence "Indicates a destination node is configured.";
            description
              "Node identifier, tunnel identifier and
               optional global identifier of the destination
               of the LSP";
            leaf node-id {
              type inet:ipv4-address-no-zone;
              description
                "Node identifier in IPv4 address format";
            }
            leaf tunnel-id {
              type uint32 {
                range "0..65535";
              }
              mandatory true;
              description
                "Tunnel identifier in numeric value";
            }
            leaf global-id {
              type uint32 {
                range "1..65535";
              }
              description
                "Global identifier in numeric value";
            }
          }
          container forward-lsp {
            description
              "Forward transport profile LSP";
            container forward-io-map {
              presence "Indicates a forward-io-map node is configured.";
              description
                "Label cross-connect of forward transport
                 profile LSP";
              leaf in-label {
                type uint32 {
                  range "16..4015";
                }
                description
                  "MPLS label";
              }
              leaf out-label {
                type uint32 {
                  range "16..1048575";
                }
                mandatory true;
                description
                  "Outgoing MPLS label";
              }
              leaf out-link {
                type uint32 {
                  range "1..65535";
                }
                mandatory true;
                description
                  "Transport profile identifier of outgoing
                   link";
              }
            }
            leaf forward-bandwidth {
              type uint32 {
                range "0..4294967295";
              }
              units "kbit/s";
              description
                "Bandwidth of forward transport profile LSP";
            }
          }
          container reverse-lsp {
            description
              "none";
            container reverse-io-map {
              presence "Indicates a reverse-io-map node is configured.";
              description
                "Label cross-connect of reverse transport
                 profile LSP";
              leaf in-label {
                type uint32 {
                  range "16..4015";
                }
                description
                  "MPLS label";
              }
              leaf out-label {
                type uint32 {
                  range "16..1048575";
                }
                mandatory true;
                description
                  "Outgoing MPLS label";
              }
              leaf out-link {
                type uint32 {
                  range "1..65535";
                }
                mandatory true;
                description
                  "Transport profile identifier of outgoing
                   link";
              }
            }
            leaf reverse-bandwidth {
              type uint32 {
                range "0..4294967295";
              }
              units "kbit/s";
              description
                "Bandwidth of reverse transport profile LSP";
            }
          }
          leaf tunnel-name {
            type string;
            description
              "Tunnel Name";
          }
          leaf lsp-protect {
            type empty;
            description
              "Enable LSP protection";
          }
          leaf lsp-id {
            type uint32 {
              range "0..65535";
            }
            description
              "Numeric identifier";
          }
          leaf midpoint-name {
            type xr:Cisco-ios-xr-string {
              length "1..64";
            }
            description
              "Name of mid-point";
          }
        }
      }
      leaf global-id {
        type uint32 {
          range "1..65535";
        }
        description
          "Transport profile global identifier";
      }
      leaf node-id {
        type inet:ipv4-address-no-zone;
        description
          "Node identifier in IPv4 address format";
      }
    }
    container interfaces {
      description
        "Configure MPLS TE interfaces";
      list interface {
        key "interface-name";
        description
          "Configure an MPLS TE interface";
        container transport-profile-link {
          description
            "MPLS transport profile capable link";
          container links {
            description
              "Transport profile link table";
            list link {
              key "link-id";
              description
                "Transport profile link";
              leaf link-id {
                type uint32 {
                  range "1..65535";
                }
                description
                  "Numeric link identifier";
              }
              leaf next-hop-type {
                type Link-next-hop;
                mandatory true;
                description
                  "Next hop type";
              }
              leaf next-hop-address {
                when "../next-hop-type = 'ipv4-address'" {
                  description
                    "../NextHopType = IPV4Address";
                }
                type inet:ipv4-address-no-zone;
                description
                  "Next-hop address in IPv4 format";
              }
            }
          }
        }
        container lcac {
          description
            "LCAC specific MPLS interface configuration";
          container switchings {
            description
              "Set the te-link switching attributes";
            list switching {
              key "switching-id";
              description
                "The te-link switching attributes";
              leaf encoding {
                type Mpls-te-switching-encoding;
                description
                  "Set the local encoding type";
              }
              leaf capability {
                type Mpls-te-switching-cap;
                description
                  "Set the local switching capability";
              }
              leaf switching-id {
                type Mpls-te-switching-index;
                description
                  "Switching index";
              }
            }
          }
          container flood-area {
            description
              "Set the IGP instance into which this
               interface is to be flooded (GMPLS only)";
            leaf igp-type {
              type Mpls-lcac-flooding-igp;
              description
                "IGP type";
            }
            leaf process-name {
              type xr:Cisco-ios-xr-string {
                length "1..32";
              }
              description
                "Process name";
            }
            leaf area-id {
              type uint32;
              description
                "Area ID";
            }
          }
          container attribute-name-xr {
            description
              "Set the interface attribute names";
            leaf-list attribute-name {
              type string;
              max-elements 32;
              description
                "Array of Attribute Names";
            }
          }
          container attribute-names {
            description
              "Attribute name table";
            list attribute-name {
              key "affinity-index";
              description
                "Set the interface attribute names";
              leaf affinity-index {
                type uint32 {
                  range "1..9";
                }
                description
                  "Specify the entry index";
              }
              leaf-list value {
                type string;
                min-elements 1;
                max-elements 32;
                description
                  "Array of Attribute Names";
              }
            }
          }
          container srlgs {
            description
              "Configure SRLG membership for the interface";
            list srlg {
              key "srlg-number";
              description
                "SRLG membership number";
              leaf srlg-number {
                type uint32 {
                  range "0..4294967295";
                }
                description
                  "SRLG membership number";
              }
            }
          }
          container up-thresholds {
            description
              "Set thresholds for increased resource
               availability in %";
            leaf-list up-threshold {
              type Mpls-lcac-flooding-threshold-percent-range;
              units "percentage";
              max-elements 14;
              description
                "Array of up threshold percentage";
            }
          }
          container down-thresholds {
            description
              "Set thresholds for decreased resource
               availability in %";
            leaf-list down-threshold {
              type Mpls-lcac-flooding-threshold-percent-range;
              units "percentage";
              max-elements 14;
              description
                "Array of down threshold percentage";
            }
          }
          leaf bfd {
            type empty;
            description
              "Enable use of Bidirectional Forwarding
               Detection";
          }
          leaf fault-oam-lockout {
            type empty;
            description
              "Lockout protection on the interface for Flex
               LSP";
          }
          leaf attribute-flags {
            type xr:Hex-integer;
            description
              "Set user defined interface attribute flags";
          }
          leaf enable {
            type empty;
            description
              "Enable MPLS-TE on the link";
          }
          leaf admin-weight {
            type uint32 {
              range "0..4294967295";
            }
            description
              "Set administrative weight for the interface";
          }
        }
        container global-attributes {
          description
            "MPLS TE global interface configuration";
          container backup-tunnels {
            description
              "Configure MPLS TE backup tunnels for this
               interface";
            list backup-tunnel {
              key "tunnel-name";
              description
                "Tunnel name";
              leaf tunnel-name {
                type xr:Cisco-ios-xr-string {
                  length "1..64";
                }
                description
                  "Tunnel name";
              }
            }
          }
          container auto-tunnel {
            description
              "Auto tunnel configuration";
            container backup {
              description
                "Auto tunnel backup configuration";
              container bandwidth-protection {
                description
                  "Auto-tunnel bandwidth protection";
                leaf maximum-aggregate {
                  type uint32 {
                    range "1..4294967295";
                  }
                  units "kbit/s";
                  description
                    "Set maximum aggregated amount of bandwidth
                     to protect";
                }
              }
              container exclude {
                description
                  "Auto-tunnel backup exclusion criteria";
                leaf srlg-mode {
                  type Mpls-tesrlg-exclude;
                  description
                    "Set exclude SRLG mode for auto-tunnel
                     backup on this TE link";
                }
              }
              leaf enable {
                type empty;
                description
                  "Enable auto-tunnel backup on this TE link";
              }
              leaf reoptimize {
                type uint32 {
                  range "0..65535";
                }
                units "second";
                description
                  "Auto tunnel backup reoptimize timer period
                   in seconds";
              }
              leaf attribute-set {
                type Attribute-set-name-length;
                description
                  "The name of attribute set to be applied to
                   this auto backup lsp";
              }
              leaf next-hop-only {
                type empty;
                description
                  "Enable NHOP-only mode for auto-tunnel
                   backup on this TE link";
              }
            }
          }
          container backup-paths {
            description
              "Configure MPLS TE backup tunnels for this
               interface";
            list backup-path {
              key "tunnel-number";
              description
                "Tunnel interface number";
              leaf tunnel-number {
                type uint32 {
                  range "0..65535";
                }
                description
                  "Tunnel interface number";
              }
            }
          }
        }
        leaf interface-name {
          type xr:Interface-name;
          description
            "Interface name";
        }
      }
    }
    container gmpls-nni {
      description
        "GMPLS-NNI configuration";
      container topology-instances {
        description
          "GMPLS-NNI topology instance table";
        list topology-instance {
          must "ospf-int or ospfip-addr" {
            description
              "OSPFInt or OSPFIPAddr must be present.";
          }
          key "ospf-area-type igp-instance-name igp-type";
          description
            "GMPLS-NNI topology instance configuration";
          grouping TOPOLOGY-INSTANCE-CONTENT {
            description
              "TOPOLOGY INSTANCE CONTENT";
            container controllers {
              description
                "GMPLS-NNI controllers";
              list controller {
                key "controller-name";
                description
                  "Configure a GMPLS NNI controller";
                container tti-mode {
                  description
                    "Set tandem connection monitoring for the
                     interface";
                  leaf tti-mode-type {
                    type Gmplstti-mode;
                    description
                      "Type of Trail Trace Identifier";
                  }
                  leaf tcmid {
                    when "../tti-mode-type = 'tcm'" {
                      description
                        "../TTIModeType = TCM";
                    }
                    type uint32 {
                      range "1..6";
                    }
                    description
                      "Tandem Connection Monitoring ID for the
                       interface";
                  }
                }
                container affinity-names {
                  description
                    "Set the interface affinity names";
                  leaf-list affinity-name {
                    type string;
                    max-elements 32;
                    description
                      "Array of Attribute Names";
                  }
                }
                leaf admin-weight {
                  type uint32 {
                    range "0..65535";
                  }
                  description
                    "Set administrative weight for the
                     interface";
                }
                leaf enable {
                  type empty;
                  description
                    "Enable GMPLS-NNI on the link";
                }
                leaf delay {
                  type uint32 {
                    range "1..16777215";
                  }
                  description
                    "Set link delay for the interface";
                }
                leaf controller-name {
                  type xr:Interface-name;
                  description
                    "Controller name";
                }
              }
            }
          }
          leaf igp-type {
            type Mpls-te-igp-protocol;
            description
              "IGP type";
          }
          leaf igp-instance-name {
            type xr:Cisco-ios-xr-string {
              length "1..40";
            }
            description
              "Name of IGP instance";
          }
          leaf ospf-area-type {
            type Ospf-area-mode;
            description
              "OSPF area format";
          }
          list ospf-int {
            when "../ospf-area-type = 'ospf-int'" {
              description
                "../OSPFAreaType = OSPFInt";
            }
            key "igp-area";
            description
              "ospf int";
            leaf igp-area {
              type uint32;
              description
                "IGP area";
            }
            uses TOPOLOGY-INSTANCE-CONTENT;
          }
          list ospfip-addr {
            when "../ospf-area-type = 'ospfip-addr'" {
              description
                "../OSPFAreaType = OSPFIPAddr";
            }
            key "address";
            description
              "ospfip addr";
            leaf address {
              type inet:ipv4-address-no-zone;
              description
                "Area ID if in IP address format";
            }
            uses TOPOLOGY-INSTANCE-CONTENT;
          }
        }
      }
      container tunnel-heads {
        description
          "GMPLS-NNI tunnel-head table";
        list tunnel-head {
          key "tunnel-id";
          description
            "The configuration for a GMPLS NNI tunnel
             head-end";
          container signalled-bandwidth {
            description
              "The existence of this configuration indicates
               the signalled bandwidth has been set for the
               tunnel";
            leaf signalled-bandwidth-type {
              type Otn-signaled-bandwidth;
              description
                "The g.709 signal type requested";
            }
            leaf bitrate {
              when "../signalled-bandwidth-type = 'od-uflex-cbr' or ../signalled-bandwidth-type = 'od-uflex-gfp-resize' or ../signalled-bandwidth-type = 'od-uflex-gfp-not-resize'" {
                description
                  "../SignalledBandwidthType = ODUflexCBR or
                   ../SignalledBandwidthType =
                   ODUflexGFPResize or .
                   ./SignalledBandwidthType =
                   ODUflexGFPNotResize";
              }
              type uint32;
              units "kbit/s";
              description
                "Bitrate value in Kbps for ODUflex framing
                 type";
            }
            leaf od-uflex-framing-type {
              when "../signalled-bandwidth-type = 'od-uflex-cbr' or ../signalled-bandwidth-type = 'od-uflex-gfp-resize' or ../signalled-bandwidth-type = 'od-uflex-gfp-not-resize'" {
                description
                  "../SignalledBandwidthType = ODUflexCBR or
                   ../SignalledBandwidthType =
                   ODUflexGFPResize or .
                   ./SignalledBandwidthType =
                   ODUflexGFPNotResize";
              }
              type Otn-signaled-bandwidth-flex-framing;
              description
                "Framing type in case of ODUflex signal type";
            }
          }
          container destination {
            description
              "The existence of this configuration indicates
               the destination has been set for the tunnel";
            leaf destination {
              type inet:ipv4-address-no-zone;
              description
                "IPV4 tunnel destination";
            }
            leaf destination-type {
              type Otn-destination;
              description
                "Destination type whether it is unicast or
                 unnumbered";
            }
            leaf interface-if-index {
              type uint32;
              description
                "Interface index of port";
            }
          }
          container protection-switching {
            description
              "The configuration for a GMPLS NNI tunnel
               protection switch";
            leaf lockout {
              type Otn-protection-switch-lockout;
              description
                "The configuration is used to prevent switch
                 over for a particular path type in tunnel";
            }
          }
          container logging {
            description
              "Tunnel event logging";
            leaf active-lsp-message {
              type empty;
              description
                "Log all tunnel messages for changes in
                 Active LSP";
            }
            leaf homepath-state-message {
              type empty;
              description
                "Log all messages for changes in state of
                 Homepath of Working LSP";
            }
            leaf signalling-state-message {
              type empty;
              description
                "Log all tunnel sub-LSP state messages";
            }
            leaf path-change-message {
              type empty;
              description
                "Log all tunnel messages for changes in
                 path-change";
            }
            leaf static-cross-connect-message {
              type empty;
              description
                "Log all tunnel messages for static
                 cross-connect messages";
            }
            leaf tunnel-state-message {
              type empty;
              description
                "Log all tunnel messages for changes in
                 tunnel-state";
            }
            leaf insufficient-bw-message {
              type empty;
              description
                "Log tunnel messages for insufficient
                 bandwidth";
            }
          }
          container path-options {
            description
              "GMPLS NNI path options";
            list path-option {
              key "preference-level";
              description
                "The existence of this configuration
                 indicates the path options have been set for
                 the tunnel";
              leaf preference-level {
                type uint32 {
                  range "1..1000";
                }
                description
                  "Preference level for this path option";
              }
              leaf path-type {
                type Mpls-te-path-option;
                description
                  "The type of the path option";
              }
              leaf path-id {
                type uint32 {
                  range "1..65535";
                }
                description
                  "The ID of the IP explicit path associated
                   with this option";
              }
              leaf path-name {
                type string;
                description
                  "The name of the IP explicit path associated
                   with this option";
              }
              leaf protected-by-preference-level {
                type uint32 {
                  range "1..1001";
                }
                description
                  "Preference level of the protecting explicit
                   path. ";
              }
              leaf restore-by-preference-level {
                type uint32 {
                  range "1..1000";
                }
                description
                  "Preference level of the restore path. ";
              }
              leaf xro-type {
                type Mpls-te-path-option-xro;
                mandatory true;
                description
                  "The route-exclusion type";
              }
              leaf xro-attribute-set-name {
                type Attribute-set-name-length;
                description
                  "The name of the XRO attribute set to be
                   used for this path-option";
              }
              leaf affinity-attribute-set-name {
                type Attribute-set-affinity-name-length;
                description
                  "The name of the affinity attribute set to
                   be used for this path-option";
              }
              leaf lockdown {
                type Mpls-te-path-option-property;
                description
                  "Lockdown properties";
              }
            }
          }
          container static-uni {
            description
              "The existence of this configuration indicates
               the static UNI endpoints have been set for
               the tunnel";
            leaf ingress-controller-name {
              type xr:Cisco-ios-xr-string {
                length "1..255";
              }
              description
                "Name of  ingress controller";
            }
            leaf egress-controller-if-index {
              type uint32;
              description
                "Interface index of Egress controller";
            }
            leaf ingress-type {
              type Otn-static-uni;
              description
                "Ingress type whether it is xconnect or
                 terminated";
            }
            leaf egress-type {
              type Otn-static-uni;
              description
                "Egress type whether it is xconnect or
                 terminated";
            }
          }
          leaf enable {
            type empty;
            description
              "The existence of this configuration indicates
               the a new GMPLS NNI tunnel has been enabled";
          }
          leaf announce-srlg {
            type empty;
            description
              "Announce SRLG on term interface for the
               tunnel";
          }
          leaf restore-lsp-shutdown {
            type empty;
            description
              "The existence of this configuration indicates
               the restore LSP of tunnel is shutdown";
          }
          leaf current-lsp-shutdown {
            type empty;
            description
              "The existence of this configuration indicates
               the current/working LSP of tunnel is shutdown";
          }
          leaf path-selection-metric {
            type Mpls-te-path-selection-metric;
            description
              "Path selection configuration for this
               specific tunnel";
          }
          leaf payload {
            type Otn-payload;
            description
              "The existence of this configuration indicates
               the Payload type have been set for the tunnel";
          }
          leaf standby-lsp-shutdown {
            type empty;
            description
              "The existence of this configuration indicates
               the standby/protect LSP of tunnel is shutdown";
          }
          leaf shutdown {
            type empty;
            description
              "The existence of this configuration indicates
               the tunnel is shutdown";
          }
          leaf path-protection-attribute-set-profile {
            type string {
              length "1..64";
            }
            description
              "The name of the path-protection profile to be
               included in signalling messages";
          }
          leaf tunnel-id {
            type uint32 {
              range "0..65535";
            }
            description
              "Tunnel ID";
          }
          uses RECORD-ROUTE;
          uses SIGNALLED-NAME;
        }
      }
      leaf path-selection-metric {
        type Mpls-te-path-selection-metric;
        description
          "Path selection configuration for all gmpls nni
           tunnels";
      }
      leaf enable-gmpls-nni {
        type empty;
        description
          "Enable MPLS Traffic Engineering GMPLS-NNI";
      }
    }
    container lcac {
      description
        "LCAC specific MPLS global configuration";
      container bfd {
        description
          "BFD configuration";
        leaf interval {
          type uint32 {
            range "15..200";
          }
          units "millisecond";
          description
            "Hello interval for BFD sessions created by TE";
        }
        leaf detection-multiplier {
          type uint32 {
            range "2..10";
          }
          description
            "Detection multiplier for BFD sessions created
             by TE";
        }
      }
      container flooding-threshold {
        description
          "Configure flooding threshold as percentage of
           total link bandwidth.";
        leaf up-stream {
          type Mpls-percent-range;
          units "percentage";
          description
            "Upward flooding Threshold in percentages of
             total bandwidth";
        }
        leaf down-stream {
          type Mpls-percent-range;
          units "percentage";
          description
            "Downward flooding Threshold in percentages of
             total bandwidth";
        }
      }
      leaf bandwidth-hold-timer {
        type Mpls-lcac-bandwidth-hold-timer-range;
        units "second";
        description
          "Bandwidth hold timer value (seconds)";
      }
      leaf delay-preempt-bundle-capacity-timer {
        type uint32 {
          range "0..300";
        }
        units "second";
        description
          "Bundle capacity preemption timer value
           (seconds)";
      }
      leaf periodic-flooding-timer {
        type uint32 {
          range "0..3600";
        }
        units "second";
        description
          "Periodic flooding value (seconds)";
      }
    }
    leaf enable-traffic-engineering {
      type empty;
      description
        "Enable MPLS Traffic Engineering";
    }
  }

  augment "/a1:interface-configurations/a1:interface-configuration" {
    description
      "This augment extends the configuration data of
       'Cisco-IOS-XR-ifmgr-cfg'";
    container tunnel-te-attributes {
      status deprecated;
      description
        "This model is deprecated and is replaced by
         Cisco-IOS-XR-um-mpls-te-cfg.yang which will
         provide the compatible functionalities.  MPLS
         tunnel attributes";
      container backup-bandwidth {
        description
          "Tunnel backup bandwidth requirement";
        leaf dste-type {
          type Mpls-te-bandwidth-dste;
          description
            "DSTE-standard flag";
        }
        leaf pool-type {
          type Mpls-te-backup-bandwidth-pool;
          description
            "Backup bandwidth pool type, relevant only if
             DSTEType is PreStandardDSTE";
        }
        leaf class-type {
          type Mpls-te-backup-bandwidth-class;
          description
            "Backup bandwidth class type, relevant only if
             DSTEType is StandardDSTE";
        }
        leaf limit-type {
          type Mpls-te-bandwidth-limit;
          description
            "Backup bandwidth limit type";
        }
        leaf backup-bandwidth {
          type uint32 {
            range "1..4294967295";
          }
          description
            "Backup bandwidth requested by this tunnel in
             kbps. Ignored if bandwidth limit type is
             unlimited.";
        }
      }
      container bfd-over-lsp {
        description
          "BFD over TE LSP";
        leaf dampening-initial-wait {
          type uint32 {
            range "1..518400000";
          }
          description
            "Initial delay in milliseconds (default 16000)";
        }
        leaf bringup-timeout {
          type uint32 {
            range "10..3600";
          }
          description
            "Wait for session to come up in seconds
             (default 60)";
        }
        leaf periodic-ping-disable {
          type empty;
          description
            "Disable Periodic LSP Ping for BFD over LSP";
        }
        leaf dampening-secondary-wait {
          type uint32 {
            range "1..518400000";
          }
          description
            "Secondary delay in milliseconds (default
             20000)";
        }
        leaf periodic-ping-interval {
          type uint32 {
            range "60..3600";
          }
          description
            "Periodic LSP Ping Interval in seconds (default
             120)";
        }
        leaf dampening-maximum-wait {
          type uint32 {
            range "1..518400000";
          }
          description
            "Maximum delay in milliseconds (default 600000)";
        }
        leaf encap-mode {
          type uint32 {
            range "0..1";
          }
          description
            "Specify BFD Encap Mode on the tunnel";
        }
        uses FAST-DETECT;
        uses MPLS-TE-TUNNEL-CFG-ENABLE;
        uses MULTIPLIER;
        uses MINIMUM-INTERVAL;
      }
      container binding-segment-id-mpls {
        description
          "Allocate MPLS binding segment ID";
        leaf segment-id-type {
          type Binding-segment-id;
          description
            "MPLS label value type";
        }
        leaf label-value {
          when "../segment-id-type = 'specified-label'" {
            description
              "../SegmentIDType = SpecifiedLabel";
          }
          type uint32 {
            range "16..4015";
          }
          description
            "MPLS label";
        }
      }
      container tunnel-path-protection {
        description
          "MPLS tunnel path protected configs";
        container protection-mode {
          description
            "Configure Protection Mode";
          leaf non-revertive {
            type empty;
            description
              "Enable non-revertive mode";
          }
        }
        uses MPLS-TE-TUNNEL-CFG-ENABLE-MP;
        uses SRLG-DIVERSE;
      }
      container path-option-protects {
        description
          "Tunnel path protection state";
        list path-option-protect {
          key "protection";
          description
            "Tunnel path protection";
          container path-options {
            description
              "Tunnel path options";
            list path-option {
              key "preference-level";
              description
                "A tunnel path option";
              leaf preference-level {
                type uint32 {
                  range "1..1000";
                }
                description
                  "Preference level for this path option";
              }
              leaf path-type {
                type Mpls-te-path-option;
                mandatory true;
                description
                  "The type of the path option";
              }
              leaf path-id {
                type uint32 {
                  range "1..65535";
                }
                description
                  "The ID of the IP explicit path associated
                   with this option";
              }
              leaf path-name {
                type string;
                description
                  "The name of the IP explicit path associated
                   with this option";
              }
              leaf path-property {
                type uint32;
                default "0";
                description
                  "Deprecated";
              }
              leaf interface {
                type xr:Interface-name;
                description
                  "Deprecated";
              }
              leaf output-label {
                type uint32;
                default "0";
                description
                  "Deprecated";
              }
              leaf destination {
                type inet:ipv4-address-no-zone;
                default "0.0.0.0";
                description
                  "Deprecated";
              }
              leaf lockdown {
                type Mpls-te-path-option-property;
                default "none";
                description
                  "Lockdown properties";
              }
              leaf verbatim {
                type Mpls-te-path-option-property;
                default "none";
                description
                  "Verbatim properties";
              }
              leaf pce {
                type Mpls-te-path-option-property;
                default "none";
                description
                  "PCE properties";
              }
              leaf pce-address {
                type inet:ipv4-address-no-zone;
                default "0.0.0.0";
                description
                  "PCE address";
              }
              leaf igp-type {
                type Mpls-te-igp-protocol;
                default "none";
                description
                  "IGP type";
              }
              leaf igp-instance {
                type string {
                  length "1..40";
                }
                description
                  "IGP instance name";
              }
              leaf igp-area {
                type uint32;
                default "0";
                description
                  "IGP area ID in integer format";
              }
              leaf igp-area-ip-address-id {
                type inet:ipv4-address-no-zone;
                default "0.0.0.0";
                description
                  "IGP area ID in IP address format";
              }
              leaf path-option-attribute-set-name {
                type string;
                description
                  "Path option attribute set name";
              }
              leaf protected-by-preference-level {
                type uint32 {
                  range "1..1000";
                }
                default "1";
                description
                  "Preference level of the protecting explicit
                   path. Leave unset in order to not use an
                   explicit protecting path";
              }
              leaf segment-routing {
                type Mpls-te-path-option-property;
                default "none";
                description
                  "Deprecated";
              }
              leaf sticky {
                type Mpls-te-path-option-property;
                default "none";
                description
                  "Sticky properties";
              }
            }
          }
          leaf protection {
            type Mpls-te-path-option-protection;
            description
              "Protection type for this path";
          }
        }
      }
      container bidirectional {
        description
          "Tunnel Interface Bidirectional configuration
           data";
        container association-corouted-type {
          description
            "Association Corouted Type";
          container fault-oam {
            description
              "Tunnel Fault OAM";
            leaf enable {
              type empty;
              description
                "This object is only valid for bidirectional
                 tunnel interfaces and it controls whether
                 that interface has fault OAM enabled on it
                 or not.";
            }
          }
          leaf wrap-protection-enable {
            type empty;
            description
              "This object is only valid for bidirectional
               tunnel interfaces and it controls whether
               that interface has LSP Wrap protectionenabled
               on it or not.";
          }
          leaf enable {
            type empty;
            description
              "Controls whether association type is
               co-routed.";
          }
          leaf disable-protection-object {
            type empty;
            description
              "Disable signaling of RSVP Protection Object";
          }
        }
        container association-parameters {
          presence "Indicates a association-parameters node is configured.";
          description
            "Association ID, Source IP Address, and Global
             ID";
          leaf association-id {
            type uint32 {
              range "0..65535";
            }
            mandatory true;
            description
              "Association ID";
          }
          leaf association-source-address {
            type inet:ipv4-address-no-zone;
            mandatory true;
            description
              "Association Source IP Address";
          }
          leaf association-is-global-id-configured {
            type boolean;
            description
              "Is Association Global ID Configured";
          }
          leaf association-global-id {
            type uint32 {
              range "0..4294967295";
            }
            description
              "Association Global ID";
          }
        }
        leaf enabled {
          type empty;
          description
            "This object is only valid for tunnel
             interfaces and it controls whether that
             interface has bidirectional enabled on it or
             not.";
        }
      }
      container admin-mode {
        description
          "Performs admin operations on the optical tunnel
           interface";
        leaf deactivate-tunnel {
          type empty;
          description
            "Performs signalling operation to deactivate
             optical tunnel";
        }
      }
      container switching {
        description
          "Specify tunnel LSPs switching capability
           descriptor";
        container transit {
          presence "Indicates a transit node is configured.";
          description
            "Specify transit switching descriptor
             parameters";
          leaf capability {
            type Mpls-te-switching-cap;
            mandatory true;
            description
              "Switching capability";
          }
          leaf encoding {
            type Mpls-te-switching-encode;
            description
              "LSP encoding";
          }
        }
        container endpoint {
          presence "Indicates a endpoint node is configured.";
          description
            "Specify end point switching descriptor
             parameters";
          leaf capability {
            type Mpls-te-switching-cap;
            mandatory true;
            description
              "Switching capability";
          }
          leaf encoding {
            type Mpls-te-switching-encode;
            description
              "LSP encoding";
          }
        }
      }
      container pce {
        description
          "PCE config";
        container delegation {
          description
            "PCE Delegation config";
          leaf enable {
            type empty;
            description
              "Enable PCE Delegation";
          }
          leaf reopt {
            type empty;
            description
              "Enable Reopt for PCE delegated Tunnel";
          }
        }
        leaf enable {
          type empty;
          description
            "Always set to true";
        }
      }
      uses DELAY-MEASUREMENT;
      uses REOPTIMIZE-TIMER-FREQUENCY;
      uses FORWARD-CLASS;
      uses TUNNEL-PATH-SELECTION;
      uses AUTO-BANDWIDTH;
      uses PRIORITY;
      uses DESTINATION;
      uses RECORD-ROUTE;
      uses AFFINITY-MASK;
      uses FORWARDING-ADJACENCY;
      uses LOGGING;
      uses BANDWIDTH;
      uses AUTOROUTE;
      uses POLICY-CLASSES;
      uses PATH-SELECTION-METRIC;
      uses NEW-STYLE-AFFINITY-TABLE;
      uses SOFT-PREEMPTION;
      uses FAST-REROUTE;
      uses LOAD-SHARE;
      uses DESCRIPTION;
      uses SIGNALLED-NAME;
    }
  }
  augment "/a1:interface-configurations/a1:interface-configuration" {
    description
      "This augment extends the configuration data of
       'Cisco-IOS-XR-ifmgr-cfg'";
    container transport-profile-tunnel {
      status deprecated;
      description
        "This model is deprecated and is replaced by
         Cisco-IOS-XR-um-mpls-te-cfg.yang which will
         provide the compatible functionalities.  MPLS-TP
         tunnel attributes";
      container bfd {
        description
          "Configure BFD parameters";
        container min-interval {
          description
            "Hello interval, either in milli-seconds or in
             micro-seconds";
          leaf interval-ms {
            type uint32 {
              range "3..5000";
            }
            description
              "Hello interval in milli-seconds";
          }
          leaf interval-us {
            type uint32 {
              range "3000..5000000";
            }
            description
              "Hello interval in micro-seconds";
          }
        }
        container min-interval-standby {
          description
            "Hello interval for standby transport profile
             LSP, either in milli-seconds or in
             micro-seconds";
          leaf interval-standby-ms {
            type uint32 {
              range "3..5000";
            }
            description
              "Hello interval in milli-seconds";
          }
          leaf interval-standby-us {
            type uint32 {
              range "3000..5000000";
            }
            description
              "Hello interval in micro-seconds";
          }
        }
        leaf detection-multiplier {
          type uint32 {
            range "2..10";
          }
          description
            "Detect multiplier";
        }
        leaf enable {
          type empty;
          description
            "Configure BFD parameters";
        }
        leaf multiplier-standby {
          type uint32 {
            range "2..10";
          }
          description
            "Detect multiplier for standby transport
             profile LSP";
        }
      }
      container working-lsp {
        description
          "Working LSP";
        container out-label {
          presence "Indicates a out-label node is configured.";
          description
            "Outgoing MPLS label of the working LSP";
          leaf label {
            type uint32 {
              range "16..1048575";
            }
            description
              "MPLS label";
          }
          leaf link {
            type uint32 {
              range "1..65535";
            }
            mandatory true;
            description
              "Transport profile identifier of outgoing link";
          }
        }
        leaf in-label {
          type uint32 {
            range "16..4015";
          }
          description
            "Incoming MPLS label of the working LSP";
        }
        leaf lockout {
          type empty;
          description
            "Enable lockout of working LSP";
        }
        leaf lsp-id {
          type uint32 {
            range "0..65535";
          }
          default "0";
          description
            "LSP Identifier of the working LSP";
        }
      }
      container destination {
        description
          "Node identifier and optional global identifier
           and tunnel identifier at destination";
        leaf node-id {
          type inet:ipv4-address-no-zone;
          description
            "Node identifier in IPv4 address format";
        }
        leaf global-id {
          type uint32 {
            range "1..65535";
          }
          description
            "Numeric global identifier";
        }
        leaf tunnel-id {
          type uint32 {
            range "0..65535";
          }
          description
            "Numeric tunnel identifier";
        }
      }
      container fault {
        description
          "Fault management";
        container protection-trigger {
          description
            "OAM events that trigger protection switching";
          leaf ldi {
            type boolean;
            description
              "Enable protection switching due to LDI event";
          }
          leaf ais {
            type boolean;
            description
              "Enable protection switching due to AIS event";
          }
          leaf lkr {
            type boolean;
            description
              "Enable protection switching due to LKR event";
          }
        }
        leaf enable {
          type empty;
          description
            "Enter transport profile tunnel fault
             configuration";
        }
      }
      container protect-lsp {
        description
          "Protect LSP";
        container out-label {
          presence "Indicates a out-label node is configured.";
          description
            "Outgoing MPLS label of the protect LSP";
          leaf label {
            type uint32 {
              range "16..1048575";
            }
            description
              "MPLS label";
          }
          leaf link {
            type uint32 {
              range "1..65535";
            }
            mandatory true;
            description
              "Transport profile identifier of outgoing link";
          }
        }
        leaf in-label {
          type uint32 {
            range "16..4015";
          }
          description
            "Incoming MPLS label of the protect LSP";
        }
        leaf lockout {
          type empty;
          description
            "Enable lockout of protect LSP";
        }
        leaf lsp-id {
          type uint32 {
            range "0..65535";
          }
          default "1";
          description
            "LSP Identifier of the protect LSP";
        }
      }
      leaf source {
        type inet:ipv4-address-no-zone;
        description
          "Transport profile node identifier in IPv4
           address format";
      }
    }
  }
  augment "/a1:interface-configurations/a1:interface-configuration" {
    description
      "This augment extends the configuration data of
       'Cisco-IOS-XR-ifmgr-cfg'";
    container mte-tunnel-attributes {
      status deprecated;
      description
        "This model is deprecated and is replaced by
         Cisco-IOS-XR-um-mpls-te-cfg.yang which will
         provide the compatible functionalities.  MPLS
         P2MP tunnel attributes";
      container destination-leafs {
        description
          "P2MP destination table";
        list destination-leaf {
          key "address";
          description
            "P2MP destination leaf";
          container s2l-logging {
            description
              "Log tunnel destination s2l messages";
            leaf s2l-reroute-messsage {
              type empty;
              description
                "Log tunnel destination s2l rereoute messages";
            }
            leaf s2l-insufficient-bw-messsage {
              type empty;
              description
                "Log tunnel destination s2l insufficient BW
                 messages";
            }
            leaf s2l-pcalc-failure-message {
              type empty;
              description
                "Enable logging for destination s2l
                 path-calculation failures";
            }
            leaf s2l-state-message {
              type empty;
              description
                "Log tunnel destination s2l state messages";
            }
          }
          container path-options {
            description
              "P2MP destination path-options attributes
               table";
            list path-option {
              key "preference-level";
              description
                "P2MP destination path option";
              leaf preference-level {
                type uint32 {
                  range "1..1000";
                }
                description
                  "Preference level for this path option";
              }
              leaf path-type {
                type Mpls-te-path-option;
                description
                  "The type of the path option";
              }
              leaf path-id {
                type uint32 {
                  range "1..65535";
                }
                description
                  "The ID of the IP explicit path associated
                   with this option";
              }
              leaf path-name {
                type string;
                description
                  "The name of the IP explicit path associated
                   with this option";
              }
              leaf lockdown {
                type Mpls-te-path-option-property;
                description
                  "Path option properties";
              }
              leaf verbatim {
                type Mpls-te-path-option-property;
                description
                  "Path option properties";
              }
            }
          }
          leaf destination-disable {
            type empty;
            description
              "Disables P2MP destination";
          }
          leaf destination {
            type empty;
            description
              "Always set to true";
          }
          leaf address {
            type inet:ipv4-address-no-zone;
            description
              "Address of P2MP destination";
          }
        }
      }
      container priority {
        presence "Indicates a priority node is configured.";
        description
          "P2MP tunnel setup and hold priorities";
        leaf setup-priority {
          type uint32 {
            range "0..7";
          }
          mandatory true;
          description
            "Setup Priority";
        }
        leaf hold-priority {
          type uint32 {
            range "0..7";
          }
          mandatory true;
          description
            "Hold Priority";
        }
      }
      container new-style-affinity-affinity-types {
        description
          "P2MP tunnel new style affinity attributes table";
        list new-style-affinity-affinity-type {
          key "affinity-type";
          description
            "Tunnel new style affinity attribute";
          leaf affinity-type {
            type Mpls-te-tunnel-affinity;
            description
              "The type of the affinity entry";
          }
        }
        list new-style-affinity-affinity-type-affinity1 {
          key "affinity-type affinity1";
          description
            "Tunnel new style affinity attribute";
          leaf affinity-type {
            type Mpls-te-tunnel-affinity;
            description
              "The type of the affinity entry";
          }
          leaf affinity1 {
            type xr:Cisco-ios-xr-string;
            description
              "The name of the first affinity";
          }
        }
        list new-style-affinity-affinity-type-affinity1-affinity2 {
          key "affinity-type affinity1 affinity2";
          description
            "Tunnel new style affinity attribute";
          leaf affinity-type {
            type Mpls-te-tunnel-affinity;
            description
              "The type of the affinity entry";
          }
          leaf affinity1 {
            type xr:Cisco-ios-xr-string;
            description
              "The name of the first affinity";
          }
          leaf affinity2 {
            type xr:Cisco-ios-xr-string;
            description
              "The name of the second affinity";
          }
        }
        list new-style-affinity-affinity-type-affinity1-affinity2-affinity3 {
          key "affinity-type affinity1 affinity2 affinity3";
          description
            "Tunnel new style affinity attribute";
          leaf affinity-type {
            type Mpls-te-tunnel-affinity;
            description
              "The type of the affinity entry";
          }
          leaf affinity1 {
            type xr:Cisco-ios-xr-string;
            description
              "The name of the first affinity";
          }
          leaf affinity2 {
            type xr:Cisco-ios-xr-string;
            description
              "The name of the second affinity";
          }
          leaf affinity3 {
            type xr:Cisco-ios-xr-string;
            description
              "The name of the third affinity";
          }
        }
        list new-style-affinity-affinity-type-affinity1-affinity2-affinity3-affinity4 {
          key "affinity-type affinity1 affinity2 affinity3 affinity4";
          description
            "Tunnel new style affinity attribute";
          leaf affinity-type {
            type Mpls-te-tunnel-affinity;
            description
              "The type of the affinity entry";
          }
          leaf affinity1 {
            type xr:Cisco-ios-xr-string;
            description
              "The name of the first affinity";
          }
          leaf affinity2 {
            type xr:Cisco-ios-xr-string;
            description
              "The name of the second affinity";
          }
          leaf affinity3 {
            type xr:Cisco-ios-xr-string;
            description
              "The name of the third affinity";
          }
          leaf affinity4 {
            type xr:Cisco-ios-xr-string;
            description
              "The name of the fourth affinity";
          }
        }
        list new-style-affinity-affinity-type-affinity1-affinity2-affinity3-affinity4-affinity5 {
          key "affinity-type affinity1 affinity2 affinity3 affinity4 affinity5";
          description
            "Tunnel new style affinity attribute";
          leaf affinity-type {
            type Mpls-te-tunnel-affinity;
            description
              "The type of the affinity entry";
          }
          leaf affinity1 {
            type xr:Cisco-ios-xr-string;
            description
              "The name of the first affinity";
          }
          leaf affinity2 {
            type xr:Cisco-ios-xr-string;
            description
              "The name of the second affinity";
          }
          leaf affinity3 {
            type xr:Cisco-ios-xr-string;
            description
              "The name of the third affinity";
          }
          leaf affinity4 {
            type xr:Cisco-ios-xr-string;
            description
              "The name of the fourth affinity";
          }
          leaf affinity5 {
            type xr:Cisco-ios-xr-string;
            description
              "The name of the fifth affinity";
          }
        }
        list new-style-affinity-affinity-type-affinity1-affinity2-affinity3-affinity4-affinity5-affinity6 {
          key "affinity-type affinity1 affinity2 affinity3 affinity4 affinity5 affinity6";
          description
            "Tunnel new style affinity attribute";
          leaf affinity-type {
            type Mpls-te-tunnel-affinity;
            description
              "The type of the affinity entry";
          }
          leaf affinity1 {
            type xr:Cisco-ios-xr-string;
            description
              "The name of the first affinity";
          }
          leaf affinity2 {
            type xr:Cisco-ios-xr-string;
            description
              "The name of the second affinity";
          }
          leaf affinity3 {
            type xr:Cisco-ios-xr-string;
            description
              "The name of the third affinity";
          }
          leaf affinity4 {
            type xr:Cisco-ios-xr-string;
            description
              "The name of the fourth affinity";
          }
          leaf affinity5 {
            type xr:Cisco-ios-xr-string;
            description
              "The name of the fifth affinity";
          }
          leaf affinity6 {
            type xr:Cisco-ios-xr-string;
            description
              "The name of the sixth affinity";
          }
        }
        list new-style-affinity-affinity-type-affinity1-affinity2-affinity3-affinity4-affinity5-affinity6-affinity7 {
          key "affinity-type affinity1 affinity2 affinity3 affinity4 affinity5 affinity6 affinity7";
          description
            "Tunnel new style affinity attribute";
          leaf affinity-type {
            type Mpls-te-tunnel-affinity;
            description
              "The type of the affinity entry";
          }
          leaf affinity1 {
            type xr:Cisco-ios-xr-string;
            description
              "The name of the first affinity";
          }
          leaf affinity2 {
            type xr:Cisco-ios-xr-string;
            description
              "The name of the second affinity";
          }
          leaf affinity3 {
            type xr:Cisco-ios-xr-string;
            description
              "The name of the third affinity";
          }
          leaf affinity4 {
            type xr:Cisco-ios-xr-string;
            description
              "The name of the fourth affinity";
          }
          leaf affinity5 {
            type xr:Cisco-ios-xr-string;
            description
              "The name of the fifth affinity";
          }
          leaf affinity6 {
            type xr:Cisco-ios-xr-string;
            description
              "The name of the sixth affinity";
          }
          leaf affinity7 {
            type xr:Cisco-ios-xr-string;
            description
              "The name of the seventh affinity";
          }
        }
        list new-style-affinity-affinity-type-affinity1-affinity2-affinity3-affinity4-affinity5-affinity6-affinity7-affinity8 {
          key "affinity-type affinity1 affinity2 affinity3 affinity4 affinity5 affinity6 affinity7 affinity8";
          description
            "Tunnel new style affinity attribute";
          leaf affinity-type {
            type Mpls-te-tunnel-affinity;
            description
              "The type of the affinity entry";
          }
          leaf affinity1 {
            type xr:Cisco-ios-xr-string;
            description
              "The name of the first affinity";
          }
          leaf affinity2 {
            type xr:Cisco-ios-xr-string;
            description
              "The name of the second affinity";
          }
          leaf affinity3 {
            type xr:Cisco-ios-xr-string;
            description
              "The name of the third affinity";
          }
          leaf affinity4 {
            type xr:Cisco-ios-xr-string;
            description
              "The name of the fourth affinity";
          }
          leaf affinity5 {
            type xr:Cisco-ios-xr-string;
            description
              "The name of the fifth affinity";
          }
          leaf affinity6 {
            type xr:Cisco-ios-xr-string;
            description
              "The name of the sixth affinity";
          }
          leaf affinity7 {
            type xr:Cisco-ios-xr-string;
            description
              "The name of the seventh affinity";
          }
          leaf affinity8 {
            type xr:Cisco-ios-xr-string;
            description
              "The name of the eighth affinity";
          }
        }
        list new-style-affinity-affinity-type-affinity1-affinity2-affinity3-affinity4-affinity5-affinity6-affinity7-affinity8-affinity9 {
          key "affinity-type affinity1 affinity2 affinity3 affinity4 affinity5 affinity6 affinity7 affinity8 affinity9";
          description
            "Tunnel new style affinity attribute";
          leaf affinity-type {
            type Mpls-te-tunnel-affinity;
            description
              "The type of the affinity entry";
          }
          leaf affinity1 {
            type xr:Cisco-ios-xr-string;
            description
              "The name of the first affinity";
          }
          leaf affinity2 {
            type xr:Cisco-ios-xr-string;
            description
              "The name of the second affinity";
          }
          leaf affinity3 {
            type xr:Cisco-ios-xr-string;
            description
              "The name of the third affinity";
          }
          leaf affinity4 {
            type xr:Cisco-ios-xr-string;
            description
              "The name of the fourth affinity";
          }
          leaf affinity5 {
            type xr:Cisco-ios-xr-string;
            description
              "The name of the fifth affinity";
          }
          leaf affinity6 {
            type xr:Cisco-ios-xr-string;
            description
              "The name of the sixth affinity";
          }
          leaf affinity7 {
            type xr:Cisco-ios-xr-string;
            description
              "The name of the seventh affinity";
          }
          leaf affinity8 {
            type xr:Cisco-ios-xr-string;
            description
              "The name of the eighth affinity";
          }
          leaf affinity9 {
            type xr:Cisco-ios-xr-string;
            description
              "The name of the nineth affinity";
          }
        }
        list new-style-affinity-affinity-type-affinity1-affinity2-affinity3-affinity4-affinity5-affinity6-affinity7-affinity8-affinity9-affinity10 {
          key "affinity-type affinity1 affinity2 affinity3 affinity4 affinity5 affinity6 affinity7 affinity8 affinity9 affinity10";
          description
            "Tunnel new style affinity attribute";
          leaf affinity-type {
            type Mpls-te-tunnel-affinity;
            description
              "The type of the affinity entry";
          }
          leaf affinity1 {
            type xr:Cisco-ios-xr-string;
            description
              "The name of the first affinity";
          }
          leaf affinity2 {
            type xr:Cisco-ios-xr-string;
            description
              "The name of the second affinity";
          }
          leaf affinity3 {
            type xr:Cisco-ios-xr-string;
            description
              "The name of the third affinity";
          }
          leaf affinity4 {
            type xr:Cisco-ios-xr-string;
            description
              "The name of the fourth affinity";
          }
          leaf affinity5 {
            type xr:Cisco-ios-xr-string;
            description
              "The name of the fifth affinity";
          }
          leaf affinity6 {
            type xr:Cisco-ios-xr-string;
            description
              "The name of the sixth affinity";
          }
          leaf affinity7 {
            type xr:Cisco-ios-xr-string;
            description
              "The name of the seventh affinity";
          }
          leaf affinity8 {
            type xr:Cisco-ios-xr-string;
            description
              "The name of the eighth affinity";
          }
          leaf affinity9 {
            type xr:Cisco-ios-xr-string;
            description
              "The name of the nineth affinity";
          }
          leaf affinity10 {
            type xr:Cisco-ios-xr-string;
            description
              "The name of the tenth affinity";
          }
        }
      }
      container bandwidth {
        description
          "P2MP tunnel bandwidth requirement";
        leaf dste-type {
          type Mpls-te-bandwidth-dste;
          description
            "DSTE-standard flag";
        }
        leaf class-or-pool-type {
          type uint32 {
            range "0..1";
          }
          description
            "Class type for the bandwidth allocation";
        }
        leaf bandwidth {
          type uint32 {
            range "0..4294967295";
          }
          description
            "The value of the bandwidth reserved by this
             tunnel in kbps";
        }
      }
      container affinity-mask {
        description
          "P2MP tunnel affinity and mask";
        leaf affinity {
          type xr:Hex-integer;
          description
            "Affinity flags";
        }
        leaf mask {
          type xr:Hex-integer;
          description
            "Affinity mask";
        }
      }
      leaf soft-preemption {
        type empty;
        description
          "Enable the soft-preemption feature on the
           tunnel";
      }
      leaf record-route {
        type empty;
        description
          "Record route used by individual P2MP S2L(s)";
      }
      leaf signalled-name {
        type string {
          length "1..254";
        }
        description
          "The name of the P2MP tunnel to be included in
           signalling messages";
      }
      leaf path-selection-metric {
        type Mpls-te-path-selection-metric;
        description
          "Path selection configuration for this specific
           tunnel";
      }
      leaf signalled-payload {
        type xr:Hex-integer;
        description
          "P2MP tunnel ipv6 signalled payload";
      }
      leaf fast-reroute {
        type empty;
        description
          "Specify P2MP tunnel can be fast-rerouted";
      }
      leaf impose-explicit-null {
        type empty;
        description
          "Impose an explicit null bellow the TE label";
      }
      uses MPLS-MTE-TUNNEL-CFG-LOGGING;
    }
  }
  augment "/a2:mib" {
    description
      "This augment extends the configuration data of
       'Cisco-IOS-XR-snmp-agent-cfg'";
    container mpls-te-mib {
      status deprecated;
      description
        "This model is deprecated and is replaced by
         Cisco-IOS-XR-um-mpls-te-cfg.yang which will
         provide the compatible functionalities.  MPLS TE
         MIB configuration";
      leaf cache-garbage-collect-timer {
        type uint32 {
          range "0..3600";
        }
        units "second";
        default "1800";
        description
          "Configure the cache garbage collector time for
           the mib.";
      }
      uses CACHE-TIMER;
    }
  }
  augment "/a2:mib" {
    description
      "This augment extends the configuration data of
       'Cisco-IOS-XR-snmp-agent-cfg'";
    container mpls-p2mp-mib {
      status deprecated;
      description
        "This model is deprecated and is replaced by
         Cisco-IOS-XR-um-mpls-te-cfg.yang which will
         provide the compatible functionalities.  MPLS
         P2MP MIB configuration";
      uses CACHE-TIMER;
    }
  }
  augment "/a2:mib" {
    description
      "This augment extends the configuration data of
       'Cisco-IOS-XR-snmp-agent-cfg'";
    container mpls-te-ext-std-mib {
      status deprecated;
      description
        "This model is deprecated and is replaced by
         Cisco-IOS-XR-um-mpls-te-cfg.yang which will
         provide the compatible functionalities.  MPLS TE
         EXT STD MIB configuration";
      uses CACHE-TIMER;
    }
  }
  augment "/a2:mib" {
    description
      "This augment extends the configuration data of
       'Cisco-IOS-XR-snmp-agent-cfg'";
    container mpls-te-ext-mib {
      status deprecated;
      description
        "This model is deprecated and is replaced by
         Cisco-IOS-XR-um-mpls-te-cfg.yang which will
         provide the compatible functionalities.  MPLS TE
         EXT MIB configuration";
      uses CACHE-TIMER;
    }
  }
  augment "/a2:mib" {
    description
      "This augment extends the configuration data of
       'Cisco-IOS-XR-snmp-agent-cfg'";
    container mpls-frr-mib {
      status deprecated;
      description
        "This model is deprecated and is replaced by
         Cisco-IOS-XR-um-mpls-te-cfg.yang which will
         provide the compatible functionalities.  FRR MIB
         configuration";
      uses CACHE-TIMER;
    }
  }
  augment "/a2:snmp/a2:notification" {
    description
      "This augment extends the configuration data of
       'Cisco-IOS-XR-snmp-agent-cfg'";
    container mpls-te-p2mp {
      status deprecated;
      description
        "This model is deprecated and is replaced by
         Cisco-IOS-XR-um-mpls-te-cfg.yang which will
         provide the compatible functionalities.
         CISCO-MPLS-TE-P2MP-STD-MIB notification
         configuration";
      leaf up {
        type empty;
        description
          "Enable cmplsTeP2mpTunnelDestUp notification";
      }
      leaf down {
        type empty;
        description
          "Enable cmplsTeP2mpTunnelDestDown notification";
      }
    }
  }
  augment "/a2:snmp/a2:notification" {
    description
      "This augment extends the configuration data of
       'Cisco-IOS-XR-snmp-agent-cfg'";
    container mpls-te {
      status deprecated;
      description
        "This model is deprecated and is replaced by
         Cisco-IOS-XR-um-mpls-te-cfg.yang which will
         provide the compatible functionalities.
         MPLS-TE-STD-MIB notification configuration";
      container cisco-extension {
        description
          "CISCO-MPLS-TE-STD-EXT-MIB notification
           configuration";
        leaf preempt {
          type empty;
          description
            "Enable cmplsTunnelPreempt notification";
        }
        leaf insufficient-bandwidth {
          type empty;
          description
            "Enable cmplsTunnelInsuffBW notification";
        }
        leaf re-route-pending-clear {
          type empty;
          description
            "Enable cmplsTunnelReRoutePendingClear
             notification";
        }
        leaf bringup-fail {
          type empty;
          description
            "Enable cmplsTunnelBringupFail notification";
        }
        leaf re-route-pending {
          type empty;
          description
            "Enable cmplsTunnelReRoutePending notification";
        }
      }
      leaf cisco {
        type empty;
        description
          "Enable MPLS TE tunnel Cisco format (default
           IETF) notification";
      }
      leaf up {
        type empty;
        description
          "Enable mplsTunnelUp notification";
      }
      leaf reoptimize {
        type empty;
        description
          "Enable mplsTunnelReoptimized notification";
      }
      leaf reroute {
        type empty;
        description
          "Enable mplsTunnelRerouted notification";
      }
      leaf down {
        type empty;
        description
          "Enable mplsTunnelDown notification";
      }
    }
  }
  augment "/a2:snmp/a2:notification" {
    description
      "This augment extends the configuration data of
       'Cisco-IOS-XR-snmp-agent-cfg'";
    container mpls-frr {
      status deprecated;
      description
        "This model is deprecated and is replaced by
         Cisco-IOS-XR-um-mpls-te-cfg.yang which will
         provide the compatible functionalities.
         CISCO-IETF-FRR-MIB notification configuration";
      leaf unprotected {
        type empty;
        description
          "Enable cmplsFrrUnProtected notification";
      }
      leaf enable {
        type empty;
        description
          "Enable cmplsFrrMIB notifications";
      }
      leaf protected {
        type empty;
        description
          "Enable cmplsFrrProtected notification";
      }
    }
  }
}
