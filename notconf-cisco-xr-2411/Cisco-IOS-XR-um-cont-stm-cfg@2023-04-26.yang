module Cisco-IOS-XR-um-cont-stm-cfg {
  namespace "http://cisco.com/ns/yang/Cisco-IOS-XR-um-cont-stm-cfg";
  prefix um-cont-stm-cfg;

  import Cisco-IOS-XR-um-interface-cfg {
    prefix a1;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR cont-stm package configuration.

     This YANG module augments the
     modules with configuration data.

     Copyright (c) 2021-2023 by Cisco Systems, Inc.
     All rights reserved.";

  revision 2023-04-26 {
    semver:module-version "1.1.0";
    description
      "Added aug-mapping hierarchy
       2022-07-11
         Added missing description statement to nodes
       2022-06-01
         Adjusted controller augmentation hierarchy
       2022-05-13
         Added new leaf node sixtyfour-bytes under container overhead/j0/send and overhead/j0/expected";
  }
  revision 2021-05-07 {
    semver:module-version "1.0.0";
    description
      "Initial release";
  }

  grouping CONT-BODY {
    description
      "Grouping for controller";
    container clock {
      description
        "Configure SONET/SDH port clock";
      leaf source {
        type enumeration {
          enum "internal" {
            value 0;
            description
              "Select internal clock";
          }
          enum "line" {
            value 1;
            description
              "Select clock recovered from line (default)";
          }
        }
        description
          "Configure SONET/SDH port TX clock source";
      }
    }
    container loopback {
      description
        "Configure SONET/SDH controller loopback mode";
      container internal {
        must "not(../line)";
        presence "Indicates a internal node is configured.";
        description
          "Select local (terminal) loopback";
      }
      container line {
        must "not(../internal)";
        presence "Indicates a line node is configured.";
        description
          "Select network (facility) loopback";
      }
    }
    container overhead {
      description
        "Configure SONET Section & Line or SDH Regeneration Section & Multiplex Section OH byte/bit values";
      container j0 {
        description
          "Specify SONET Section trace or SDH Regeneration Section identifier (J0/C1) ";
        container send {
          description
            "Set transmit trace Identifier";
          leaf one-byte {
            type uint32 {
              range "0..255" {
                description
                  "J0/C1 byte value (default 0x01)";
              }
            }
            must "not(../sixteen-bytes or ../sixtyfour-bytes)";
            description
              "Configure a 1 byte section or Regeneration section trace ";
          }
          leaf sixteen-bytes {
            type string {
              length "1..15" {
                description
                  "ASCII text ";
              }
            }
            must "not(../one-byte or ../sixtyfour-bytes)";
            description
              "Configure a 16 bytes section or Regeneration section trace";
          }
          leaf sixtyfour-bytes {
            type string {
              length "1..62" {
                description
                  "ASCII text ";
              }
            }
            must "not(../one-byte or ../sixteen-bytes)";
            description
              "Configure a Section layer/Regeneration layer trace, string of upto 62 characters accepted(<CR> & <LF> characters will be added at the end).";
          }
        }
        container expected {
          description
            "Set expected trace Identifier";
          leaf one-byte {
            type uint32 {
              range "0..255" {
                description
                  "J0/C1 byte value (default 0x01)";
              }
            }
            must "not(../sixteen-bytes or ../sixtyfour-bytes)";
            description
              "Configure a 1 byte section or Regeneration section trace ";
          }
          leaf sixteen-bytes {
            type string {
              length "1..15" {
                description
                  "ASCII text ";
              }
            }
            must "not(../one-byte or ../sixtyfour-bytes)";
            description
              "Configure a 16 bytes section or Regeneration section trace";
          }
          leaf sixtyfour-bytes {
            type string {
              length "1..62" {
                description
                  "ASCII text ";
              }
            }
            must "not(../one-byte or ../sixteen-bytes)";
            description
              "Configure a Section layer/Regeneration layer trace, string of upto 62 characters accepted(<CR> & <LF> characters will be added at the end).";
          }
        }
      }
    }
    container aug-mapping {
      description
        "Configure Administrative Unit Group(AUG) for STM controller";
      container au4 {
        description
          "Mapping type AU4";
        container au-4s {
          description
            "Select AU number";
          list au-4 {
            key "au-4-id";
            description
              "Select AU number";
            leaf au-4-id {
              type uint32 {
                range "1" {
                  description
                    "AU4 number";
                }
              }
              description
                "Select AU number";
            }
            container modes {
              description
                "Configure mode for this Auxilary Unit 4(AU4)";
              list mode {
                key "mode-id";
                description
                  "Configure mode for this Auxilary Unit 4(AU4)";
                leaf mode-id {
                  type enumeration {
                    enum "tug3" {
                      value 3;
                      description
                        "Tributary Unit Group (TUG3)";
                    }
                  }
                  description
                    "Configure mode for this Auxilary Unit 4(AU4)";
                }
                container tug-3s {
                  description
                    "Select TUG-3(Tributary Unit Group (TUG-n)) number";
                  list tug-3 {
                    key "tug-3-id";
                    description
                      "Select TUG-3(Tributary Unit Group (TUG-n)) number";
                    leaf tug-3-id {
                      type uint32 {
                        range "1..3" {
                          description
                            "TUG-3 number";
                        }
                      }
                      description
                        "Select TUG-3(Tributary Unit Group (TUG-n)) number";
                    }
                    container modes {
                      description
                        "Configure mode for this TUG-3";
                      list mode {
                        key "mode-id";
                        description
                          "Configure mode for this TUG-3";
                        leaf mode-id {
                          type enumeration {
                            enum "tug2" {
                              value 4;
                              description
                                "Mode TUG2 (Tributary Unit Group TUG-2)";
                            }
                          }
                          description
                            "Configure mode for this TUG-3";
                        }
                        container tug-2s {
                          description
                            "Configure TUG-2";
                          list tug-2 {
                            key "tug-2-id payload-id";
                            description
                              "Configure TUG-2";
                            leaf tug-2-id {
                              type uint32 {
                                range "1..7" {
                                  description
                                    "Select TUG-2 number";
                                }
                              }
                              description
                                "Configure TUG-2";
                            }
                            leaf payload-id {
                              type enumeration {
                                enum "vc12" {
                                  value 5;
                                  description
                                    "Payload type VC12(Virtual Container)";
                                }
                              }
                              description
                                "Configure payload type";
                            }
                            container vc12s {
                              description
                                "Configure VC12 type Virtual Container ";
                              list vc12 {
                                key "vc12-id";
                                description
                                  "Configure VC12 type Virtual Container ";
                                leaf vc12-id {
                                  type uint32 {
                                    range "1..3" {
                                      description
                                        "Select VC12 number";
                                    }
                                  }
                                  description
                                    "Configure VC12 type Virtual Container ";
                                }
                                leaf mapping {
                                  type enumeration {
                                    enum "e1" {
                                      value 5;
                                      description
                                        "Mapping type E1";
                                    }
                                  }
                                  mandatory true;
                                  description
                                    "Configure mapping for this VC(Virtual Container)";
                                }
                              }
                            }
                          }
                        }
                      }
                    }
                  }
                }
              }
            }
          }
        }
      }
    }
    container perf-mon {
      description
        "Enable/Disable Performance Monitoring";
      container disable {
        must "not(../enable)";
        presence "Indicates a disable node is configured.";
        description
          "Disable performance monitoring";
      }
      container enable {
        must "not(../disable)";
        presence "Indicates a enable node is configured.";
        description
          "Enable performance monitoring";
      }
    }
    container threshold {
      description
        "Configure SONET section/line or SDH Regeneration/Multiplex Section BER threshold values";
      leaf b1-tca {
        type uint32 {
          range "3..9" {
            description
              "Bit error rate (10 to the minus n) (default 6)";
          }
        }
        description
          "Set B1 BER Threshold Crossing Alert (TCA) threshold";
      }
      leaf b2-tca {
        type uint32 {
          range "3..9" {
            description
              "Bit error rate (10 to the minus n) (default 6)";
          }
        }
        description
          "Set B2 BER Threshold Crossing Alert (TCA) threshold";
      }
      leaf sd-ber {
        type uint32 {
          range "5..9" {
            description
              "Bit error rate (10 to the minus n) (default 6)";
          }
        }
        description
          "Set Signal Degrade BER threshold";
      }
      leaf sf-ber {
        type uint32 {
          range "3..5" {
            description
              "Bit error rate (10 to the minus n) (default 3)";
          }
        }
        description
          "Set Signal Fail BER threshold";
      }
    }
  }

  augment "/a1:controllers/a1:controller" {
    description
      "This augment extends active nodes configuration";
    uses CONT-BODY;
  }
  augment "/a1:controllers/a1:controller-preconfigure" {
    description
      "This augment extends preconfigured nodes
       configuration";
    uses CONT-BODY;
  }
}
