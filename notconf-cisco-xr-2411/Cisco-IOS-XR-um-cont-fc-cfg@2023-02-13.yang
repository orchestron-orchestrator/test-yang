module Cisco-IOS-XR-um-cont-fc-cfg {
  namespace "http://cisco.com/ns/yang/Cisco-IOS-XR-um-cont-fc-cfg";
  prefix um-cont-fc-cfg;

  import Cisco-IOS-XR-types {
    prefix xr;
  }
  import Cisco-IOS-XR-um-interface-cfg {
    prefix a1;
  }
  import Cisco-IOS-XR-um-snmp-server-cfg {
    prefix a2;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR cont-fc package configuration.

     This YANG module augments the
     modules with configuration data.

     Copyright (c) 2023 by Cisco Systems, Inc.
     All rights reserved.";

  revision 2023-02-13 {
    semver:module-version "1.0.0";
    description
      "Added tts support";
  }
  revision 2022-09-22 {
    description
      "Initial release";
  }

  grouping CONT-BODY {
    description
      "Grouping for controller";
    container perf-mon {
      description
        "Performance Monitoring";
      container disable {
        presence "Indicates a disable node is configured.";
        description
          "Disable performance monitoring";
      }
    }
    leaf loopback {
      type enumeration {
        enum "line" {
          value 1;
          description
            "Enable line loopback";
        }
        enum "internal" {
          value 2;
          description
            "Enable internal loopback";
        }
      }
      description
        "Set the loopback mode on a controller";
    }
    container laser-squelch {
      presence "Indicates a laser-squelch node is configured.";
      description
        "Enable Fibre Channel controller laser-squelch";
    }
    container holdoff-time {
      description
        "Holdoff time configuration";
      leaf trunk-fault {
        type uint32 {
          range "0..3000" {
            description
              "Time in ms";
          }
        }
        description
          "Holdoff time trunk fault configuration";
      }
    }
    container threshold {
      description
        "Configure BER threshold values";
      leaf sd-ber {
        type uint32 {
          range "6..12" {
            description
              "Bit error rate (10 to the minus n)";
          }
        }
        description
          "Set Signal Degrade BER threshold";
      }
      leaf sf-ber {
        type uint32 {
          range "3..9" {
            description
              "Bit error rate (10 to the minus n) ";
          }
        }
        description
          "Set Signal Fail BER threshold";
      }
    }
    leaf fec {
      type enumeration {
        enum "none" {
          value 1;
          description
            "Disable any FEC enabled on the controller";
        }
        enum "standard" {
          value 2;
          description
            "Set the standard FEC";
        }
      }
      description
        "Set the Forward Error Correction mode on a controller";
    }
    container tts {
      presence "Indicates a tts node is configured.";
      description
        "Set Transmitter Training Signal configuration for fibre channel controller";
    }
    container prbs {
      presence "Indicates a prbs node is configured.";
      description
        "Configure Pseudo Random Binary Sequence test";
      leaf mode {
        type enumeration {
          enum "source" {
            value 1;
            description
              "source mode";
          }
          enum "sink" {
            value 2;
            description
              "sink mode";
          }
          enum "source-sink" {
            value 3;
            description
              "source-sink mode";
          }
        }
        must "../pattern";
        mandatory true;
        description
          "Configure PRBS mode";
      }
      leaf pattern {
        type enumeration {
          enum "pn31" {
            value 1;
            description
              "Configure PRBS pattern pn31";
          }
          enum "pn23" {
            value 2;
            description
              "Configure PRBS pattern pn23";
          }
          enum "pn15" {
            value 3;
            description
              "Configure PRBS pattern pn15";
          }
          enum "pn11" {
            value 4;
            description
              "Configure PRBS pattern pn11";
          }
          enum "pn9" {
            value 5;
            description
              "Configure PRBS pattern pn9";
          }
          enum "pn7" {
            value 6;
            description
              "Configure PRBS pattern pn7";
          }
          enum "user-defined" {
            value 7;
            description
              "Configure any 64-bit user defined pattern";
          }
        }
        must "../mode";
        mandatory true;
        description
          "Configure PRBS pattern";
      }
      leaf framing {
        type enumeration {
          enum "framed" {
            value 1;
            description
              "Framed PRBS";
          }
          enum "unframed" {
            value 2;
            description
              "Unframed PRBS";
          }
        }
        description
          "Configure prbs framing type";
      }
      leaf direction {
        type enumeration {
          enum "line" {
            value 1;
            description
              "Run prbs towards line side";
          }
          enum "system" {
            value 2;
            description
              "Run prbs towards system side";
          }
        }
        description
          "Configure prbs direction";
      }
      leaf error-inject {
        type enumeration {
          enum "single" {
            value 1;
            description
              "Inject error once";
          }
          enum "continuous" {
            value 2;
            description
              "Inject error continuously";
          }
        }
        description
          "Inject errors in the PRBS pattern";
      }
      leaf user-pattern {
        type xr:Hex-long-integer;
        description
          "PRBS user defined pattern(64-bit hex value)";
      }
    }
    container extended-loopback {
      description
        "Configure Extended loopback (diagnostics)";
      container levels {
        description
          "Level at which to loopback";
        list level {
          key "level-id";
          description
            "Level at which to loopback";
          leaf level-id {
            type uint32 {
              range "1..3" {
                description
                  "";
              }
            }
            description
              "Level at which to loopback";
          }
        }
      }
    }
  }

  augment "/a1:controllers/a1:controller" {
    description
      "This augment extends active nodes configuration";
    uses CONT-BODY;
  }
  augment "/a1:controllers/a1:controller-preconfigure" {
    description
      "This augment extends preconfigured nodes configuration";
    uses CONT-BODY;
  }
  augment "/a2:snmp-server/a2:traps" {
    description
      "This augment extends snmp-server traps nodes configuration";
    container fibrechannel {
      presence "Indicates a fibrechannel node is configured.";
      description
        "Enable SNMP Cisco fibrechannel traps";
    }
  }
}
