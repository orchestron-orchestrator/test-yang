submodule Cisco-IOS-XR-switch-oper-sub1 {
  belongs-to Cisco-IOS-XR-switch-oper {
    prefix Cisco-IOS-XR-switch-oper;
  }

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR switch package operational data.

     Copyright (c) 2013-2023 by Cisco Systems, Inc.
     All rights reserved.";

  revision 2023-09-27 {
    semver:module-version "1.1.0";
    description
      "Added an entry for unstable link alarm threshold to health state data";
  }
  revision 2020-08-13 {
    semver:module-version "1.0.0";
    description
      "Added an entry for show controller switch data-integrity errror";
  }
  revision 2020-07-16 {
    description
      "Added an entry for show controller switch debug counters";
  }
  revision 2020-06-30 {
    description
      "Added an entry for show controller switch events";
  }
  revision 2020-05-22 {
    description
      "Added an entry for show controller switch health state";
  }
  revision 2020-03-16 {
    description
      "Added an entry for show controller switch txq";
  }
  revision 2019-10-30 {
    description
      "Change class name VLANInfoLnstance to VLANInfoInstance";
  }
  revision 2019-04-05 {
    description
      "Establish semantic version baseline.";
  }
  revision 2019-03-08 {
    description
      "and entry for show controller switch bridge";
  }
  revision 2019-03-01 {
    description
      "Rename esdma-oper to switch-oper, esdma-emon-oper to emon-oper";
  }
  revision 2019-02-07 {
    description
      "Rework clear and set operations.";
  }
  revision 2019-01-30 {
    description
      "Schema rework to match the CLI.";
  }
  revision 2015-11-09 {
    description
      "IOS XR 6.0 revision.";
  }

  grouping ESDMA-SHOW-ETHSW-EVENT-DATA {
    description
      "ethernet switch event info";
    leaf id {
      type uint32;
      description
        "Identifier";
    }
    leaf name {
      type string {
        length "0..64";
      }
      description
        "Name";
    }
    leaf received {
      type uint32;
      description
        "Received";
    }
    leaf dropped {
      type uint32;
      description
        "Dropped";
    }
    leaf queued {
      type uint32;
      description
        "Queued";
    }
    leaf notified {
      type uint32;
      description
        "Notified";
    }
    leaf handled {
      type uint32;
      description
        "Handled";
    }
  }

  grouping ESDMA-SHOW-ETHSW-EVENTS-INFO {
    description
      "show ethernet switch events info";
    container ethsw-location-info {
      description
        "Ethernet Switch Location Info";
      uses ESDMA-SHOW-ETHSW-LOCATION-DATA;
    }
    leaf max-queued-events {
      type uint32;
      description
        "Max Queued Events";
    }
    leaf max-queued-events-time {
      type string {
        length "0..64";
      }
      description
        "Max Queued Events Time";
    }
    leaf total-received {
      type uint64;
      description
        "Total Received";
    }
    leaf total-dropped {
      type uint64;
      description
        "Total Dropped";
    }
    leaf total-queued {
      type uint64;
      description
        "Total Queued";
    }
    leaf total-notified {
      type uint64;
      description
        "Total Notified";
    }
    leaf total-handled {
      type uint64;
      description
        "Total Handled";
    }
    list ethsw-event-info {
      description
        "Ethernet switch event info";
      uses ESDMA-SHOW-ETHSW-EVENT-DATA;
    }
  }

  grouping ESDMA-SHOW-ETHSW-TXQ-STATISTICS-DETAILED-COLOR-DATA {
    description
      "ethernet switch tx queue statistics detailed
       color info";
    leaf color {
      type string {
        length "0..8";
      }
      description
        "Traffic class color";
    }
    leaf pass-packets {
      type uint64;
      description
        "Pass packets";
    }
    leaf pass-bytes {
      type uint64;
      units "byte";
      description
        "Pass bytes";
    }
    leaf drop-packets {
      type uint64;
      description
        "Drop packets";
    }
    leaf drop-bytes {
      type uint64;
      units "byte";
      description
        "Drop bytes";
    }
  }

  grouping ESDMA-SHOW-ETHSW-TXQ-STATISTICS-DETAILED-TRAFFIC-CLASS-DATA {
    description
      "ethernet switch tx queue statistics detailed
       traffic class info";
    leaf traffic-class {
      type string {
        length "0..4";
      }
      description
        "Traffic class";
    }
    list ethsw-txq-statistics-detailed-color-info {
      description
        "Ethernet switch Tx queue statistics detailed
         color info";
      uses ESDMA-SHOW-ETHSW-TXQ-STATISTICS-DETAILED-COLOR-DATA;
    }
  }

  grouping ESDMA-SHOW-ETHSW-TXQ-STATISTICS-DETAILED-PORT-DATA {
    description
      "ethernet switch tx queue statistics detailed port
       info";
    leaf port {
      type uint32;
      description
        "Port";
    }
    leaf traffic-class {
      type string {
        length "0..4";
      }
      description
        "Traffic class";
    }
    leaf traffic-class-color {
      type string {
        length "0..8";
      }
      description
        "Traffic class color";
    }
    leaf total-queued-packets {
      type uint64;
      description
        "Total queued packets";
    }
    leaf total-queued-bytes {
      type uint64;
      units "byte";
      description
        "Total queued bytes";
    }
    leaf total-drop-packets {
      type uint64;
      description
        "Total drop packets";
    }
    leaf total-drop-bytes {
      type uint64;
      units "byte";
      description
        "Total drop bytes";
    }
    list ethsw-txq-statistics-detailed-traffic-class-info {
      description
        "Ethernet switch Tx queue statistics detailed
         traffic class info";
      uses ESDMA-SHOW-ETHSW-TXQ-STATISTICS-DETAILED-TRAFFIC-CLASS-DATA;
    }
  }

  grouping ESDMA-SHOW-ETHSW-TXQ-STATISTICS-DETAILED-DATA {
    description
      "ethernet switch tx queue statistics detailed info";
    list ethsw-txq-statistics-detailed-port-info {
      description
        "Ethernet switch Tx queue statistics detailed
         port info";
      uses ESDMA-SHOW-ETHSW-TXQ-STATISTICS-DETAILED-PORT-DATA;
    }
  }

  grouping ESDMA-SHOW-ETHSW-TXQ-STATISTICS-SUMMARY-PORT-DATA {
    description
      "ethernet switch tx queue statistics summary port
       info";
    leaf port {
      type uint32;
      description
        "Port";
    }
    leaf traffic-class {
      type string {
        length "0..4";
      }
      description
        "Traffic class";
    }
    leaf traffic-class-color {
      type string {
        length "0..8";
      }
      description
        "Traffic class color";
    }
    leaf total-queued-packets {
      type uint64;
      description
        "Total queued packets";
    }
    leaf total-queued-bytes {
      type uint64;
      units "byte";
      description
        "Total queued bytes";
    }
    leaf total-drop-packets {
      type uint64;
      description
        "Total drop packets";
    }
    leaf total-drop-bytes {
      type uint64;
      units "byte";
      description
        "Total drop bytes";
    }
  }

  grouping ESDMA-SHOW-ETHSW-TXQ-STATISTICS-SUMMARY-DATA {
    description
      "ethernet switch tx queue statistics summary info";
    list ethsw-txq-statistics-summary-port-info {
      description
        "Ethernet switch Tx queue statistics summary port
         info";
      uses ESDMA-SHOW-ETHSW-TXQ-STATISTICS-SUMMARY-PORT-DATA;
    }
  }

  grouping ESDMA-SHOW-ETHSW-TXQ-CONFIGURATION-PORT-DATA {
    description
      "ethernet switch tx queue configuration port info";
    leaf port {
      type uint32;
      description
        "Port";
    }
    leaf config-drop-profile {
      type uint32;
      description
        "Configured drop profile";
    }
    leaf config-scheduler-profile {
      type uint32;
      description
        "Configured scheduler profile";
    }
  }

  grouping ESDMA-SHOW-ETHSW-TXQ-CONFIGURATION-PROFILE-PER-TRAFFIC-CLASS-DATA {
    description
      "ethernet switch tx queue configuration profile
       per traffic class info";
    leaf traffic-class {
      type uint32;
      description
        "Traffic class";
    }
    leaf arbitration-group {
      type string {
        length "0..8";
      }
      description
        "Traffic arbitration group";
    }
    leaf weighted-round-robin-weight {
      type uint32;
      description
        "Weighted round robin weight";
    }
    leaf sharing {
      type string {
        length "0..8";
      }
      description
        "Traffic class sharing";
    }
    leaf drop-profile0-max-buffers {
      type uint32;
      description
        "Drop profile 0 max buffers";
    }
    leaf drop-profile1-max-buffers {
      type uint32;
      description
        "Drop profile 1 max buffers";
    }
    leaf drop-profile2-max-buffers {
      type uint32;
      description
        "Drop profile 2 max buffers";
    }
    leaf drop-profile0-max-traffic-descriptors {
      type uint32;
      description
        "Drop profile 0 max traffic descriptors";
    }
    leaf drop-profile1-max-traffic-descriptors {
      type uint32;
      description
        "Drop profile 1 max traffic descriptors";
    }
    leaf drop-profile2-max-traffic-descriptors {
      type uint32;
      description
        "Drop profile 2 max traffic descriptors";
    }
    leaf traffic-class-max-buffers {
      type uint32;
      description
        "Traffic class max buffers";
    }
    leaf traffic-class-max-traffic-descriptors {
      type uint32;
      description
        "Traffic class max traffic descriptors";
    }
  }

  grouping ESDMA-SHOW-ETHSW-TXQ-CONFIGURATION-PROFILE-DATA {
    description
      "ethernet switch tx queue configuration profile
       info";
    leaf id {
      type uint32;
      description
        "Id";
    }
    leaf sharing {
      type string {
        length "0..8";
      }
      description
        "Profile sharing";
    }
    leaf max-buffers {
      type uint32;
      description
        "Max buffers";
    }
    leaf max-traffic-descriptors {
      type uint32;
      description
        "Max traffic descriptors";
    }
    list ethsw-txq-configuration-profile-per-traffic-class-info {
      description
        "Ethernet switch Tx queue configured profile per
         traffic class info";
      uses ESDMA-SHOW-ETHSW-TXQ-CONFIGURATION-PROFILE-PER-TRAFFIC-CLASS-DATA;
    }
  }

  grouping ESDMA-SHOW-ETHSW-TXQ-CONFIGURATION-GLOBAL-DATA {
    description
      "ethernet switch tx queue configuration global
       info";
    leaf global-traffic-descriptors {
      type uint32;
      description
        "Global traffic descriptors";
    }
    leaf global-buffers {
      type uint32;
      description
        "Global buffers";
    }
    leaf shared-pool0-traffic-descriptors {
      type uint32;
      description
        "Shared pool 0 traffic descriptors";
    }
    leaf shared-pool0-buffers {
      type uint32;
      description
        "Shared pool 0 buffers";
    }
    leaf multi-target-traffic-descriptors {
      type uint32;
      description
        "Multi target traffic descriptors";
    }
    leaf multi-target-buffers {
      type uint32;
      description
        "Multi target buffers";
    }
    leaf sniffed-ingress-traffic-descriptors {
      type uint32;
      description
        "Sniffed ingress traffic descriptors";
    }
    leaf sniffed-ingress-buffers {
      type uint32;
      description
        "Sniffed ingress buffers";
    }
    leaf sniffed-egress-traffic-descriptors {
      type uint32;
      description
        "Sniffed egress traffic descriptors";
    }
    leaf sniffed-egress-buffers {
      type uint32;
      description
        "Sniffed egress buffers";
    }
    leaf weighted-round-robin-schedule-mode {
      type string {
        length "0..12";
      }
      description
        "Weighted round robin schedule mode";
    }
    leaf weighted-round-robin-schedule-mtu {
      type string {
        length "0..8";
      }
      description
        "Weighted round robin Schedule mtu";
    }
  }

  grouping ESDMA-SHOW-ETHSW-TXQ-CONFIGURATION-DATA {
    description
      "ethernet switch tx queue configuration info";
    list ethsw-txq-configuration-global-info {
      description
        "Ethernet switch Tx queue configured global info";
      uses ESDMA-SHOW-ETHSW-TXQ-CONFIGURATION-GLOBAL-DATA;
    }
    list ethsw-txq-configuration-profile-info {
      description
        "Ethernet switch Tx queue configured profile info";
      uses ESDMA-SHOW-ETHSW-TXQ-CONFIGURATION-PROFILE-DATA;
    }
    list ethsw-txq-configuration-port-info {
      description
        "Ethernet switch Tx queue configured port info";
      uses ESDMA-SHOW-ETHSW-TXQ-CONFIGURATION-PORT-DATA;
    }
  }

  grouping ESDMA-SHOW-ETHSW-TXQ-INFO {
    description
      "show ethernet switch txq info";
    container ethsw-location-info {
      description
        "Ethernet switch location info";
      uses ESDMA-SHOW-ETHSW-LOCATION-DATA;
    }
    leaf initial-configuration {
      type string {
        length "0..64";
      }
      description
        "Disabled";
    }
    list ethsw-txq-configuration-info {
      description
        "Ethernet switch Tx queue config info";
      uses ESDMA-SHOW-ETHSW-TXQ-CONFIGURATION-DATA;
    }
    list ethsw-txq-statistics-summary-info {
      description
        "Ethernet switch Tx queue statistics summary info";
      uses ESDMA-SHOW-ETHSW-TXQ-STATISTICS-SUMMARY-DATA;
    }
    list ethsw-txq-statistics-detailed-info {
      description
        "Ethernet switch Tx queue statistics detailed
         info";
      uses ESDMA-SHOW-ETHSW-TXQ-STATISTICS-DETAILED-DATA;
    }
  }

  grouping ESDMA-SHOW-ETHSW-VLAN-MEMBERSHIP-DATA {
    description
      "show ethernet switch vlan membership info";
    leaf vlan {
      type uint32;
      description
        "Vlan number";
    }
    leaf-list ports {
      type uint8;
      description
        "Port number";
    }
  }

  grouping ESDMA-SHOW-ETHSW-VLANMEMBERSHIP-INFO {
    description
      "show ethernet switch VLAN port membership";
    container ethsw-location-info {
      description
        "Ethernet switch location info";
      uses ESDMA-SHOW-ETHSW-LOCATION-DATA;
    }
    list ethsw-vlan-memb-info {
      description
        "Ethernet switch vlan membership info";
      uses ESDMA-SHOW-ETHSW-VLAN-MEMBERSHIP-DATA;
    }
  }

  grouping ESDMA-SHOW-ETHSW-VLAN-DATA {
    description
      "show ethernet switch vlan info";
    leaf vlan {
      type uint32;
      description
        "Vlan number";
    }
    leaf vlan-use {
      type string {
        length "0..64";
      }
      description
        "Vlan use";
    }
  }

  grouping ESDMA-SHOW-ETHSW-VLANINFO-INFO {
    description
      "show ethernet switch VLAN info";
    container ethsw-location-info {
      description
        "Ethernet switch location info";
      uses ESDMA-SHOW-ETHSW-LOCATION-DATA;
    }
    list ethsw-vlan-info {
      description
        "Ethernet switch vlan info";
      uses ESDMA-SHOW-ETHSW-VLAN-DATA;
    }
  }

  grouping ESDMA-SHOW-ETHSW-DETAILED-STATISTICS-DATA {
    description
      "show ethernet switch detailed statistics info";
    leaf port {
      type uint8;
      description
        "Port number";
    }
    leaf port-state {
      type string {
        length "0..8";
      }
      description
        "Port state";
    }
    leaf port-speed {
      type string {
        length "0..8";
      }
      description
        "Port speed";
    }
    leaf connects-to {
      type string {
        length "0..64";
      }
      description
        "Connects to";
    }
    leaf rx-unicast-packets {
      type uint64;
      description
        "Rx unicast packets";
    }
    leaf rx-multicast-packets {
      type uint64;
      description
        "Rx multicast packets";
    }
    leaf rx-broadcast-packets {
      type uint64;
      description
        "Rx broadcast packets";
    }
    leaf rx-flow-control {
      type uint64;
      description
        "Rx flow control";
    }
    leaf rx-good-octets {
      type uint64;
      description
        "Rx good octets";
    }
    leaf rx-bad-octets {
      type uint64;
      description
        "Rx bad octets";
    }
    leaf rx-fifo-overrun {
      type uint64;
      description
        "Rx FIFO overrun";
    }
    leaf rx-undersize {
      type uint64;
      description
        "Rx undersize";
    }
    leaf rx-fragments {
      type uint64;
      description
        "Rx fragments";
    }
    leaf rx-oversize {
      type uint64;
      description
        "Rx oversize";
    }
    leaf rx-jabber {
      type uint64;
      description
        "Rx jabber";
    }
    leaf rx-errors {
      type uint64;
      description
        "Rx errors";
    }
    leaf rx-bad-crc {
      type uint64;
      description
        "Rx bad CRC";
    }
    leaf rx-collisons {
      type uint64;
      description
        "Rx collisopns";
    }
    leaf rx-policing-drops {
      type uint64;
      description
        "Rx policing drops";
    }
    leaf tx-unitcast-packets {
      type uint64;
      description
        "Tx unicast packets";
    }
    leaf tx-multicast-packets {
      type uint64;
      description
        "Tx multicast packets";
    }
    leaf tx-broadcast-packets {
      type uint64;
      description
        "Tx broadcast packets";
    }
    leaf txflow-control {
      type uint64;
      description
        "Tx flow control";
    }
    leaf tx-good-octets {
      type uint64;
      description
        "Tx good octets";
    }
    leaf tx-deferred {
      type uint64;
      description
        "Tx deferred packets";
    }
    leaf tx-fifo-unrun {
      type uint64;
      description
        "Tx FIFO underrun/CRC";
    }
    leaf tx-multi-collision {
      type uint64;
      description
        "Tx Multiple collisions";
    }
    leaf tx-excess-collision {
      type uint64;
      description
        "Tx excess collisions";
    }
    leaf tx-late-collisions {
      type uint64;
      description
        "Tx late collisions";
    }
    leaf tx-policing-drops {
      type uint64;
      description
        "Tx policing drops";
    }
    leaf tx-queue-drops {
      type uint64;
      description
        "Tx queueing drops";
    }
    leaf rx-tx-packets-64 {
      type uint64;
      description
        "RxTx Packets 64";
    }
    leaf rx-tx-packets-65-127 {
      type uint64;
      description
        "RxTx Packets 65 to 127";
    }
    leaf rx-tx-packets-128-255 {
      type uint64;
      description
        "RxTx Packets 128 to 255";
    }
    leaf rx-tx-packets-256-511 {
      type uint64;
      description
        "RxTx Packets 256 to 511";
    }
    leaf rx-tx-packets-512-1023 {
      type uint64;
      description
        "RxTx Packets 512 1023";
    }
    leaf rx-tx-packets-1024-max {
      type uint64;
      description
        "RxTx Packets 1024 to max.";
    }
  }

  grouping ESDMA-SHOW-ETHSW-SUMMARY-STATISTICS-DATA {
    description
      "show ethernet switch summary statistics info";
    leaf port {
      type uint8;
      description
        "Port number";
    }
    leaf port-state {
      type string {
        length "0..8";
      }
      description
        "Port state";
    }
    leaf port-state-changes {
      type uint32;
      description
        "Port state changes";
    }
    leaf tx-packets {
      type uint64;
      description
        "Tx packets";
    }
    leaf rx-packets {
      type uint64;
      description
        "Rx packets";
    }
    leaf tx-drops-errors {
      type uint64;
      description
        "Tx drops errors";
    }
    leaf rx-drops-errors {
      type uint64;
      description
        "Rx drops errors";
    }
    leaf connects-to {
      type string {
        length "0..64";
      }
      description
        "Connects to";
    }
  }

  grouping ESDMA-SHOW-ETHSW-STATISTICS-INFO {
    description
      "show ethernet switch statistics info";
    container ethsw-location-info {
      description
        "Ethernet switch location info";
      uses ESDMA-SHOW-ETHSW-LOCATION-DATA;
    }
    list ethsw-summary-stat-info {
      description
        "Ethernet switch summary statistics info";
      uses ESDMA-SHOW-ETHSW-SUMMARY-STATISTICS-DATA;
    }
    list ethsw-detailed-stat-info {
      description
        "Ethernet switch detailed statistics info";
      uses ESDMA-SHOW-ETHSW-DETAILED-STATISTICS-DATA;
    }
  }

  grouping ESDMA-SHOW-ETHSW-POLICING-PORT-DATA {
    description
      "ethernet switch policing port data";
    leaf policing-port {
      type string {
        length "0..64";
      }
      description
        "Policing Port";
    }
    leaf policing-port-speed {
      type string {
        length "0..64";
      }
      description
        "Policing Port Speed";
    }
    leaf policing-id {
      type uint32;
      description
        "Policing Id";
    }
    leaf policing-dir {
      type string {
        length "0..8";
      }
      description
        "Policing Direction";
    }
    leaf policing-count-only {
      type string {
        length "0..8";
      }
      description
        "Policing Count Only";
    }
    leaf policing-vid {
      type uint32;
      description
        "Policing VID";
    }
    leaf policing-vid-mask {
      type uint32;
      description
        "Policing VID Mask";
    }
    leaf policing-up {
      type uint32;
      description
        "Policing Up";
    }
    leaf policing-up-mask {
      type uint32;
      description
        "Policing Up Mask";
    }
    leaf policing-config-cir {
      type uint64;
      description
        "Policing Config CIR";
    }
    leaf policing-config-cir-pcnt {
      type uint32;
      units "percentage";
      description
        "Policing Config CIR Percent";
    }
    leaf policing-config-pir {
      type uint64;
      description
        "Policing Config PIR";
    }
    leaf policing-config-pir-pcnt {
      type uint32;
      units "percentage";
      description
        "Policing Config PIR Percent";
    }
    leaf policing-config-cbs {
      type uint64;
      description
        "Policing Config CBS";
    }
    leaf policing-config-pbs {
      type uint64;
      description
        "Policing Config PBS";
    }
    leaf policing-stats-total {
      type uint64;
      description
        "Policing Stats Total";
    }
    leaf policing-stats-green {
      type uint64;
      description
        "Policing Stats Green";
    }
    leaf policing-stats-yellow {
      type uint64;
      description
        "Policing Stats Yellow";
    }
    leaf policing-stats-red {
      type uint64;
      description
        "Policing Stats Red";
    }
    leaf policing-desc {
      type string {
        length "0..64";
      }
      description
        "Policing Description";
    }
  }

  grouping ESDMA-SHOW-ETHSW-POLICING-INFO {
    description
      "show ethernet switch policing info";
    container ethsw-location-info {
      description
        "Ethernet switch location info";
      uses ESDMA-SHOW-ETHSW-LOCATION-DATA;
    }
    leaf policing-config-ingress0 {
      type string {
        length "0..32";
      }
      description
        "Policing Config Ingress 0";
    }
    leaf policing-config-ingress0-mru {
      type uint32;
      description
        "Policing Config Ingress 0 MRU";
    }
    leaf policing-config-ingress1 {
      type string {
        length "0..32";
      }
      description
        "Policing Config Ingress 1";
    }
    leaf policing-config-ingress1-mru {
      type uint32;
      description
        "Policing Config Ingress 1 MRU";
    }
    leaf policing-config-egress {
      type string {
        length "0..32";
      }
      description
        "Policing Config Egress";
    }
    leaf policing-config-egress-mru {
      type uint32;
      description
        "Policing Config Egress MRU";
    }
    list ethsw-policing-port-data {
      description
        "Ethernet switch policing port data";
      uses ESDMA-SHOW-ETHSW-POLICING-PORT-DATA;
    }
  }

  grouping ESDMA-SHOW-ETHSW-ALL-INFO {
    description
      "show ethernet switch";
    container ethsw-trunk {
      description
        "Ethernet switch trunk info";
      uses ESDMA-SHOW-ETHSW-TRUNK-INFO;
    }
    container ethsw-bridge {
      description
        "Ethernet switch bridge info";
      uses ESDMA-SHOW-ETHSW-BRIDGE-INFO;
    }
    container ethsw-summay {
      description
        "Ethernet switch summary info";
      uses ESDMA-SHOW-ETHSW-SUMMARY-INFO;
    }
    container ethsw-fdb {
      description
        "Ethernet switch FDB info";
      uses ESDMA-SHOW-ETHSW-FDB-INFO;
    }
    container ethsw-policing {
      description
        "Ethernet switch policing info";
      uses ESDMA-SHOW-ETHSW-POLICING-INFO;
    }
    container ethsw-statistics {
      description
        "Ethernet switch statistics info";
      uses ESDMA-SHOW-ETHSW-STATISTICS-INFO;
    }
    container ethsw-vlan-ifo {
      description
        "Ethernet switch VLAN info";
      uses ESDMA-SHOW-ETHSW-VLANINFO-INFO;
    }
    container ethsw-vlan-membership {
      description
        "Ethernet switch VLAN membership info";
      uses ESDMA-SHOW-ETHSW-VLANMEMBERSHIP-INFO;
    }
    container ethsw-serdes {
      description
        "Ethernet switch SERDES info";
      uses ESDMA-SHOW-ETHSW-REGISTER-INFO;
    }
    container ethsw-mac {
      description
        "Ethernet switch MAC info";
      uses ESDMA-SHOW-ETHSW-REGISTER-INFO;
    }
    container ethsw-txq {
      description
        "Ethernet switch Tx queue info";
      uses ESDMA-SHOW-ETHSW-TXQ-INFO;
    }
    container ethsw-health-state {
      description
        "Ethernet switch health state info";
      uses ESDMA-SHOW-ETHSW-HEALTH-STATE-INFO;
    }
    container ethsw-events {
      description
        "Ethernet switch events info";
      uses ESDMA-SHOW-ETHSW-EVENTS-INFO;
    }
    container ethsw-debug-counters {
      description
        "Ethernet switch debug counters info";
      uses ESDMA-SHOW-ETHSW-DEBUG-COUNTERS-INFO;
    }
    container ethsw-data-integrity-error {
      description
        "Ethernet switch data integrity error info";
      uses ESDMA-SHOW-ETHSW-DATA-INTEGRITY-ERROR-INFO;
    }
  }

  grouping ESDMA-SHOW-ETHSW-SUMMARY-DATA {
    description
      "show ethernet switch summary info";
    leaf port {
      type uint8;
      description
        "Port number";
    }
    leaf port-state {
      type string {
        length "0..8";
      }
      description
        "Port state";
    }
    leaf port-admin-state {
      type string {
        length "0..8";
      }
      description
        "Port admin state";
    }
    leaf port-speed {
      type string {
        length "0..8";
      }
      description
        "Port speed";
    }
    leaf port-protocol-state {
      type string {
        length "0..8";
      }
      description
        "Port protocol state";
    }
    leaf port-forwarding {
      type string {
        length "0..16";
      }
      description
        "Port is forwarding";
    }
    leaf connects-to {
      type string {
        length "0..64";
      }
      description
        "Connects to";
    }
  }

  grouping ESDMA-SHOW-ETHSW-SUMMARY-INFO {
    description
      "show ethernet switch summary info";
    container ethsw-location-info {
      description
        "Ethernet switch location info";
      uses ESDMA-SHOW-ETHSW-LOCATION-DATA;
    }
    list ethsw-sum-info {
      description
        "Ethernet switch summary info";
      uses ESDMA-SHOW-ETHSW-SUMMARY-DATA;
    }
  }

  grouping ESDMA-SHOW-ETHSW-TRUNK-DATA {
    description
      "show ethernet switch trunk info";
    leaf port {
      type uint8;
      description
        "Port number";
    }
    leaf port-status {
      type uint8;
      description
        "Port status";
    }
  }

  grouping ESDMA-SHOW-ETHSW-TRUNK-INFO {
    description
      "show ethernet switch trunk info";
    container ethsw-location-info {
      description
        "Ethernet switch location info";
      uses ESDMA-SHOW-ETHSW-LOCATION-DATA;
    }
    leaf member-count {
      type uint8;
      description
        "Member count";
    }
    leaf trunk-name {
      type string {
        length "0..64";
      }
      description
        "Trunk name";
    }
    list ethsw-trunk-info {
      description
        "Ethernet switch trunk info";
      uses ESDMA-SHOW-ETHSW-TRUNK-DATA;
    }
  }

  grouping ESDMA-SHOW-ETHSW-HEALTH-STATE-HISTORY-ENTRY-DATA {
    description
      "ethernet switch health state history entry info";
    leaf instance {
      type uint32;
      description
        "Instance";
    }
    leaf type {
      type string {
        length "0..8";
      }
      description
        "Type";
    }
    leaf new-state {
      type string {
        length "0..64";
      }
      description
        "New state";
    }
    leaf fault {
      type string {
        length "0..64";
      }
      description
        "Fault";
    }
    leaf epoch {
      type string {
        length "0..64";
      }
      description
        "Epoch time";
    }
  }

  grouping ESDMA-SHOW-ETHSW-HEALTH-STATE-PARTNER-DATA {
    description
      "ethernet switch health state partner info";
    leaf card-type {
      type uint32;
      description
        "Card type";
    }
    leaf logical-slot {
      type uint32;
      description
        "Logical slot";
    }
    leaf present {
      type uint32;
      description
        "Present";
    }
    leaf active {
      type uint32;
      description
        "Active";
    }
    leaf epoch {
      type string {
        length "0..64";
      }
      description
        "Epoch time";
    }
    leaf card-name {
      type string {
        length "0..16";
      }
      description
        "Card name";
    }
  }

  grouping ESDMA-SHOW-ETHSW-HEALTH-STATE-PARTNER-ACTIVE-DATA {
    description
      "ethernet switch health state partner active info";
    leaf card-type {
      type uint32;
      description
        "Card type";
    }
    leaf logical-slot {
      type uint32;
      description
        "Logical slot";
    }
  }

  grouping ESDMA-SHOW-ETHSW-HEALTH-STATE-DETAILED-STATE-DATA {
    description
      "ethernet switch health state link state info";
    leaf state {
      type string {
        length "0..16";
      }
      description
        "State";
    }
    leaf fault {
      type string {
        length "0..64";
      }
      description
        "Fault";
    }
    leaf epoch {
      type string {
        length "0..64";
      }
      description
        "Epoch time";
    }
    leaf count {
      type uint32;
      description
        "Count";
    }
  }

  grouping ESDMA-SHOW-ETHSW-HEALTH-STATE-PORT-DATA {
    description
      "ethernet switch health state port info";
    leaf port {
      type uint32;
      description
        "Port";
    }
    leaf port-name {
      type string {
        length "0..64";
      }
      description
        "Port name";
    }
    leaf polling-mode {
      type string {
        length "0..16";
      }
      description
        "Polling mode";
    }
    leaf polling-count {
      type uint32;
      description
        "Polling count";
    }
    leaf polling-interval-ms {
      type uint32;
      description
        "Polling interval in milli second";
    }
    leaf monitor-mode {
      type string {
        length "0..16";
      }
      description
        "Monitor mode";
    }
    leaf monitor-enabled {
      type string {
        length "0..16";
      }
      description
        "Monitor enabled";
    }
    leaf recovery-mode {
      type string {
        length "0..64";
      }
      description
        "Recovery mode";
    }
    leaf recovery-enabled {
      type string {
        length "0..64";
      }
      description
        "Recovery enabled";
    }
    leaf recovery-attempts {
      type uint32;
      description
        "Recovery attempts";
    }
    leaf unstable-link-threshold {
      type uint32;
      description
        "Unstable link threshold";
    }
    list ethsw-health-state-link-state-info {
      description
        "Ethernet switch health state link state info";
      uses ESDMA-SHOW-ETHSW-HEALTH-STATE-DETAILED-STATE-DATA;
    }
    list ethsw-health-state-sync-state-info {
      description
        "Ethernet switch health state sync state info";
      uses ESDMA-SHOW-ETHSW-HEALTH-STATE-DETAILED-STATE-DATA;
    }
    list ethsw-health-state-admin-state-info {
      description
        "Ethernet switch health state admin state info";
      uses ESDMA-SHOW-ETHSW-HEALTH-STATE-DETAILED-STATE-DATA;
    }
    list ethsw-health-state-phy-sync-state-info {
      description
        "Ethernet switch health state phy sync state info";
      uses ESDMA-SHOW-ETHSW-HEALTH-STATE-DETAILED-STATE-DATA;
    }
    list ethsw-health-state-health-state-info {
      description
        "Ethernet switch health state's health status
         info";
      uses ESDMA-SHOW-ETHSW-HEALTH-STATE-DETAILED-STATE-DATA;
    }
    list ethsw-health-state-partner-state-info {
      description
        "Ethernet switch health state partner state info";
      uses ESDMA-SHOW-ETHSW-HEALTH-STATE-DETAILED-STATE-DATA;
    }
    list ethsw-health-state-partner-active-info {
      description
        "Ethernet switch health state partner active info";
      uses ESDMA-SHOW-ETHSW-HEALTH-STATE-PARTNER-ACTIVE-DATA;
    }
    list ethsw-health-state-partner-info {
      description
        "Ethernet switch health state partner info";
      uses ESDMA-SHOW-ETHSW-HEALTH-STATE-PARTNER-DATA;
    }
    list ethsw-health-state-history-entry-info {
      description
        "Ethernet switch health state history entry info";
      uses ESDMA-SHOW-ETHSW-HEALTH-STATE-HISTORY-ENTRY-DATA;
    }
  }

  grouping ESDMA-SHOW-ETHSW-HEALTH-STATE-INFO {
    description
      "show ethernet switch health state info";
    container ethsw-location-info {
      description
        "Ethernet switch location info";
      uses ESDMA-SHOW-ETHSW-LOCATION-DATA;
    }
    list ethsw-health-state-port-info {
      description
        "Ethernet switch health state port info";
      uses ESDMA-SHOW-ETHSW-HEALTH-STATE-PORT-DATA;
    }
  }

  grouping ESDMA-SHOW-ETHSW-DEBUG-COUNTERS-CORE-STATISTICS-DATA {
    description
      "ethernet switch debug counters core statistics
       info";
    leaf core {
      type uint32;
      description
        "Core";
    }
    leaf msi-count {
      type uint64;
      description
        "MSI count";
    }
    leaf aer-count {
      type uint64;
      description
        "AER count";
    }
    leaf hotplug-count {
      type uint64;
      description
        "Hotplug count";
    }
    leaf watchdog-count {
      type uint64;
      description
        "Watchdog count";
    }
    leaf task-lock-longest-wait-time {
      type uint64;
      description
        "Task lock longest wait time";
    }
    leaf task-lock-longest-held-time {
      type uint64;
      description
        "Task lock longest held time";
    }
    leaf task-unlock-longest-wait-time {
      type uint64;
      description
        "Task unlock longest wait time";
    }
  }

  grouping ESDMA-SHOW-ETHSW-DEBUG-COUNTERS-INFO {
    description
      "show ethernet switch debug counters info";
    container ethsw-location-info {
      description
        "Ethernet switch location info";
      uses ESDMA-SHOW-ETHSW-LOCATION-DATA;
    }
    leaf tx-thread-watchdog-count {
      type uint64;
      description
        "Tx thread watchdog count";
    }
    leaf rx-thread-watchdog-count {
      type uint64;
      description
        "Rx thread watchdog count";
    }
    leaf task-lock-longest-wait-time {
      type uint64;
      description
        "Task lock longest wait time";
    }
    leaf task-lock-longest-wait-event {
      type uint32;
      description
        "Task lock longest wait event";
    }
    leaf task-lock-longest-held-time {
      type uint64;
      description
        "Task lock longest held time";
    }
    leaf task-lock-longest-held-event {
      type uint32;
      description
        "Task lock longest held event";
    }
    leaf task-unlock-longest-wait-time {
      type uint64;
      description
        "Task unlock longest wait time";
    }
    leaf task-unlock-longest-wait-event {
      type uint32;
      description
        "Task unlock longest wait event";
    }
    leaf dma-health-checks {
      type string {
        length "0..16";
      }
      description
        "DMA health checks status";
    }
    leaf dma-max-rx-packets-dequeued-per-interrupt {
      type uint64;
      description
        "DMA max Rx packets dequeued per interrupt";
    }
    leaf dma-rx-packets-dequeued {
      type uint64;
      description
        "DMA Rx packets dequeued";
    }
    leaf dma-rx-packet-dequeue-errors {
      type uint64;
      description
        "DMA Rx packet dequeue errors";
    }
    leaf dma-tx-packets-queued {
      type uint64;
      description
        "DMA Tx packets queued";
    }
    leaf dma-tx-packets-completed {
      type uint64;
      description
        "DMA Tx packets completed";
    }
    leaf dma-tx-packet-no-message-errors {
      type uint64;
      description
        "DMA Tx packet no message errors";
    }
    leaf dma-tx-packet-message-too-big-errors {
      type uint64;
      description
        "DMA Tx packet message too big errors";
    }
    leaf dma-tx-packet-no-buffer-errors {
      type uint64;
      description
        "DMA Tx packet no buffer errors";
    }
    leaf dma-tx-packet-queue-errors {
      type uint64;
      description
        "DMA Tx packet queue errors";
    }
    leaf dma-tx-packet-completion-errors {
      type uint64;
      description
        "DMA Tx packet completion errors";
    }
    leaf dma-max-tx-packets-freed-per-interrupt {
      type uint64;
      description
        "DMA max Tx packets freed per interrupt";
    }
    leaf dma-tx-buffer-allocation-count {
      type uint64;
      description
        "DMA Tx buffer allocation count";
    }
    leaf dma-tx-buffer-free-count {
      type uint64;
      description
        "DMA Tx buffer free count";
    }
    list ethsw-debug-counters-core-statistics-info {
      description
        "Ethernet switch debug counters core statistics
         info";
      uses ESDMA-SHOW-ETHSW-DEBUG-COUNTERS-CORE-STATISTICS-DATA;
    }
  }

  grouping ESDMA-SHOW-ETHSW-BRIDGE-EGRESS-DATA {
    description
      "ethernet switch bridge egress info";
    leaf entry-number {
      type uint8;
      description
        "Entry number";
    }
    leaf egress-port-vlan-tc-dp {
      type string {
        length "0..32";
      }
      description
        "Egress port, vlan, TC and DP";
    }
    leaf egress-unicast-frames {
      type uint64;
      description
        "Egress unicast frames";
    }
    leaf egress-multicast-frames {
      type uint64;
      description
        "Egress multicast frames";
    }
    leaf egress-broadcast-frames {
      type uint64;
      description
        "Egress broadcast frames";
    }
    leaf egress-discarded-frames {
      type uint64;
      description
        "Egress discarded frames";
    }
    leaf egress-transmit-q-cong {
      type uint64;
      description
        "Egress transmit q congestion";
    }
    leaf egress-control-packets {
      type uint64;
      description
        "Egress control packats";
    }
    leaf egress-other-drops {
      type uint64;
      description
        "Egress other drops";
    }
  }

  grouping ESDMA-SHOW-ETHSW-BRIDGE-INGRESS-DATA {
    description
      "ethernet switch bridge ingress info";
    leaf entry-number {
      type uint8;
      description
        "Entry number";
    }
    leaf ingress-port-vlan {
      type string {
        length "0..32";
      }
      description
        "Ingress port and vlan";
    }
    leaf ingress-frames {
      type uint64;
      description
        "Ingress frames";
    }
    leaf ingress-vlan-discards {
      type uint64;
      description
        "Ingress vlan discards";
    }
    leaf ingress-sec-discards {
      type uint64;
      description
        "Ingress security discards";
    }
    leaf ingress-other-discards {
      type uint64;
      description
        "Ingress other discards";
    }
  }

  grouping ESDMA-SHOW-ETHSW-BRIDGE-INFO {
    description
      "show ethernet switch bridge info";
    container ethsw-location-info {
      description
        "Ethernet switch location info";
      uses ESDMA-SHOW-ETHSW-LOCATION-DATA;
    }
    list ethsw-bridge-ingress-info {
      description
        "Ethernet switch bridge ingress info";
      uses ESDMA-SHOW-ETHSW-BRIDGE-INGRESS-DATA;
    }
    list ethsw-bridge-egress-info {
      description
        "Ethernet switch bridge egress info";
      uses ESDMA-SHOW-ETHSW-BRIDGE-EGRESS-DATA;
    }
  }

  grouping ESDMA-SHOW-ETHSW-FDB-CORE-DATA {
    description
      "ethernet switch fdb core info";
    leaf fdb-instance {
      type string {
        length "0..32";
      }
      description
        "Fdb Instance";
    }
    leaf fdb-entries {
      type uint32;
      description
        "Total entries";
    }
    leaf fdb-static-entries {
      type uint32;
      description
        "Static entries";
    }
  }

  grouping ESDMA-SHOW-ETHSW-FDB-STATISTICS-DATA {
    description
      "ethernet switch fdb statistics info";
    leaf fdb-shadow-entries {
      type uint32;
      description
        "Current shadow table entries";
    }
    leaf fdb-max-shadow-entries {
      type uint32;
      description
        "Maximum shadow table entries";
    }
    leaf fdb-max-hash-chain {
      type uint32;
      description
        "Maximum hash chain depth";
    }
    leaf fdb-entries-added {
      type uint32;
      description
        "Number of entries added";
    }
    leaf fdb-entries-deleted {
      type uint32;
      description
        "Number of entries deleted";
    }
    leaf fdb-entries-updated {
      type uint32;
      description
        "Number of entries updated";
    }
    leaf fdb-flushed {
      type uint32;
      description
        "Number of FDB flushes";
    }
    leaf fdb-address-updates {
      type uint32;
      description
        "Address update messages";
    }
    leaf fdb-new-address {
      type uint32;
      description
        "New addresses";
    }
    leaf fdb-aged-updates {
      type uint32;
      description
        "Aged addresses";
    }
    leaf fdb-transplant-updates {
      type uint32;
      description
        "Transplanted updates";
    }
    leaf fdb-forwarding-updates {
      type uint32;
      description
        "Forwarding updates";
    }
    leaf fdb-addr-insert-errors {
      type uint32;
      description
        "Address insert errors";
    }
    leaf fdb-addr-update-errors {
      type uint32;
      description
        "Address update errors";
    }
    leaf fdbmemory-errors {
      type uint32;
      description
        "FDB memory errors";
    }
    leaf fdb-allocation-errors {
      type uint32;
      description
        "FDB allocation errors";
    }
    leaf fdb-addr-updates-q {
      type uint32;
      description
        "Address updates queued";
    }
    leaf fdb-addr-q-full {
      type string {
        length "0..32";
      }
      description
        "Address queue full";
    }
    leaf fdbforwarding-updates-qed {
      type uint32;
      description
        "Forwarding updates queued";
    }
    leaf fdb-forwarding-q-full {
      type string {
        length "0..32";
      }
      description
        "Forwarding queue full";
    }
  }

  grouping ESDMA-SHOW-ETHSW-FDB-DATA {
    description
      "ethernet switch fdb info";
    leaf fdb-mac-addr {
      type string {
        length "0..32";
      }
      description
        "Fdb MAC address";
    }
    leaf fdb-vlan {
      type uint32;
      description
        "Fdb VLAN";
    }
    leaf fdb-port {
      type string {
        length "0..32";
      }
      description
        "Fdb port";
    }
    leaf fdb-trap-entry {
      type string {
        length "0..32";
      }
      description
        "Fdb trap entry";
    }
    leaf fdb-static-entry {
      type string {
        length "0..32";
      }
      description
        "Fdb static entry";
    }
    leaf fdb-synced-cores {
      type uint32;
      description
        "Fdb synced cores";
    }
    leaf fdb-index {
      type uint32;
      description
        "Fdb index";
    }
  }

  grouping ESDMA-SHOW-ETHSW-FDB-INFO {
    description
      "show ethernet switch forwarding data base info";
    container ethsw-location-info {
      description
        "Ethernet switch location info";
      uses ESDMA-SHOW-ETHSW-LOCATION-DATA;
    }
    leaf has-trunk-entry {
      type string {
        length "0..32";
      }
      description
        "Has trunk entry";
    }
    leaf trunk-entry-message {
      type string {
        length "0..256";
      }
      description
        "Trunk entry message";
    }
    list ethsw-fdb-info {
      description
        "Ethernet switch FDB info";
      uses ESDMA-SHOW-ETHSW-FDB-DATA;
    }
    list ethsw-fdb-statistic {
      description
        "Ethernet switch FDB statistics info";
      uses ESDMA-SHOW-ETHSW-FDB-STATISTICS-DATA;
    }
    list ethsw-fdb-core-info {
      description
        "Ethernet switch FDB core info";
      uses ESDMA-SHOW-ETHSW-FDB-CORE-DATA;
    }
  }

  grouping ESDMA-SHOW-ETHSW-REGISTER-DATA {
    description
      "ethernet switch register data";
    leaf base-reg {
      type string {
        length "0..16";
      }
      description
        "Register address";
    }
    leaf description {
      type string {
        length "0..64";
      }
      description
        "Register description";
    }
    leaf value {
      type string {
        length "0..16";
      }
      description
        "Register value";
    }
  }

  grouping ESDMA-SHOW-ETHSW-PORT-DATA {
    description
      "ethernet switch port info";
    leaf port {
      type uint8;
      description
        "Port number";
    }
    list ethsw-register-data {
      description
        "Register data";
      uses ESDMA-SHOW-ETHSW-REGISTER-DATA;
    }
  }

  grouping ESDMA-SHOW-ETHSW-REGISTER-INFO {
    description
      "show ethernet switch register info";
    container ethsw-location-info {
      description
        "Ethernet switch location info";
      uses ESDMA-SHOW-ETHSW-LOCATION-DATA;
    }
    list ethsw-port-info {
      description
        "Ethernet switch port info";
      uses ESDMA-SHOW-ETHSW-PORT-DATA;
    }
  }

  grouping ESDMA-SHOW-ETHSW-DATA-INTEGRITY-ERROR-HISTORY-ENTRY-DATA {
    description
      "ethernet switch data integrity error history
       entry info";
    leaf instance {
      type uint32;
      description
        "Entry instance";
    }
    leaf memory-type {
      type uint32;
      description
        "Memory type";
    }
    leaf memory-type-name {
      type string {
        length "0..64";
      }
      description
        "Memory type name";
    }
    leaf memory-row {
      type uint32;
      description
        "Memory row";
    }
    leaf tcam-rule-index {
      type string {
        length "0..16";
      }
      description
        "TCAM rule index";
    }
    leaf hardware-table {
      type string {
        length "0..16";
      }
      description
        "Hardware table";
    }
    leaf hardware-table-name {
      type string {
        length "0..64";
      }
      description
        "Hardware table name";
    }
    leaf hardware-table-index {
      type string {
        length "0..16";
      }
      description
        "Hardware table index";
    }
    leaf logical-table {
      type string {
        length "0..16";
      }
      description
        "Logical table";
    }
    leaf logical-table-name {
      type string {
        length "0..64";
      }
      description
        "Logical table name";
    }
    leaf logical-table-index {
      type string {
        length "0..16";
      }
      description
        "Logical table index";
    }
    leaf interrupt {
      type uint32;
      description
        "Interrupt";
    }
    leaf error-type {
      type string {
        length "0..64";
      }
      description
        "Error type";
    }
    leaf memory-usage {
      type string {
        length "0..64";
      }
      description
        "Memory usage";
    }
    leaf correction-method {
      type string {
        length "0..64";
      }
      description
        "Correction method";
    }
    leaf error-status {
      type string {
        length "0..64";
      }
      description
        "Error status";
    }
    leaf error-time {
      type string {
        length "0..64";
      }
      description
        "Error time";
    }
  }

  grouping ESDMA-SHOW-ETHSW-DATA-INTEGRITY-ERROR-HISTORY-DATA {
    description
      "ethernet switch data integrity error history data";
    leaf number-of-entries {
      type uint32;
      description
        "Number of entries";
    }
    list ethsw-data-integrity-error-history-entry-info {
      description
        "Ethernet switch data integrity error history
         entry info";
      uses ESDMA-SHOW-ETHSW-DATA-INTEGRITY-ERROR-HISTORY-ENTRY-DATA;
    }
  }

  grouping ESDMA-SHOW-ETHSW-DATA-INTEGRITY-ERROR-INFORMATION-ENTRY-DATA {
    description
      "ethernet switch data integrity error information
       entry";
    leaf instance {
      type uint32;
      description
        "Entry instance";
    }
    leaf memory-type {
      type uint32;
      description
        "Memory type";
    }
    leaf memory-type-name {
      type string {
        length "0..64";
      }
      description
        "Memory type name";
    }
    leaf hardware-table {
      type string {
        length "0..16";
      }
      description
        "Hardware table";
    }
    leaf hardware-table-name {
      type string {
        length "0..64";
      }
      description
        "Hardware table name";
    }
    leaf logical-table {
      type string {
        length "0..16";
      }
      description
        "Logical table";
    }
    leaf logical-table-name {
      type string {
        length "0..64";
      }
      description
        "Logical table name";
    }
    leaf protection-type {
      type string {
        length "0..16";
      }
      description
        "Protection type";
    }
    leaf parity-error-count {
      type uint32;
      description
        "Parity error count";
    }
    leaf single-bit-error-correction-code-error-count {
      type uint32;
      description
        "Single bit error correction code error count";
    }
    leaf multi-bit-error-correction-code-error-count {
      type uint32;
      description
        "Multi bit error correction code error count";
    }
    leaf corrected-error-count {
      type uint32;
      description
        "Corrected error count";
    }
    leaf uncorrected-error-count {
      type uint32;
      description
        "Uncorrected error count";
    }
    leaf last-error-time {
      type string {
        length "0..64";
      }
      description
        "Last error time";
    }
  }

  grouping ESDMA-SHOW-ETHSW-DATA-INTEGRITY-ERROR-INFORMATION-DATA {
    description
      "ethernet switch data integrity error information";
    leaf number-of-entries {
      type uint32;
      description
        "Number of entries";
    }
    list ethsw-data-integrity-error-information-entry-info {
      description
        "Ethernet switch data integrity error information
         entry details";
      uses ESDMA-SHOW-ETHSW-DATA-INTEGRITY-ERROR-INFORMATION-ENTRY-DATA;
    }
  }

  grouping ESDMA-SHOW-ETHSW-DATA-INTEGRITY-ERROR-SUMMARY-ENTRY-DATA {
    description
      "ethernet switch data integrity error summary
       entry info";
    leaf memory-type {
      type uint32;
      description
        "Memory type";
    }
    leaf memory-type-name {
      type string {
        length "0..64";
      }
      description
        "Memory type name";
    }
    leaf parity-error-count {
      type uint32;
      description
        "Parity error count";
    }
    leaf single-bit-error-correction-code-error-count {
      type uint32;
      description
        "Single bit error correction code error count";
    }
    leaf multi-bit-error-correction-code-error-count {
      type uint32;
      description
        "Multi bit error correction code error count";
    }
    leaf corrected-error-count {
      type uint32;
      description
        "Corrected error count";
    }
    leaf uncorrected-error-count {
      type uint32;
      description
        "Uncorrected error count";
    }
  }

  grouping ESDMA-SHOW-ETHSW-DATA-INTEGRITY-ERROR-SUMMARY-DATA {
    description
      "ethernet switch data integrity error summary info";
    leaf number-of-entries {
      type uint32;
      description
        "Number of entries";
    }
    leaf total-parity-error-count {
      type uint64;
      description
        "Total parity error count";
    }
    leaf total-single-bit-error-correction-code-error-count {
      type uint64;
      description
        "Total single bit error correction code error
         count";
    }
    leaf total-multi-bit-error-correction-code-error-count {
      type uint64;
      description
        "Total multi bit error correction code error
         count";
    }
    leaf total-corrected-error-count {
      type uint64;
      description
        "Total corrected error count";
    }
    leaf total-uncorrected-error-count {
      type uint64;
      description
        "Total uncorrected error count";
    }
    list ethsw-data-integrity-error-summary-entry-info {
      description
        "Ethernet switch data integrity error summary
         entry info";
      uses ESDMA-SHOW-ETHSW-DATA-INTEGRITY-ERROR-SUMMARY-ENTRY-DATA;
    }
  }

  grouping ESDMA-SHOW-ETHSW-DATA-INTEGRITY-ERROR-INFO {
    description
      "show ethernet switch data integrity error info";
    container ethsw-location-info {
      description
        "Ethernet switch location info";
      uses ESDMA-SHOW-ETHSW-LOCATION-DATA;
    }
    list ethsw-data-integrity-error-summary-info {
      description
        "Ethernet switch data integrity error summary
         info";
      uses ESDMA-SHOW-ETHSW-DATA-INTEGRITY-ERROR-SUMMARY-DATA;
    }
    list ethsw-data-integrity-error-information {
      description
        "Ethernet switch data integrity error information";
      uses ESDMA-SHOW-ETHSW-DATA-INTEGRITY-ERROR-INFORMATION-DATA;
    }
    list ethsw-data-integrity-error-history-info {
      description
        "Ethernet switch data integrity error history
         info";
      uses ESDMA-SHOW-ETHSW-DATA-INTEGRITY-ERROR-HISTORY-DATA;
    }
  }

  grouping ESDMA-SHOW-ETHSW-LOCATION-DATA {
    description
      "ethernet switch location info";
    leaf rack {
      type uint8;
      description
        "Rack number";
    }
    leaf card {
      type string {
        length "0..16";
      }
      description
        "Card name";
    }
    leaf switch {
      type string {
        length "0..8";
      }
      description
        "Switch name";
    }
    leaf serial-num {
      type string {
        length "0..20";
      }
      description
        "Serial number";
    }
  }

  grouping ESDMA-SHOW-ETHSW-REACHABLE-INFO {
    description
      "show ethernet switch reachable info";
    list ethsw-reachable-info {
      description
        "Ethernet switch location info";
      uses ESDMA-SHOW-ETHSW-LOCATION-DATA;
    }
  }
}
