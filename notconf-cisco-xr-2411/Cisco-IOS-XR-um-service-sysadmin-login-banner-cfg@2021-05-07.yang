module Cisco-IOS-XR-um-service-sysadmin-login-banner-cfg {
  namespace "http://cisco.com/ns/yang/Cisco-IOS-XR-um-service-sysadmin-login-banner-cfg";
  prefix um-service-sysadmin-login-banner-cfg;

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR service-sysadmin-login-banner package configuration.

     This YANG module augments the
     modules with configuration data.

     Copyright (c) 2020-2022 by Cisco Systems, Inc.
     All rights reserved.";

  revision 2021-05-07 {
    semver:module-version "1.0.0";
    description
      "Initial release";
  }

  container service {
    description
      "Modify use of network based services";
    container sysadmin-login-banner {
      description
        "Configuration to disable sysadmin login banner";
      container disable {
        presence "Indicates a disable node is configured.";
        description
          "Disable sysadmin login banner";
      }
    }
  }
}
