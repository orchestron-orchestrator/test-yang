module Cisco-IOS-XR-msdp-oper {
  namespace "http://cisco.com/ns/yang/Cisco-IOS-XR-msdp-oper";
  prefix msdp-oper;

  import ietf-inet-types {
    prefix inet;
  }
  import Cisco-IOS-XR-types {
    prefix xr;
  }
  import cisco-semver {
    prefix semver;
  }

  include Cisco-IOS-XR-msdp-oper-sub1 {
    revision-date 2021-09-22;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR msdp package operational data.

     This module contains definitions
     for the following management objects:
       msdp: MSDP operational data

     Copyright (c) 2013-2021 by Cisco Systems, Inc.
     All rights reserved.";

  revision 2021-09-22 {
    semver:module-version "2.0.0";
    description
      "backward compatible addition";
  }
  revision 2019-08-27 {
    semver:module-version "1.0.0";
    description
      "Providing MSDP information.";
  }
  revision 2019-04-05 {
    description
      "Establish semantic version baseline.";
  }
  revision 2015-11-09 {
    description
      "IOS XR 6.0 revision.";
  }

  typedef Bgp-asn-plain {
    type uint32 {
      range "1..4294967295";
    }
    description
      "Bgp asn plain";
  }

  grouping PEER-TABLE {
    description
      "Common node of default-context, vrf";
    container peers {
      description
        "MSDP Peers";
      list peer {
        key "peer-address";
        description
          "MSDP Peer Info";
        leaf peer-address {
          type inet:ipv4-address-no-zone;
          description
            "Peer Address";
        }
        uses MSDP-PEER-BAG;
      }
    }
  }

  grouping VRF-TABLE {
    description
      "Common node of active, standby";
    container vrfs {
      description
        "VRF Table";
      list vrf {
        key "vrf-name";
        description
          "VRF Name";
        leaf vrf-name {
          type xr:Cisco-ios-xr-string {
            length "1..32";
          }
          description
            "VRF name";
        }
        uses STAT-PEER-TABLE;
        uses PEER-TABLE;
        uses PEER-SUMMARY-TABLE;
        uses SA-CACHE-TABLE;
        uses RPF-TABLE;
        uses ROUTING-CONTEXT;
        uses CACHE-SUMMARY;
        uses ALL-SA-CACHE-TABLE;
        uses AS-SOURCE-GROUP-SA-CACHE-TABLE;
        uses RP-SOURCE-GROUP-SA-CACHE-TABLE;
      }
    }
  }

  grouping SA-CACHE-TABLE {
    description
      "Common node of default-context, vrf";
    container sa-caches {
      description
        "MSDP SA Cache table - sources with Local &
         External flags Set";
      list sa-cache {
        key "source-address group-address";
        description
          "MSDP SA Cache Entry - Sources with Local &
           External flags set";
        leaf source-address {
          type inet:ipv4-address-no-zone;
          description
            "Previous Source Address";
        }
        leaf group-address {
          type inet:ipv4-address-no-zone;
          description
            "Previous Group Address";
        }
        uses MSDP-SRC-BAG;
      }
    }
  }

  grouping AS-SOURCE-GROUP-SA-CACHE-TABLE {
    description
      "Common node of default-context, vrf";
    container as-source-group-sa-caches {
      description
        "AS Filtered MSDP SA Cache table";
      list as-source-group-sa-cache {
        key "as source-address group-address";
        description
          "AS Filtered MSDP SA Cache Entries";
        leaf as {
          type Bgp-asn-plain;
          description
            "AS Number";
        }
        leaf source-address {
          type inet:ipv4-address-no-zone;
          description
            "Source Address";
        }
        leaf group-address {
          type inet:ipv4-address-no-zone;
          description
            "Group Address";
        }
        uses MSDP-SRC-BAG;
      }
    }
  }

  grouping ALL-SA-CACHE-TABLE {
    description
      "Common node of default-context, vrf";
    container all-sa-caches {
      description
        "All of MSDP SA Cache ignoring source flags";
      list all-sa-cache {
        key "source-address group-address";
        description
          "MSDP All SA Cache Entries ignoring source flags";
        leaf source-address {
          type inet:ipv4-address-no-zone;
          description
            "Source Address";
        }
        leaf group-address {
          type inet:ipv4-address-no-zone;
          description
            "Group Address";
        }
        uses MSDP-SRC-BAG;
      }
    }
  }

  grouping PROCESS {
    description
      "Common node of active, standby";
    container process {
      description
        "Process";
      container globals {
        description
          "MSDP Global Data";
        uses MSDP-GLOBAL-BAG;
      }
      container nsf {
        description
          "NSF Information";
        uses MSDP-EDM-NSF-BAG;
      }
      container summary {
        description
          "MSDP Process Summary Info";
        uses MSDP-PROCESS-SUMM-BAG;
      }
      container nsr {
        description
          "NSR Information";
        uses MSDP-NSR-BAG;
      }
    }
  }

  grouping RPF-TABLE {
    description
      "Common node of default-context, vrf";
    container rpfs {
      description
        "MSDP Reverse Path Forwarding Info";
      list rpf {
        key "rp-address";
        description
          "MSDP Reverse Path Forwarding entries";
        leaf rp-address {
          type inet:ipv4-address-no-zone;
          description
            "RP Address";
        }
        uses MSDP-RPF-BAG;
      }
    }
  }

  grouping RP-SOURCE-GROUP-SA-CACHE-TABLE {
    description
      "Common node of default-context, vrf";
    container rp-source-group-sa-caches {
      description
        "RP Filtered MSDP SA Cache table";
      list rp-source-group-sa-cache {
        key "rp-address source-address group-address";
        description
          "RP Filtered MSDP SA Cache Entries";
        leaf rp-address {
          type inet:ipv4-address-no-zone;
          description
            "RP Address";
        }
        leaf source-address {
          type inet:ipv4-address-no-zone;
          description
            "Source Address";
        }
        leaf group-address {
          type inet:ipv4-address-no-zone;
          description
            "Group Address";
        }
        uses MSDP-SRC-BAG;
      }
    }
  }

  grouping CACHE-SUMMARY {
    description
      "Common node of default-context, vrf";
    container cache-summary {
      description
        "Cache Summary";
      container rp-cache-summaries {
        description
          "RP specific Cache Summary Table";
        list rp-cache-summary {
          key "rp-address";
          description
            "Cache Summary RP";
          leaf rp-address {
            type inet:ipv4-address-no-zone;
            description
              "RP Address";
          }
          uses MSDP-SUMMARY-RP-BAG;
        }
      }
      container cache-summary-preface {
        description
          "Cache Summary Preface";
        uses MSDP-SUMMARY-PREFACE-BAG;
      }
      container as-cache-summaries {
        description
          "AS specific Cache Summary Table";
        list as-cache-summary {
          key "as";
          description
            "Cache Summary AS";
          leaf as {
            type Bgp-asn-plain;
            description
              "AS Number";
          }
          uses MSDP-SUMMARY-AS-BAG;
        }
      }
    }
  }

  grouping ROUTING-CONTEXT {
    description
      "Common node of default-context, vrf";
    container routing-context {
      description
        "MSDP routing context";
      uses MSDP-CONTEXT;
    }
  }

  grouping STAT-PEER-TABLE {
    description
      "Common node of default-context, vrf";
    container stat-peers {
      description
        "Statistics for MSDP Peers";
      list stat-peer {
        key "peer-address";
        description
          "MSDP Peer Statistics Info";
        leaf peer-address {
          type inet:ip-address-no-zone;
          description
            "Peer Address";
        }
        uses MSDP-STATS-PEER-BAG;
      }
    }
  }

  grouping DEFAULT-CONTEXT {
    description
      "Common node of active, standby";
    container default-context {
      description
        "Default Context";
      uses STAT-PEER-TABLE;
      uses PEER-TABLE;
      uses PEER-SUMMARY-TABLE;
      uses SA-CACHE-TABLE;
      uses RPF-TABLE;
      uses ROUTING-CONTEXT;
      uses CACHE-SUMMARY;
      uses ALL-SA-CACHE-TABLE;
      uses AS-SOURCE-GROUP-SA-CACHE-TABLE;
      uses RP-SOURCE-GROUP-SA-CACHE-TABLE;
    }
  }

  grouping PEER-SUMMARY-TABLE {
    description
      "Common node of default-context, vrf";
    container peer-summaries {
      description
        "MSDP Peers summary";
      list peer-summary {
        key "peer-address";
        description
          "MSDP Peer Summary Info";
        leaf peer-address {
          type inet:ipv4-address-no-zone;
          description
            "Peer Address";
        }
        uses MSDP-PEER-SUMM-BAG;
      }
    }
  }

  container msdp {
    config false;
    description
      "MSDP operational data";
    container standby {
      description
        "Standby Process";
      uses DEFAULT-CONTEXT;
      uses PROCESS;
      uses VRF-TABLE;
    }
    container active {
      description
        "Active Process";
      uses DEFAULT-CONTEXT;
      uses PROCESS;
      uses VRF-TABLE;
    }
  }
}
