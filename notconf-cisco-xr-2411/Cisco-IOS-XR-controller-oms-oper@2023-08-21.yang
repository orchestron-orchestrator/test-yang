module Cisco-IOS-XR-controller-oms-oper {
  namespace "http://cisco.com/ns/yang/Cisco-IOS-XR-controller-oms-oper";
  prefix controller-oms-oper;

  import Cisco-IOS-XR-types {
    prefix xr;
  }
  import cisco-semver {
    prefix semver;
  }

  include Cisco-IOS-XR-controller-oms-oper-sub1 {
    revision-date 2023-08-21;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR controller-oms package operational data.

     This module contains definitions
     for the following management objects:
       oms-oper: Oms operational data

     Copyright (c) 2013-2023 by Cisco Systems, Inc.
     All rights reserved.";

  revision 2023-08-21 {
    semver:module-version "1.0.0";
    description
      "Added support for Egress Amplifier Back Reflection status, Egress Amplifier Back Reflection Power and Egress Amplifier Back Reflection Ratio";
  }
  revision 2023-07-11 {
    description
      "egress-ampli-gain-config leaf data-type changed from uint32 to int32";
  }
  revision 2023-06-02 {
    description
      "Added support for tx-voa-attenuation and rx-voa-attenuation";
  }
  revision 2023-06-02 {
    description
      "Added support for ingress-ampli-osri and egress-ampli-osri";
  }
  revision 2023-06-02 {
    description
      "Added support for EDFA parameters";
  }
  revision 2022-05-23 {
    description
      "total-rx-power leaf is changed to rx-power in oms-info container";
  }
  revision 2022-03-25 {
    description
      "Added transport_admin_state for OMS controller";
  }
  revision 2021-06-28 {
    description
      "New Oper Model Added for Oms Controller";
  }
  revision 2019-04-05 {
    description
      "Establish semantic version baseline.";
  }
  revision 2015-11-09 {
    description
      "IOS XR 6.0 revision.";
  }

  container oms-oper {
    config false;
    description
      "Oms operational data";
    container oms-ports {
      description
        "All Oms Port operational data";
      list oms-port {
        key "name";
        description
          "Oms operational data";
        container oms-info {
          description
            "Oms operational data";
          uses OMS-EDM-INFO;
        }
        leaf name {
          type xr:Interface-name;
          description
            "Port name";
        }
      }
    }
  }
}
