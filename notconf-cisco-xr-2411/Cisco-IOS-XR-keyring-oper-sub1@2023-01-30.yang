submodule Cisco-IOS-XR-keyring-oper-sub1 {
  belongs-to Cisco-IOS-XR-keyring-oper {
    prefix Cisco-IOS-XR-keyring-oper;
  }

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR keyring package operational data.

     Copyright (c) 2013-2023 by Cisco Systems, Inc.
     All rights reserved.";

  revision 2023-01-30 {
    semver:module-version "1.1.0";
    description
      "PPK support";
  }
  revision 2019-04-05 {
    semver:module-version "1.0.1";
    description
      "Establish semantic version baseline.";
  }
  revision 2019-02-04 {
    description
      "Keyring Operational Yang Support";
  }
  revision 2015-11-09 {
    description
      "IOS XR 6.0 revision.";
  }

  grouping IKEV2-EDM-PEER {
    description
      "IKEV2 EDM PEER";
    leaf peer-name {
      type string;
      description
        "Name of the peer";
    }
    leaf ip-address {
      type string;
      description
        "IP Address of the peer";
    }
    leaf subnet {
      type string;
      description
        "Subnet mask of the peer";
    }
    leaf local-psk {
      type string;
      description
        "Local PSK";
    }
    leaf remote-psk {
      type string;
      description
        "Remote PSK";
    }
    leaf ppk-mode {
      type string;
      description
        "PPK mode if configured";
    }
    leaf ppk-mandatory {
      type string;
      description
        "PPK required or not";
    }
  }

  grouping IKEV2-EDM-KEYRING {
    description
      "IKEV2 EDM KEYRING";
    leaf keyring-name {
      type string;
      description
        "Name of the Keyring";
    }
    leaf total-peers {
      type uint32;
      description
        "Total Peers";
    }
    list peer {
      description
        "List of peers";
      uses IKEV2-EDM-PEER;
    }
  }
}
