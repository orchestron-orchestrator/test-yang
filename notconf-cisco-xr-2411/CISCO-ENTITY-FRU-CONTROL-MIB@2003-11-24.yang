module CISCO-ENTITY-FRU-CONTROL-MIB {
  namespace "http://tail-f.com/ns/mibs/CISCO-ENTITY-FRU-CONTROL-MIB/200311240000Z";
  prefix CISCO_ENTITY_FRU_CONTROL_MIB;

  import ietf-yang-types {
    prefix yang;
  }
  import tailf-common {
    prefix tailf;
  }
  import SNMPv2-TC {
    prefix SNMPv2-TC;
  }
  import INET-ADDRESS-MIB {
    prefix INET-ADDRESS-MIB;
  }
  import Cisco-IOS-XR-sysadmin-entity-mib {
    prefix ENTITY-MIB;
  }

  organization
    "Cisco Systems, Inc.";
  contact
    "Cisco Systems, Inc.
     Customer Service

     Postal: 170 West Tasman Drive
     San Jose, CA 95134

     Tel: +1 800 553-NETS

     E-mail: cs-yang@cisco.com";
  description
    "This module contains definitions
     for the Calvados model objects.

     Copyright (c) 2012-2020 by Cisco Systems, Inc.
     All rights reserved.";

  revision 2003-11-24;

  tailf:id "";
  tailf:snmp-mib-module-name "CISCO-ENTITY-FRU-CONTROL-MIB";

  typedef PowerRedundancyType {
    type enumeration {
      enum "notsupported" {
        value 1;
      }
      enum "redundant" {
        value 2;
      }
      enum "combined" {
        value 3;
      }
    }
  }

  typedef PowerAdminType {
    type enumeration {
      enum "on" {
        value 1;
      }
      enum "off" {
        value 2;
      }
      enum "inlineAuto" {
        value 3;
      }
      enum "inlineOn" {
        value 4;
      }
    }
  }

  typedef PowerOperType {
    type enumeration {
      enum "offEnvOther" {
        value 1;
      }
      enum "on" {
        value 2;
      }
      enum "offAdmin" {
        value 3;
      }
      enum "offDenied" {
        value 4;
      }
      enum "offEnvPower" {
        value 5;
      }
      enum "offEnvTemp" {
        value 6;
      }
      enum "offEnvFan" {
        value 7;
      }
      enum "failed" {
        value 8;
      }
      enum "onButFanFail" {
        value 9;
      }
    }
  }

  typedef FRUCurrentType {
    type int32 {
      range "-1000000000 .. 1000000000";
    }
  }

  typedef ModuleAdminType {
    type enumeration {
      enum "enabled" {
        value 1;
      }
      enum "disabled" {
        value 2;
      }
      enum "reset" {
        value 3;
      }
      enum "outOfServiceAdmin" {
        value 4;
      }
    }
  }

  typedef ModuleOperType {
    type enumeration {
      enum "unknown" {
        value 1;
      }
      enum "ok" {
        value 2;
      }
      enum "disabled" {
        value 3;
      }
      enum "okButDiagFailed" {
        value 4;
      }
      enum "boot" {
        value 5;
      }
      enum "selfTest" {
        value 6;
      }
      enum "failed" {
        value 7;
      }
      enum "missing" {
        value 8;
      }
      enum "mismatchWithParent" {
        value 9;
      }
      enum "mismatchConfig" {
        value 10;
      }
      enum "diagFailed" {
        value 11;
      }
      enum "dormant" {
        value 12;
      }
      enum "outOfServiceAdmin" {
        value 13;
      }
      enum "outOfServiceEnvTemp" {
        value 14;
      }
      enum "poweredDown" {
        value 15;
      }
      enum "poweredUp" {
        value 16;
      }
      enum "powerDenied" {
        value 17;
      }
      enum "powerCycled" {
        value 18;
      }
      enum "okButPowerOverWarning" {
        value 19;
      }
      enum "okButPowerOverCritical" {
        value 20;
      }
      enum "updatingFPD" {
        value 21;
      }
    }
  }

  typedef ModuleResetReasonType {
    type enumeration {
      enum "unknown" {
        value 1;
      }
      enum "powerUp" {
        value 2;
      }
      enum "parityError" {
        value 3;
      }
      enum "clearConfigReset" {
        value 4;
      }
      enum "manualReset" {
        value 5;
      }
      enum "watchDogTimeoutReset" {
        value 6;
      }
      enum "resourceOverflowReset" {
        value 7;
      }
      enum "missingTaskReset" {
        value 8;
      }
      enum "lowVoltageReset" {
        value 9;
      }
      enum "controllerReset" {
        value 10;
      }
      enum "systemReset" {
        value 11;
      }
      enum "switchoverReset" {
        value 12;
      }
      enum "upgradeReset" {
        value 13;
      }
      enum "downgradeReset" {
        value 14;
      }
      enum "cacheErrorReset" {
        value 15;
      }
      enum "deviceDriverReset" {
        value 16;
      }
      enum "softwareExceptionReset" {
        value 17;
      }
      enum "restoreConfigReset" {
        value 18;
      }
      enum "abortRevReset" {
        value 19;
      }
      enum "burnBootReset" {
        value 20;
      }
      enum "standbyCdHealthierReset" {
        value 21;
      }
      enum "nonNativeConfigClearReset" {
        value 22;
      }
      enum "memoryProtectionErrorReset" {
        value 23;
      }
    }
  }

  typedef FRUTimeSeconds {
    type uint32 {
      range "0 .. 4294967295";
    }
  }

  typedef cefcMaxDefaultInLinePowerType {
    type int32 {
      range "0 .. 12500";
    }
  }

  typedef cefcFanTrayOperStatusType {
    type enumeration {
      enum "unknown" {
        value 1;
      }
      enum "up" {
        value 2;
      }
      enum "down" {
        value 3;
      }
      enum "warning" {
        value 4;
      }
    }
  }

  typedef cefcPhysicalStatusType {
    type enumeration {
      enum "other" {
        value 1;
      }
      enum "supported" {
        value 2;
      }
      enum "unsupported" {
        value 3;
      }
      enum "incompatible" {
        value 4;
      }
    }
  }

  container CISCO-ENTITY-FRU-CONTROL-MIB {
    container cefcFRUPower {
      tailf:snmp-oid "1.3.6.1.4.1.9.9.117.1.1";
      config false;
      leaf cefcMaxDefaultInLinePower {
        tailf:snmp-oid "1.3.6.1.4.1.9.9.117.1.1.3";
        type cefcMaxDefaultInLinePowerType;
        default "12500";
      }
      leaf cefcMaxDefaultHighInLinePower {
        tailf:snmp-oid "1.3.6.1.4.1.9.9.117.1.1.5";
        type uint32;
      }
    }
    container cefcMIBNotificationEnables {
      tailf:snmp-oid "1.3.6.1.4.1.9.9.117.1.3";
      config false;
      leaf cefcMIBEnableStatusNotification {
        tailf:snmp-oid "1.3.6.1.4.1.9.9.117.1.3.1";
        type SNMPv2-TC:TruthValue;
        default "false";
      }
    }
    container cefcFRUPowerSupplyGroupTable {
      config false;
      list cefcFRUPowerSupplyGroupEntry {
        tailf:sort-order "snmp";
        tailf:snmp-oid "1.3.6.1.4.1.9.9.117.1.1.1";
        key "entPhysicalIndex";
        leaf entPhysicalIndex {
          tailf:snmp-oid "1.3.6.1.2.1.47.1.1.1.1.1";
          type ENTITY-MIB:PhysicalIndex;
        }
        leaf cefcPowerRedundancyMode {
          tailf:snmp-oid "1.3.6.1.4.1.9.9.117.1.1.1.1.1";
          type PowerRedundancyType;
        }
        leaf cefcPowerUnits {
          tailf:snmp-oid "1.3.6.1.4.1.9.9.117.1.1.1.1.2";
          type string {
            length "0 .. 255";
          }
          config false;
        }
        leaf cefcTotalAvailableCurrent {
          tailf:snmp-oid "1.3.6.1.4.1.9.9.117.1.1.1.1.3";
          type FRUCurrentType;
          config false;
        }
        leaf cefcTotalDrawnCurrent {
          tailf:snmp-oid "1.3.6.1.4.1.9.9.117.1.1.1.1.4";
          type FRUCurrentType;
          config false;
        }
        leaf cefcPowerRedundancyOperMode {
          tailf:snmp-oid "1.3.6.1.4.1.9.9.117.1.1.1.1.5";
          type PowerRedundancyType;
          config false;
        }
      }
    }
    container cefcFRUPowerStatusTable {
      config false;
      list cefcFRUPowerStatusEntry {
        tailf:sort-order "snmp";
        tailf:snmp-oid "1.3.6.1.4.1.9.9.117.1.1.2";
        key "entPhysicalIndex";
        leaf entPhysicalIndex {
          tailf:snmp-oid "1.3.6.1.2.1.47.1.1.1.1.1";
          type ENTITY-MIB:PhysicalIndex;
        }
        leaf cefcFRUPowerAdminStatus {
          tailf:snmp-oid "1.3.6.1.4.1.9.9.117.1.1.2.1.1";
          type PowerAdminType;
          config false;
        }
        leaf cefcFRUPowerOperStatus {
          tailf:snmp-oid "1.3.6.1.4.1.9.9.117.1.1.2.1.2";
          type PowerOperType;
          config false;
        }
        leaf cefcFRUCurrent {
          tailf:snmp-oid "1.3.6.1.4.1.9.9.117.1.1.2.1.3";
          type FRUCurrentType;
          config false;
        }
      }
    }
    container cefcFRUPowerSupplyValueTable {
      config false;
      list cefcFRUPowerSupplyValueEntry {
        tailf:sort-order "snmp";
        tailf:snmp-oid "1.3.6.1.4.1.9.9.117.1.1.4";
        key "entPhysicalIndex";
        leaf entPhysicalIndex {
          tailf:snmp-oid "1.3.6.1.2.1.47.1.1.1.1.1";
          type ENTITY-MIB:PhysicalIndex;
        }
        leaf cefcFRUTotalSystemCurrent {
          tailf:snmp-oid "1.3.6.1.4.1.9.9.117.1.1.4.1.1";
          type FRUCurrentType;
        }
        leaf cefcFRUDrawnSystemCurrent {
          tailf:snmp-oid "1.3.6.1.4.1.9.9.117.1.1.4.1.2";
          type FRUCurrentType;
        }
        leaf cefcFRUTotalInlineCurrent {
          tailf:snmp-oid "1.3.6.1.4.1.9.9.117.1.1.4.1.3";
          type FRUCurrentType;
        }
        leaf cefcFRUDrawnInlineCurrent {
          tailf:snmp-oid "1.3.6.1.4.1.9.9.117.1.1.4.1.4";
          type FRUCurrentType;
        }
      }
    }
    container cefcModuleTable {
      config false;
      list cefcModuleEntry {
        tailf:sort-order "snmp";
        tailf:snmp-oid "1.3.6.1.4.1.9.9.117.1.2.1";
        key "entPhysicalIndex";
        leaf entPhysicalIndex {
          tailf:snmp-oid "1.3.6.1.2.1.47.1.1.1.1.1";
          type ENTITY-MIB:PhysicalIndex;
        }
        leaf cefcModuleAdminStatus {
          tailf:snmp-oid "1.3.6.1.4.1.9.9.117.1.2.1.1.1";
          type ModuleAdminType;
          config false;
        }
        leaf cefcModuleOperStatus {
          tailf:snmp-oid "1.3.6.1.4.1.9.9.117.1.2.1.1.2";
          type ModuleOperType;
          config false;
        }
        leaf cefcModuleResetReason {
          tailf:snmp-oid "1.3.6.1.4.1.9.9.117.1.2.1.1.3";
          type ModuleResetReasonType;
          config false;
        }
        leaf cefcModuleStatusLastChangeTime {
          tailf:snmp-oid "1.3.6.1.4.1.9.9.117.1.2.1.1.4";
          type yang:timestamp;
          config false;
        }
        leaf cefcModuleLastClearConfigTime {
          tailf:snmp-oid "1.3.6.1.4.1.9.9.117.1.2.1.1.5";
          type yang:timestamp;
          config false;
        }
        leaf cefcModuleResetReasonDescription {
          tailf:snmp-oid "1.3.6.1.4.1.9.9.117.1.2.1.1.6";
          type string {
            length "0 .. 255";
          }
          config false;
        }
        leaf cefcModuleStateChangeReasonDescr {
          tailf:snmp-oid "1.3.6.1.4.1.9.9.117.1.2.1.1.7";
          type string {
            length "0 .. 255";
          }
          config false;
        }
        leaf cefcModuleUpTime {
          tailf:snmp-oid "1.3.6.1.4.1.9.9.117.1.2.1.1.8";
          type FRUTimeSeconds;
          config false;
        }
      }
    }
    container cefcIntelliModuleTable {
      config false;
      list cefcIntelliModuleEntry {
        tailf:sort-order "snmp";
        tailf:snmp-oid "1.3.6.1.4.1.9.9.117.1.2.2";
        key "entPhysicalIndex";
        config false;
        leaf entPhysicalIndex {
          tailf:snmp-oid "1.3.6.1.2.1.47.1.1.1.1.1";
          type ENTITY-MIB:PhysicalIndex;
        }
        leaf cefcIntelliModuleIPAddrType {
          tailf:snmp-oid "1.3.6.1.4.1.9.9.117.1.2.2.1.1";
          type INET-ADDRESS-MIB:InetAddressType;
          config false;
        }
        leaf cefcIntelliModuleIPAddr {
          tailf:snmp-oid "1.3.6.1.4.1.9.9.117.1.2.2.1.2";
          type INET-ADDRESS-MIB:InetAddress;
          config false;
        }
      }
    }
    container cefcFanTrayStatusTable {
      config false;
      list cefcFanTrayStatusEntry {
        tailf:sort-order "snmp";
        tailf:snmp-oid "1.3.6.1.4.1.9.9.117.1.4.1";
        key "entPhysicalIndex";
        config false;
        leaf entPhysicalIndex {
          tailf:snmp-oid "1.3.6.1.2.1.47.1.1.1.1.1";
          type ENTITY-MIB:PhysicalIndex;
        }
        leaf cefcFanTrayOperStatus {
          tailf:snmp-oid "1.3.6.1.4.1.9.9.117.1.4.1.1.1";
          type cefcFanTrayOperStatusType;
          config false;
        }
      }
    }
    container cefcPhysicalTable {
      config false;
      list cefcPhysicalEntry {
        tailf:sort-order "snmp";
        tailf:snmp-oid "1.3.6.1.4.1.9.9.117.1.5.1";
        key "entPhysicalIndex";
        config false;
        leaf entPhysicalIndex {
          tailf:snmp-oid "1.3.6.1.2.1.47.1.1.1.1.1";
          type ENTITY-MIB:PhysicalIndex;
        }
        leaf cefcPhysicalStatus {
          tailf:snmp-oid "1.3.6.1.4.1.9.9.117.1.5.1.1.1";
          type cefcPhysicalStatusType;
          config false;
        }
      }
    }
  }
}
