module Cisco-IOS-XR-cosm-cfg {
  namespace "http://cisco.com/ns/yang/Cisco-IOS-XR-cosm-cfg";
  prefix cosm-cfg;

  import Cisco-IOS-XR-types {
    prefix xr;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR cosm package configuration.

     This module contains definitions
     for the following management objects:
       cosm-manager-global: COSM Manager configuration

     Copyright (c) 2013-2019 by Cisco Systems, Inc.
     All rights reserved.";

  revision 2019-04-05 {
    semver:module-version "1.0.0";
    description
      "Establish semantic version baseline.";
  }
  revision 2015-11-09 {
    description
      "IOS XR 6.0 revision.";
  }

  container cosm-manager-global {
    description
      "COSM Manager configuration";
    container restconf {
      description
        "Restconf configuration of COSM";
      leaf restconf-enabled {
        type boolean;
        default "true";
        description
          "Enable Restconf NBI of COSM";
      }
    }
    container redundancy {
      description
        "Redundancy configuration of COSM";
      leaf ha-gateway-ip {
        type string;
        description
          "IP address of the gateway of the HA interface
           of COSM";
      }
      leaf ha-peer-ip {
        type string;
        description
          "IP address of the peer device HA interface of
           COSM";
      }
      leaf ha-interface-name {
        type string;
        description
          "Name of the HA interface of COSM";
      }
    }
    container netconf {
      description
        "Netconf configuration of COSM";
      leaf netconf-enabled {
        type boolean;
        default "true";
        description
          "Enable Netconf NBI of COSM";
      }
      leaf netconf-port {
        type xr:Cisco-ios-xr-port-number;
        default "2022";
        description
          "Netconf port number of COSM";
      }
    }
    container web-u-iconf {
      description
        "WebUI configuration of COSM";
      leaf web-ui-enabled {
        type boolean;
        default "true";
        description
          "Enable WebUI NBI of COSM";
      }
    }
    container user-credentials {
      description
        "COSM User credentials";
      leaf user-password {
        type xr:Proprietary-password;
        description
          "User password to be configured in COSM";
      }
      leaf user-name {
        type string;
        description
          "User name to be configured in COSM";
      }
    }
    leaf mgmt-interface-name {
      type string;
      description
        "Name of the management interface of COSM";
    }
    leaf optical-type {
      type string;
      description
        "Optical type of the node (ROADM, OLA, DGE, TXP)";
    }
  }
}
