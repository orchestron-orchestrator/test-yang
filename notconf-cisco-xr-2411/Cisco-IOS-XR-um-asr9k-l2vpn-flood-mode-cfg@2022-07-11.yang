module Cisco-IOS-XR-um-asr9k-l2vpn-flood-mode-cfg {
  namespace "http://cisco.com/ns/yang/Cisco-IOS-XR-um-asr9k-l2vpn-flood-mode-cfg";
  prefix um-asr9k-l2vpn-flood-mode-cfg;

  import Cisco-IOS-XR-um-l2vpn-cfg {
    prefix a1;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR asr9k-l2vpn-flood-mode package configuration.

     This YANG module augments the
     modules with configuration data.

     Copyright (c) 2021-2022 by Cisco Systems, Inc.
     All rights reserved.";

  revision 2022-07-11 {
    semver:module-version "1.0.0";
    description
      "Added missing description statement to nodes";
  }
  revision 2021-04-13 {
    semver:module-version "1.0.0";
    description
      "Initial release";
  }

  augment "/a1:l2vpn/a1:bridge/a1:groups/a1:group/a1:bridge-domains/a1:bridge-domain" {
    description
      "This augment extends l2vpn nodes configuration";
    container flood {
      description
        "Flooding Capability";
      container mode {
        description
          "Choose Flooding Mode";
        container convergence-optimized {
          must "not(../resilience-optimized)";
          presence "Indicates a convergence-optimized node is configured.";
          description
            "Convergence Optimized Mode";
        }
        container resilience-optimized {
          must "not(../convergence-optimized)";
          presence "Indicates a resilience-optimized node is configured.";
          description
            "Resilience Optimized Mode";
        }
      }
    }
  }
}
