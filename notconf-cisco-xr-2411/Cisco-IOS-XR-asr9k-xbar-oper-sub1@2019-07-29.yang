submodule Cisco-IOS-XR-asr9k-xbar-oper-sub1 {
  belongs-to Cisco-IOS-XR-asr9k-xbar-oper {
    prefix Cisco-IOS-XR-asr9k-xbar-oper;
  }

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR asr9k-xbar package operational data.

     Copyright (c) 2013-2019 by Cisco Systems, Inc.
     All rights reserved.";

  revision 2019-07-29 {
    semver:module-version "1.0.0";
    description
      "Support for bandwidth-utils-stats CLI.";
  }
  revision 2019-04-05 {
    description
      "Establish semantic version baseline.";
  }
  revision 2015-11-09 {
    description
      "IOS XR 6.0 revision.";
  }

  grouping XBAR-EDM-SM15-PE-CC-STATS {
    description
      "XBAR EDM SM15 PE CC STATS";
    leaf in-pkt-cnt {
      type uint64;
      description
        "IN PKT CNT";
    }
    leaf out-path0-pkt-cnt {
      type uint64;
      description
        "OUT PATH0 PKT CNT";
    }
    leaf out-path1-pkt-cnt {
      type uint64;
      description
        "OUT PATH1 PKT CNT";
    }
    leaf xbar-ecc-drop-pkt-cnt {
      type uint64;
      description
        "XBAR ECC DROP PKT CNT";
    }
    leaf mem0-drop-pkt-cnt {
      type uint64;
      description
        "MEM0 DROP PKT CNT";
    }
    leaf mem1-drop-pkt-cnt {
      type uint64;
      description
        "MEM1 DROP PKT CNT";
    }
    leaf congn-pkt-cnt {
      type uint64;
      description
        "CONGN PKT CNT";
    }
    leaf xbar-ecc-single-err-cnt {
      type uint64;
      description
        "XBAR ECC SINGLE ERR CNT";
    }
    leaf xbar-ecc-double-err-cnt {
      type uint64;
      description
        "XBAR ECC DOUBLE ERR CNT";
    }
    leaf mem0-ecc-single-err-cnt {
      type uint64;
      description
        "MEM0 ECC SINGLE ERR CNT";
    }
    leaf mem0-ecc-double-err-cnt {
      type uint64;
      description
        "MEM0 ECC DOUBLE ERR CNT";
    }
    leaf mem1-ecc-single-err-cnt {
      type uint64;
      description
        "MEM1 ECC SINGLE ERR CNT";
    }
    leaf mem1-ecc-double-err-cnt {
      type uint64;
      description
        "MEM1 ECC DOUBLE ERR CNT";
    }
    leaf fc-cc-0-1-trans-cnt {
      type uint64;
      description
        "FC CC 0 1 TRANS CNT";
    }
    leaf rate-cnt {
      type uint64;
      description
        "RATE CNT";
    }
    leaf calc-rate {
      type uint64;
      description
        "Egress Control Cast Rate";
    }
  }

  grouping XBAR-EDM-SM15-PE-MC-STATS {
    description
      "XBAR EDM SM15 PE MC STATS";
    leaf in-pkt-mc-cnt {
      type uint64;
      description
        "IN PKT MC CNT";
    }
    leaf in-full-line-mc-cnt {
      type uint64;
      description
        "IN FULL LINE MC CNT";
    }
    leaf pkt-trunc-eop-mc-cnt {
      type uint64;
      description
        "PKT TRUNC EOP MC CNT";
    }
    leaf pkt-sop-drop-mc-cnt {
      type uint64;
      description
        "PKT SOP DROP MC CNT";
    }
    leaf pkt-ecc-err-drop-mc-cnt {
      type uint64;
      description
        "PKT ECC ERR DROP MC CNT";
    }
    leaf pkt-ecc-err-trunc-cnt-mc-cnt {
      type uint64;
      description
        "PKT ECC ERR TRUNC CNT MC CNT";
    }
    leaf ecc-1bit-err-mc0-cnt {
      type uint64;
      description
        "ECC 1BIT ERR MC0 CNT";
    }
    leaf ecc-1bit-err-mc1-cnt {
      type uint64;
      description
        "ECC 1BIT ERR MC1 CNT";
    }
    leaf ecc-1bit-err-mc2-cnt {
      type uint64;
      description
        "ECC 1BIT ERR MC2 CNT";
    }
    leaf ecc-2bit-err-mc0-cnt {
      type uint64;
      description
        "ECC 2BIT ERR MC0 CNT";
    }
    leaf ecc-2bit-err-mc1-cnt {
      type uint64;
      description
        "ECC 2BIT ERR MC1 CNT";
    }
    leaf ecc-2bit-err-mc2-cnt {
      type uint64;
      description
        "ECC 2BIT ERR MC2 CNT";
    }
    leaf out-pkt-mc-cnt {
      type uint64;
      description
        "OUT PKT MC CNT";
    }
    leaf fe-mc-sop-eop-pack-cnt {
      type uint64;
      description
        "FE MC SOP EOP PACK CNT";
    }
    leaf fc-mc-0-1-trans-cnt {
      type uint64;
      description
        "FC MC 0 1 TRANS CNT";
    }
    leaf rate-cnt {
      type uint64;
      description
        "RATE CNT";
    }
    leaf calc-rate {
      type uint64;
      description
        "Egress Multicast Rate";
    }
  }

  grouping XBAR-EDM-SM15-PE-UC-STATS {
    description
      "XBAR EDM SM15 PE UC STATS";
    leaf in-pkt-uc0-cnt {
      type uint64;
      description
        "IN PKT UC0 CNT";
    }
    leaf in-pkt-uc1-cnt {
      type uint64;
      description
        "IN PKT UC1 CNT";
    }
    leaf in-pkt-uc2-cnt {
      type uint64;
      description
        "IN PKT UC2 CNT";
    }
    leaf in-full-line-uc0-cnt {
      type uint64;
      description
        "IN FULL LINE UC0 CNT";
    }
    leaf in-full-line-uc1-cnt {
      type uint64;
      description
        "IN FULL LINE UC1 CNT";
    }
    leaf in-full-line-uc2-cnt {
      type uint64;
      description
        "IN FULL LINE UC2 CNT";
    }
    leaf pkt-trunc-eop-uc0-cnt {
      type uint64;
      description
        "PKT TRUNC EOP UC0 CNT";
    }
    leaf pkt-trunc-eop-uc1-cnt {
      type uint64;
      description
        "PKT TRUNC EOP UC1 CNT";
    }
    leaf pkt-trunc-eop-uc2-cnt {
      type uint64;
      description
        "PKT TRUNC EOP UC2 CNT";
    }
    leaf pkt-sop-drop-uc0-cnt {
      type uint64;
      description
        "PKT SOP DROP UC0 CNT";
    }
    leaf pkt-sop-drop-uc1-cnt {
      type uint64;
      description
        "PKT SOP DROP UC1 CNT";
    }
    leaf pkt-sop-drop-uc2-cnt {
      type uint64;
      description
        "PKT SOP DROP UC2 CNT";
    }
    leaf pkt-ecc-err-drop-uc-cnt {
      type uint64;
      description
        "PKT ECC ERR DROP UC CNT";
    }
    leaf pkt-ecc-trunc-cnt-uc-cnt {
      type uint64;
      description
        "PKT ECC TRUNC CNT UC CNT";
    }
    leaf ecc-1bit-err-uc0-0-cnt {
      type uint64;
      description
        "ECC 1BIT ERR UC0 0 CNT";
    }
    leaf ecc-1bit-err-uc0-1-cnt {
      type uint64;
      description
        "ECC 1BIT ERR UC0 1 CNT";
    }
    leaf ecc-1bit-err-uc1-0-cnt {
      type uint64;
      description
        "ECC 1BIT ERR UC1 0 CNT";
    }
    leaf ecc-1bit-err-uc1-1-cnt {
      type uint64;
      description
        "ECC 1BIT ERR UC1 1 CNT";
    }
    leaf ecc-1bit-err-uc2-0-cnt {
      type uint64;
      description
        "ECC 1BIT ERR UC2 0 CNT";
    }
    leaf ecc-1bit-err-uc2-1-cnt {
      type uint64;
      description
        "ECC 1BIT ERR UC2 1 CNT";
    }
    leaf ecc-2bit-err-uc0-0-cnt {
      type uint64;
      description
        "ECC 2BIT ERR UC0 0 CNT";
    }
    leaf ecc-2bit-err-uc0-1-cnt {
      type uint64;
      description
        "ECC 2BIT ERR UC0 1 CNT";
    }
    leaf ecc-2bit-err-uc1-0-cnt {
      type uint64;
      description
        "ECC 2BIT ERR UC1 0 CNT";
    }
    leaf ecc-2bit-err-uc1-1-cnt {
      type uint64;
      description
        "ECC 2BIT ERR UC1 1 CNT";
    }
    leaf ecc-2bit-err-uc2-0-cnt {
      type uint64;
      description
        "ECC 2BIT ERR UC2 0 CNT";
    }
    leaf ecc-2bit-err-uc2-1-cnt {
      type uint64;
      description
        "ECC 2BIT ERR UC2 1 CNT";
    }
    leaf out-pkt-uc-cnt {
      type uint64;
      description
        "OUT PKT UC CNT";
    }
    leaf fe-uc-sop-eop-pack-cnt {
      type uint64;
      description
        "FE UC SOP EOP PACK CNT";
    }
    leaf fc-uc-0-1-trans-cnt {
      type uint64;
      description
        "FC UC 0 1 TRANS CNT";
    }
    leaf rate-cnt {
      type uint64;
      description
        "RATE CNT";
    }
    leaf calc-rate {
      type uint64;
      description
        "Egress Unicast Rate";
    }
  }

  grouping XBAR-EDM-SM15-PI-CC-STATS {
    description
      "XBAR EDM SM15 PI CC STATS";
    leaf in0-ecc-serr-cnt {
      type uint64;
      description
        "IN0 ECC SERR CNT";
    }
    leaf in0-ecc-derr-cnt {
      type uint64;
      description
        "IN0 ECC DERR CNT";
    }
    leaf in1-ecc-serr-cnt {
      type uint64;
      description
        "IN1 ECC SERR CNT";
    }
    leaf in1-ecc-derr-cnt {
      type uint64;
      description
        "IN1 ECC DERR CNT";
    }
    leaf data-mem-ecc-serr-cnt {
      type uint64;
      description
        "DATA MEM ECC SERR CNT";
    }
    leaf data-mem-ecc-derr-cnt {
      type uint64;
      description
        "DATA MEM ECC DERR CNT";
    }
    leaf data-mem-ovf0-cnt {
      type uint64;
      description
        "DATA MEM OVF0 CNT";
    }
    leaf data-mem-ovf1-cnt {
      type uint64;
      description
        "DATA MEM OVF1 CNT";
    }
    leaf fpoe-mem-ecc-serr-cnt {
      type uint64;
      description
        "FPOE MEM ECC SERR CNT";
    }
    leaf fpoe-mem-ecc-derr-cnt {
      type uint64;
      description
        "FPOE MEM ECC DERR CNT";
    }
    leaf null-poe-cnt {
      type uint64;
      description
        "NULL POE CNT";
    }
    leaf shut-ack-cnt {
      type uint64;
      description
        "SHUT ACK CNT";
    }
    leaf in0-fnc-err-cnt {
      type uint64;
      description
        "IN0 FNC ERR CNT";
    }
    leaf in1-fnc-err-cnt {
      type uint64;
      description
        "IN1 FNC ERR CNT";
    }
    leaf in0-drop-cnt {
      type uint64;
      description
        "IN0 DROP CNT";
    }
    leaf in1-drop-cnt {
      type uint64;
      description
        "IN1 DROP CNT";
    }
    leaf in0-cong-cnt {
      type uint64;
      description
        "IN0 CONG CNT";
    }
    leaf in1-cong-cnt {
      type uint64;
      description
        "IN1 CONG CNT";
    }
    leaf in0-shut-cnt {
      type uint64;
      description
        "IN0 SHUT CNT";
    }
    leaf in1-shut-cnt {
      type uint64;
      description
        "IN1 SHUT CNT";
    }
    leaf tail-drop-msg-cnt {
      type uint64;
      description
        "TAIL DROP MSG CNT";
    }
    leaf in0-pkt-cnt {
      type uint64;
      description
        "IN0 PKT CNT";
    }
    leaf in1-pkt-cnt {
      type uint64;
      description
        "IN1 PKT CNT";
    }
    leaf dmem-rd-cnt {
      type uint64;
      description
        "DMEM RD CNT";
    }
    leaf in-dmem0-cnt {
      type uint64;
      description
        "IN DMEM0 CNT";
    }
    leaf in-dmem1-cnt {
      type uint64;
      description
        "IN DMEM1 CNT";
    }
    leaf out-pkt-cnt {
      type uint64;
      description
        "OUT PKT CNT";
    }
    leaf stop-thrsh-hit-cnt {
      type uint64;
      description
        "STOP THRSH HIT CNT";
    }
    leaf rate-cnt {
      type uint64;
      description
        "RATE CNT";
    }
    leaf calc-rate {
      type uint64;
      description
        "Ingress Control Cast Rate";
    }
  }

  grouping XBAR-EDM-SM15-PI-MC-STATS {
    description
      "XBAR EDM SM15 PI MC STATS";
    leaf pkt-rcv-cnt {
      type uint64;
      description
        "PKT RCV CNT";
    }
    leaf pkt-seq-err-cnt {
      type uint64;
      description
        "PKT SEQ ERR CNT";
    }
    leaf in-coming-pkt-err-cnt {
      type uint64;
      description
        "INCOMING PKT ERR CNT";
    }
    leaf min-pkt-len-err-cnt {
      type uint64;
      description
        "MIN PKT LEN ERR CNT";
    }
    leaf max-pkt-len-err-cnt {
      type uint64;
      description
        "MAX PKT LEN ERR CNT";
    }
    leaf line-err-drp-pkt {
      type uint64;
      description
        "LINE ERR DRP PKT";
    }
    leaf pkt-crc-err-cnt {
      type uint64;
      description
        "PKT CRC ERR CNT";
    }
    leaf pkt-cfh-crc-err-cnt {
      type uint64;
      description
        "PKT CFH CRC ERR CNT";
    }
    leaf line-s-written-in-mem {
      type uint64;
      description
        "LINES WRITTEN IN MEM";
    }
    leaf tail-drp-pkt-cnt {
      type uint64;
      description
        "TAIL DRP PKT CNT";
    }
    leaf data-mem0-ecc-1bit-err-cnt {
      type uint64;
      description
        "DATA MEM0 ECC 1BIT ERR CNT";
    }
    leaf data-mem1-ecc-1bit-err-cnt {
      type uint64;
      description
        "DATA MEM1 ECC 1BIT ERR CNT";
    }
    leaf data-mem2-ecc-1bit-err-cnt {
      type uint64;
      description
        "DATA MEM2 ECC 1BIT ERR CNT";
    }
    leaf data-mem0-ecc-2bit-err-cnt {
      type uint64;
      description
        "DATA MEM0 ECC 2BIT ERR CNT";
    }
    leaf data-mem1-ecc-2bit-err-cnt {
      type uint64;
      description
        "DATA MEM1 ECC 2BIT ERR CNT";
    }
    leaf data-mem2-ecc-2bit-err-cnt {
      type uint64;
      description
        "DATA MEM2 ECC 2BIT ERR CNT";
    }
    leaf diag-pkt-cnt {
      type uint64;
      description
        "DIAG PKT CNT";
    }
    leaf pkt-sent-to-disabled-port {
      type uint64;
      description
        "PKT SENT TO DISABLED PORT";
    }
    leaf pkt-fpoe-match-hit-cnt {
      type uint64;
      description
        "PKT FPOE MATCH HIT CNT";
    }
    leaf pkt-null-poe-sent-cnt {
      type uint64;
      description
        "PKT NULL POE SENT CNT";
    }
    leaf pkt-fpoe-addr-rng-hit-cnt {
      type uint64;
      description
        "PKT FPOE ADDR RNG HIT CNT";
    }
    leaf di-hdr-len-err-pkt-cnt {
      type uint64;
      description
        "DI HDR LEN ERR PKT CNT";
    }
    leaf di-err-pkt-cnt {
      type uint64;
      description
        "DI ERR PKT CNT";
    }
    leaf fpoe-mem-ecc-1bit-err-cnt {
      type uint64;
      description
        "FPOE MEM ECC 1BIT ERR CNT";
    }
    leaf fpoe-mem-ecc-2bit-err-cnt {
      type uint64;
      description
        "FPOE MEM ECC 2BIT ERR CNT";
    }
    leaf pkts-sent-to-mx-cnt {
      type uint64;
      description
        "PKTS SENT TO MX CNT";
    }
    leaf cpp-head-drop-pkt-from-ma-cnt {
      type uint64;
      description
        "CPP HEAD DROP PKT FROM MA CNT";
    }
    leaf tr-head-drop-pkt-from-ma-cnt {
      type uint64;
      description
        "TR HEAD DROP PKT FROM MA CNT";
    }
    leaf tr-pkt-sent-to-mx {
      type uint64;
      description
        "TR PKT SENT TO MX";
    }
    leaf stop-thrsh-hit-cnt {
      type uint64;
      description
        "STOP THRSH HIT CNT";
    }
    leaf rate-cnt {
      type uint64;
      description
        "RATE CNT";
    }
    leaf calc-rate {
      type uint64;
      description
        "Ingress Multicast Rate";
    }
    leaf crc-stomp-pkt-cnt {
      type uint64;
      description
        "CRC STOMP PKT CNT";
    }
  }

  grouping XBAR-EDM-SM15-PI-UC-STATS {
    description
      "XBAR EDM SM15 PI UC STATS";
    leaf pkt-rcv-cnt {
      type uint64;
      description
        "PKT RCV CNT";
    }
    leaf pkt-seq-err-cnt {
      type uint64;
      description
        "PKT SEQ ERR CNT";
    }
    leaf in-coming-pkt-err-cnt {
      type uint64;
      description
        "INCOMING PKT ERR CNT";
    }
    leaf min-pkt-len-err-cnt {
      type uint64;
      description
        "MIN PKT LEN ERR CNT";
    }
    leaf max-pkt-len-err-cnt {
      type uint64;
      description
        "MAX PKT LEN ERR CNT";
    }
    leaf line-err-drp-pkt {
      type uint64;
      description
        "LINE ERR DRP PKT";
    }
    leaf pkt-crc-err-cnt {
      type uint64;
      description
        "PKT CRC ERR CNT";
    }
    leaf pkt-cfh-crc-err-cnt {
      type uint64;
      description
        "PKT CFH CRC ERR CNT";
    }
    leaf line-s-written-in-mem0 {
      type uint64;
      description
        "LINES WRITTEN IN MEM0";
    }
    leaf line-s-written-in-mem1 {
      type uint64;
      description
        "LINES WRITTEN IN MEM1";
    }
    leaf line-s-written-in-mem2 {
      type uint64;
      description
        "LINES WRITTEN IN MEM2";
    }
    leaf tail-drp-pkt-cnt {
      type uint64;
      description
        "TAIL DRP PKT CNT";
    }
    leaf uc0-data-mem-ecc-1bit-err-cnt {
      type uint64;
      description
        "UC0 DATA MEM ECC 1BIT ERR CNT";
    }
    leaf uc1-data-mem-ecc-1bit-err-cnt {
      type uint64;
      description
        "UC1 DATA MEM ECC 1BIT ERR CNT";
    }
    leaf uc2-data-mem-ecc-1bit-err-cnt {
      type uint64;
      description
        "UC2 DATA MEM ECC 1BIT ERR CNT";
    }
    leaf uc0-data-mem-ecc-2bit-err-cnt {
      type uint64;
      description
        "UC0 DATA MEM ECC 2BIT ERR CNT";
    }
    leaf uc1-data-mem-ecc-2bit-err-cnt {
      type uint64;
      description
        "UC1 DATA MEM ECC 2BIT ERR CNT";
    }
    leaf uc2-data-mem-ecc-2bit-err-cnt {
      type uint64;
      description
        "UC2 DATA MEM ECC 2BIT ERR CNT";
    }
    leaf diag-pkt-cnt {
      type uint64;
      description
        "DIAG PKT CNT";
    }
    leaf pkt-sent-to-disabled-port-cnt {
      type uint64;
      description
        "PKT SENT TO DISABLED PORT CNT";
    }
    leaf pkt-null-poe-sent-ua0-cnt {
      type uint64;
      description
        "PKT NULL POE SENT UA0 CNT";
    }
    leaf pkt-null-poe-sent-ua1-cnt {
      type uint64;
      description
        "PKT NULL POE SENT UA1 CNT";
    }
    leaf pkt-null-poe-sent-ua2-cnt {
      type uint64;
      description
        "PKT NULL POE SENT UA2 CNT";
    }
    leaf pkt-fpoe-addr-rng-hit-cnt {
      type uint64;
      description
        "PKT FPOE ADDR RNG HIT CNT";
    }
    leaf fpoe-mem-ecc-1bit-err-cnt {
      type uint64;
      description
        "FPOE MEM ECC 1BIT ERR CNT";
    }
    leaf fpoe-mem-ecc-2bit-err-cnt {
      type uint64;
      description
        "FPOE MEM ECC 2BIT ERR CNT";
    }
    leaf pkts-sent-to-ux0-cnt {
      type uint64;
      description
        "PKTS SENT TO UX0 CNT";
    }
    leaf pkts-sent-to-ux1-cnt {
      type uint64;
      description
        "PKTS SENT TO UX1 CNT";
    }
    leaf pkts-sent-to-ux2-cnt {
      type uint64;
      description
        "PKTS SENT TO UX2 CNT";
    }
    leaf cpp-head-drop-pkt-cnt {
      type uint64;
      description
        "CPP HEAD DROP PKT CNT";
    }
    leaf tr-head-drop-pkt-cnt {
      type uint64;
      description
        "TR HEAD DROP PKT CNT";
    }
    leaf tr-pkt-sent-to-ux {
      type uint64;
      description
        "TR PKT SENT TO UX";
    }
    leaf stop-thrsh-hit-cnt {
      type uint64;
      description
        "STOP THRSH HIT CNT";
    }
    leaf rate-cnt {
      type uint64;
      description
        "RATE CNT";
    }
    leaf calc-rate {
      type uint64;
      description
        "Ingress Unicast Rate";
    }
    leaf crc-stomp-pkt-cnt {
      type uint64;
      description
        "CRC STOMP PKT CNT";
    }
  }

  grouping XBAR-EDM-SM15-PE-STATS {
    description
      "XBAR EDM SM15 PE STATS";
    leaf total-rate1-cnt {
      type uint64;
      description
        "TOTAL RATE1 CNT";
    }
    leaf total-rate2-cnt {
      type uint64;
      description
        "TOTAL RATE2 CNT";
    }
    leaf total-rate3-cnt {
      type uint64;
      description
        "TOTAL RATE3 CNT";
    }
    leaf total-calc-rate {
      type uint64;
      description
        "Egress Total Rate";
    }
    leaf mc2uc-preempt-cnt {
      type uint64;
      description
        "MC2UC PREEMPT CNT";
    }
  }

  grouping XBAR-EDM-SM15-PI-STATS {
    description
      "XBAR EDM SM15 PI STATS";
    leaf total-rate1-cnt {
      type uint64;
      description
        "TOTAL RATE1 CNT";
    }
    leaf total-rate2-cnt {
      type uint64;
      description
        "TOTAL RATE2 CNT";
    }
    leaf total-rate3-cnt {
      type uint64;
      description
        "TOTAL RATE3 CNT";
    }
    leaf total-calc-rate {
      type uint64;
      description
        "Ingress Total Rate";
    }
  }

  grouping XBAR-EDM-SM15-CA-STATS {
    description
      "XBAR EDM SM15 CA STATS";
    leaf dest-drop-pkt-cnt {
      type uint64;
      description
        "DEST DROP PKT CNT";
    }
    leaf src-dest-pkt-cnt {
      type uint64;
      description
        "SRC DEST PKT CNT";
    }
    leaf dest-src-pkt-cnt {
      type uint64;
      description
        "DEST SRC PKT CNT";
    }
    leaf rcv-pkt-cnt {
      type uint64;
      description
        "RCV PKT CNT";
    }
    leaf tx-pkt-cnt {
      type uint64;
      description
        "TX PKT CNT";
    }
    leaf rx-drop-pkt-cnt {
      type uint64;
      description
        "RX DROP PKT CNT";
    }
  }

  grouping XBAR-EDM-SM15-MA-STATS {
    description
      "XBAR EDM SM15 MA STATS";
    leaf dest-drop-pkt-cnt {
      type uint64;
      description
        "DEST DROP PKT CNT";
    }
    leaf src-dest-pkt-cnt {
      type uint64;
      description
        "SRC DEST PKT CNT";
    }
    leaf dest-src-pkt-cnt {
      type uint64;
      description
        "DEST SRC PKT CNT";
    }
    leaf rcv-pkt-cnt {
      type uint64;
      description
        "RCV PKT CNT";
    }
    leaf tx-pkt-cnt {
      type uint64;
      description
        "TX PKT CNT";
    }
    leaf rx-drop-pkt-cnt {
      type uint64;
      description
        "RX DROP PKT CNT";
    }
    leaf rx-re-transmit-cnt {
      type uint64;
      description
        "RX RETRANSMIT CNT";
    }
    leaf rx-fabric-to-cnt {
      type uint64;
      description
        "RX FABRIC TO CNT";
    }
    leaf rx-hol-to-cnt {
      type uint64;
      description
        "RX HOL TO CNT";
    }
  }

  grouping XBAR-EDM-SM15-UA-STATS {
    description
      "XBAR EDM SM15 UA STATS";
    leaf dest-drop-pkt-cnt {
      type uint64;
      description
        "DEST DROP PKT CNT";
    }
    leaf src-dest-pkt-cnt {
      type uint64;
      description
        "SRC DEST PKT CNT";
    }
    leaf dest-src-pkt-cnt {
      type uint64;
      description
        "DEST SRC PKT CNT";
    }
    leaf rcv-pkt-cnt {
      type uint64;
      description
        "RCV PKT CNT";
    }
    leaf tx-pkt-cnt {
      type uint64;
      description
        "TX PKT CNT";
    }
    leaf rx-drop-pkt-cnt {
      type uint64;
      description
        "RX DROP PKT CNT";
    }
    leaf rx-fabric-to-cnt {
      type uint64;
      description
        "RX FABRIC TO CNT";
    }
    leaf ack-wait-cnt {
      type uint64;
      description
        "ACK WAIT CNT";
    }
  }

  grouping XBAR-EDM-SM15-PORT-STATS {
    description
      "XBAR EDM SM15 PORT STATS";
    container ua0-stats {
      description
        "Unicast Arbiter0 stats";
      uses XBAR-EDM-SM15-UA-STATS;
    }
    container ua1-stats {
      description
        "Unicast Arbiter1 stats";
      uses XBAR-EDM-SM15-UA-STATS;
    }
    container ua2-stats {
      description
        "Unicast Arbiter2 stats";
      uses XBAR-EDM-SM15-UA-STATS;
    }
    container ma-stats {
      description
        "Multicast Arbiter stats";
      uses XBAR-EDM-SM15-MA-STATS;
    }
    container ca-stats {
      description
        "Control Cast stats";
      uses XBAR-EDM-SM15-CA-STATS;
    }
    container pi-stats {
      description
        "Port Ingress stats";
      uses XBAR-EDM-SM15-PI-STATS;
    }
    container pe-stats {
      description
        "Port Egress stats";
      uses XBAR-EDM-SM15-PE-STATS;
    }
    container pi-uc-stats {
      description
        "Ingress Unicast stats";
      uses XBAR-EDM-SM15-PI-UC-STATS;
    }
    container pi-mc-stats {
      description
        "Ingress Multicast stats";
      uses XBAR-EDM-SM15-PI-MC-STATS;
    }
    container pi-cc-stats {
      description
        "Ingress Control Cast stats";
      uses XBAR-EDM-SM15-PI-CC-STATS;
    }
    container pe-uc-stats {
      description
        "Egress Unicast stats";
      uses XBAR-EDM-SM15-PE-UC-STATS;
    }
    container pe-mc-stats {
      description
        "Egress Multicast stats";
      uses XBAR-EDM-SM15-PE-MC-STATS;
    }
    container pe-cc-stats {
      description
        "Egress Control Cast stats";
      uses XBAR-EDM-SM15-PE-CC-STATS;
    }
    leaf internal-err-cnt {
      type uint64;
      description
        "Internal Error Count";
    }
  }
}
