module Cisco-IOS-XR-sysadmin-fretta-envmon-types {
  namespace "http://www.cisco.com/ns/yang/Cisco-IOS-XR-sysadmin-fretta-envmon-types";
  prefix envmon-types;

  import Cisco-IOS-XR-sysadmin-types {
    prefix calvados;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains definitions
     for the Calvados model objects.

     Copyright (c) 2012-2020 by Cisco Systems, Inc.
     All rights reserved.";

  revision 2022-08-05 {
    semver:module-version "1.1.0";
    description
      "Add gen2 common low power CLI.";
  }
  revision 2019-04-15 {
    semver:module-version "1.0.0";
    description
      "Establish semantic version baseline.";
  }
  revision 2018-11-14 {
    description
      "Namespace change to keep it with accordance to the RFC";
  }
  revision 2018-04-09 {
    description
      "Required changes for ConfD 6.4.5";
  }
  revision 2017-11-27 {
    description
      "Add graceful shutdown disable CLI.";
  }
  revision 2017-07-31 {
    description
      "Changing the namespace to follow Cisco guidelines on naming convention";
  }
  revision 2017-05-01 {
    description
      "Namespace change to comply with Cisco guidelines on namespace";
  }

  typedef num_pm {
    type uint32 {
      range "0..5";
    }
  }

  grouping fan-speed-group {
    container raise-fan-speed {
      container all {
        leaf speed_pwm {
          type uint32 {
            range "0..100";
          }
        }
      }
      container rack_loc {
        list location {
          key "rackId";
          leaf rackId {
            type calvados:rack-id;
          }
          leaf speed_pwm {
            type uint32 {
              range "0..100";
            }
          }
        }
      }
    }
  }

  grouping fan-ctrl-optics-group {
    container fan-ctrl-optics {
      container enable {
        container rack_loc {
          leaf all {
            type empty;
          }
          list location {
            key "rackId";
            leaf rackId {
              type calvados:rack-id;
            }
          }
        }
      }
    }
  }

  grouping gen2-common-lowpower-group {
    container gen2-common-lowpower {
      container enable {
        container rack_loc {
          leaf all {
            type empty;
          }
          list location {
            key "rackId";
            leaf rackId {
              type calvados:rack-id;
            }
          }
        }
      }
    }
  }

  grouping vin-uv-shut-group {
    container graceful-shutdown {
      container disable {
        container rack_loc {
          leaf all {
            type empty;
          }
          list location {
            key "rackId";
            leaf rackId {
              type calvados:rack-id;
            }
          }
        }
      }
    }
  }
}
