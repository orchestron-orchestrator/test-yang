submodule Cisco-IOS-XR-platforms-common-dnx-infra-oper-sub1 {
  belongs-to Cisco-IOS-XR-platforms-common-dnx-infra-oper {
    prefix Cisco-IOS-XR-platforms-common-dnx-infra-oper;
  }

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR platforms-common-dnx-infra package operational data.

     Copyright (c) 2013-2019 by Cisco Systems, Inc.
     All rights reserved.";

  revision 2019-04-05 {
    semver:module-version "1.0.0";
    description
      "Establish semantic version baseline.";
  }
  revision 2015-11-09 {
    description
      "IOS XR 6.0 revision.";
  }

  typedef Dnx-mdb-profiles {
    type enumeration {
      enum "mdb-profile-not-applicable" {
        value 0;
        description
          "MDB Profile Not Applicable";
      }
      enum "mdb-profile-l3-max" {
        value 1;
        description
          "MDB Profile L3MAX";
      }
      enum "mdb-profile-l3-max-se" {
        value 2;
        description
          "MDB Profile L3MAX-SE";
      }
      enum "mdb-profile-l2-max" {
        value 3;
        description
          "MDB Profile L2MAX";
      }
      enum "mdb-profile-l2-max-se" {
        value 4;
        description
          "MDB Profile L2MAX_SE";
      }
      enum "mdb-profile-balanced" {
        value 5;
        description
          "MDB Profile BALANCED";
      }
      enum "mdb-profile-max" {
        value 6;
        description
          "MDB Profile Invalid";
      }
    }
    description
      "Dnx mdb profiles";
  }

  typedef Dnx-npu-op-mode {
    type enumeration {
      enum "compatibility" {
        description
          "NPU operating mode - Compatibility mode";
      }
      enum "native" {
        description
          "NPU operating mode - Native mode";
      }
      enum "not-applicable" {
        description
          "NPU operating mode - Not Applicable";
      }
    }
    description
      "Dnx npu op mode";
  }

  grouping DNX-MDB-SCALE-PROFILE-ST {
    description
      "DNX MDB SCALE PROFILE ST";
    leaf mdb-scale-profile {
      type Dnx-mdb-profiles;
      description
        "mdb scale profile configured/derived on the
         system";
    }
  }

  grouping DNX-NPU-OP-MODE-ST {
    description
      "DNX NPU OP MODE ST";
    leaf npu-op-mode {
      type Dnx-npu-op-mode;
      description
        "NPU operating mode - native or compatability
         mode";
    }
  }
}
