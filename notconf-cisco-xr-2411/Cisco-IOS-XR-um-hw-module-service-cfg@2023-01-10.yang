module Cisco-IOS-XR-um-hw-module-service-cfg {
  namespace "http://cisco.com/ns/yang/Cisco-IOS-XR-um-hw-module-service-cfg";
  prefix um-hw-module-service-cfg;

  import Cisco-IOS-XR-types {
    prefix xr;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR hw-module-service package configuration.

     This YANG module augments the
     modules with configuration data.

     Copyright (c) 2023 by Cisco Systems, Inc.
     All rights reserved.";

  revision 2023-01-10 {
    semver:module-version "1.1.0";
    description
      "added cgn for must statement
       2022-12-01
         Added cgn container";
  }
  revision 2020-08-24 {
    semver:module-version "1.0.0";
    description
      "Initial release";
  }

  container hw-module {
    description
      "Configure h/w module";
    container service {
      description
        "Configure service role.";
      container locations {
        description
          "Location to configure";
        list location {
          must "offline or firewall or cgn";
          key "location-name";
          description
            "Location to configure";
          leaf location-name {
            type xr:Node-id;
            description
              "Location to configure";
          }
          container cgn {
            presence "Indicates an cgn node is configured.";
            description
              "Take all services on the card cgn";
          }
          container offline {
            presence "Indicates an offline node is configured.";
            description
              "Take all services on the card offline";
          }
          container firewall {
            presence "Indicates an firewall node is configured.";
            description
              "Configure the firewall service as the role for a node";
          }
        }
      }
    }
  }
}
