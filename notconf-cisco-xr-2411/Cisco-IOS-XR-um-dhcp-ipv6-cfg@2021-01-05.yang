module Cisco-IOS-XR-um-dhcp-ipv6-cfg {
  namespace "http://cisco.com/ns/yang/Cisco-IOS-XR-um-dhcp-ipv6-cfg";
  prefix um-dhcp-ipv6-cfg;

  import Cisco-IOS-XR-types {
    prefix xr;
  }
  import ietf-inet-types {
    prefix inet;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR dhcp-ipv6 package configuration.

     This YANG module augments the
     modules with configuration data.

     Copyright (c) 2020-2022 by Cisco Systems, Inc.
     All rights reserved.";

  revision 2021-01-05 {
    semver:module-version "1.0.0";
    description
      "Initial release";
  }

  container dhcp {
    description
      "Dynamic Host Configuration Protocol";
    container ipv6 {
      presence "Indicates a ipv6 node is configured.";
      description
        "Configure IPv6 DHCP";
      container profiles {
        description
          "Create or enter a profile";
        list profile {
          key "profile-name";
          description
            "Create or enter a profile";
          leaf profile-name {
            type xr:Cisco-ios-xr-string {
              length "1..800" {
                description
                  "Profile name";
              }
            }
            description
              "Create or enter a profile";
          }
          container cnbng {
            presence "Indicates a cnbng node is configured.";
            description
              "Create or enter cnbng profile";
          }
          container proxy {
            presence "Indicates a proxy node is configured.";
            description
              "Create or enter proxy profile";
            list interface {
              key "interface-name";
              description
                "Specify physical interface for interface-id option";
              leaf interface-name {
                type xr:Interface-name;
                description
                  "Specify physical interface for interface-id option";
              }
              leaf interface-id {
                type xr:Cisco-ios-xr-string {
                  length "1..800" {
                    description
                      "Interface ID";
                  }
                }
                description
                  "Physical interface ID";
              }
            }
            container relay {
              description
                "Specify relay configuration";
              container option {
                description
                  "Specify relay option configuration";
                leaf link-layer-addr {
                  type enumeration {
                    enum "set" {
                      value 4;
                      description
                        "Insert Received LinkLayerAddr Value from SADB";
                    }
                  }
                  description
                    "Enter link-layer-addr value";
                }
                leaf subscriber-id {
                  type enumeration {
                    enum "pppoe" {
                      value 3;
                      description
                        "Insert Received Subscriber-ID Value from SADB";
                    }
                  }
                  description
                    "Enter subscriber-id value";
                }
                leaf remote-id {
                  type xr:Cisco-ios-xr-string {
                    length "1..256" {
                      description
                        "Remote ID";
                    }
                  }
                  description
                    "Enter remote-id value";
                }
                container pppoe {
                  must "../remote-id";
                  presence "Indicates a pppoe node is configured.";
                  description
                    "Set remote-id value from SADB";
                }
                container interface-id {
                  description
                    "Interface Id option";
                  leaf insert {
                    type enumeration {
                      enum "local" {
                        value 0;
                        description
                          "Insert locally generated/configured Interface ID value";
                      }
                      enum "received" {
                        value 1;
                        description
                          "Insert received Interface ID value";
                      }
                      enum "pppoe" {
                        value 2;
                        description
                          "Insert received Interface ID value from SADB";
                      }
                      enum "received-nodefault" {
                        value 3;
                        description
                          "No default Interface ID";
                      }
                    }
                    description
                      "Insert options for Interface Id";
                  }
                }
              }
            }
            leaf source-interface {
              type xr:Interface-name;
              description
                "Create or enter proxy profile Source Interface Name";
            }
            leaf link-address {
              type inet:ipv6-address-no-zone;
              description
                "Link Address";
            }
            container sessions {
              description
                "Change sessions configuration";
              container mac {
                presence "Indicates a mac node is configured.";
                description
                  "Throttle DHCP sessions based on MAC address";
                leaf throttle {
                  type uint32 {
                    range "1..65535" {
                      description
                        "Number of solicits at which to throttle";
                    }
                  }
                  must "../throttle-request-period";
                  mandatory true;
                  description
                    "Throttle DHCP sessions from any one MAC address";
                }
                leaf throttle-request-period {
                  type uint32 {
                    range "1..100" {
                      description
                        "Throttle request period (in secs)";
                    }
                  }
                  must "../throttle";
                  mandatory true;
                  description
                    "Throttle request period (in secs)";
                }
                leaf throttle-blocking-period {
                  type uint32 {
                    range "1..100" {
                      description
                        "Throttle blocking period (in secs)";
                    }
                  }
                  mandatory true;
                  description
                    "Throttle blocking period (in secs)";
                }
              }
            }
            container route-add-disable {
              presence "Indicates a route-add-disable node is configured.";
              description
                "Disable route add if interface is down";
            }
            container l2ac-route-add-disable {
              presence "Indicates a l2ac-route-add-disable node is configured.";
              description
                "Disable l2ac route add if interface is down";
            }
            container linkaddress-from-ra-enable {
              presence "Indicates a linkaddress-from-ra-enable node is configured.";
              description
                "Fill linkaddress in Relay fwd msg with Prefix from Router Advertisement for PPPoE sessions";
            }
            container authentication {
              description
                "Authentication username format";
              container username {
                description
                  "Set username";
                container duid {
                  presence "Indicates a duid node is configured.";
                  description
                    "Set username as DUID";
                }
              }
            }
            container helper-address {
              description
                "Configure relay destination";
              container vrfs {
                description
                  "Specify server VRF";
                list vrf {
                  key "vrf-name";
                  description
                    "VRF name";
                  leaf vrf-name {
                    type union {
                      type string {
                        pattern "default" {
                          description
                            "Default VRF";
                        }
                      }
                      type xr:Cisco-ios-xr-string {
                        length "1..32" {
                          description
                            "VRF name";
                        }
                      }
                    }
                    description
                      "VRF name";
                  }
                  list ipv6-address {
                    must "interface or any-output-interface";
                    key "address";
                    description
                      "IPv6 address";
                    leaf address {
                      type inet:ipv6-address-no-zone;
                      description
                        "IPv6 address";
                    }
                    leaf interface {
                      type xr:Interface-name;
                      description
                        "Output Interface";
                    }
                    container any-output-interface {
                      presence "Indicates a any-output-interface node is configured.";
                      description
                        "Any Output Interface";
                    }
                  }
                }
              }
            }
            container classes {
              description
                "Create or enter proxy profile class";
              list class {
                key "class-name";
                description
                  "Create or enter proxy profile class";
                leaf class-name {
                  type xr:Cisco-ios-xr-string {
                    length "1..64" {
                      description
                        "Class name";
                    }
                  }
                  description
                    "Create or enter proxy profile class";
                }
                container helper-address {
                  description
                    "Specify the server helper address";
                  container vrfs {
                    description
                      "Specify server VRF";
                    list vrf {
                      key "vrf-name";
                      description
                        "VRF name";
                      leaf vrf-name {
                        type union {
                          type string {
                            pattern "default" {
                              description
                                "Default VRF";
                            }
                          }
                          type xr:Cisco-ios-xr-string {
                            length "1..32" {
                              description
                                "VRF name";
                            }
                          }
                        }
                        description
                          "VRF name";
                      }
                      list ipv6-address {
                        key "address";
                        description
                          "Server address";
                        leaf address {
                          type inet:ipv6-address-no-zone;
                          description
                            "Server address";
                        }
                      }
                    }
                  }
                }
                leaf link-address {
                  type inet:ipv6-address-no-zone;
                  description
                    "Link Address";
                }
              }
            }
          }
          container server {
            presence "Indicates a server node is configured.";
            description
              "Create or enter server profile";
            container classes {
              description
                "Create or enter server profile class";
              list class {
                key "class-name";
                description
                  "Create or enter server profile class";
                leaf class-name {
                  type xr:Cisco-ios-xr-string {
                    length "1..64" {
                      description
                        "class name";
                    }
                  }
                  description
                    "Create or enter server profile class";
                }
                container dns-server {
                  description
                    "DNS servers";
                  leaf-list ipv6-address {
                    type inet:ipv6-address-no-zone;
                    max-elements 8;
                    description
                      "Server's IPv6 address";
                  }
                }
                leaf domain-name {
                  type xr:Cisco-ios-xr-string {
                    length "1..64" {
                      description
                        "Domain name";
                    }
                  }
                  description
                    "Domain name";
                }
                leaf address-pool {
                  type xr:Cisco-ios-xr-string {
                    length "1..64" {
                      description
                        "Address pool name";
                    }
                  }
                  description
                    "Address pool";
                }
                leaf prefix-pool {
                  type xr:Cisco-ios-xr-string {
                    length "1..64" {
                      description
                        "Prefix pool name";
                    }
                  }
                  description
                    "Prefix pool";
                }
                leaf preference {
                  type uint32 {
                    range "1..255" {
                      description
                        "Preference value";
                    }
                  }
                  description
                    "DHCP Server Preference";
                }
                container lease {
                  description
                    "lease";
                  container infinite {
                    must "not(../days)";
                    presence "Indicates a infinite node is configured.";
                    description
                      "Infinite lease";
                  }
                  leaf days {
                    type uint32 {
                      range "0..365" {
                        description
                          "Days";
                      }
                    }
                    must "not(../infinite)";
                    description
                      "Days";
                  }
                  leaf hours {
                    type uint32 {
                      range "0..23" {
                        description
                          "Hours";
                      }
                    }
                    must "../days";
                    must "../days";
                    description
                      "Hours";
                  }
                  leaf minutes {
                    type uint32 {
                      range "0..59" {
                        description
                          "Minutes";
                      }
                    }
                    must "../hours";
                    must "../hours";
                    description
                      "Minutes";
                  }
                }
              }
            }
            container dns-server {
              description
                "DNS servers";
              leaf-list ipv6-address {
                type inet:ipv6-address-no-zone;
                max-elements 8;
                description
                  "Server's IPv6 address";
              }
            }
            leaf domain-name {
              type xr:Cisco-ios-xr-string {
                length "1..64" {
                  description
                    "Domain name";
                }
              }
              description
                "Domain name";
            }
            leaf aftr-name {
              type xr:Cisco-ios-xr-string {
                length "1..64" {
                  description
                    "AFTR name";
                }
              }
              description
                "AFTR name";
            }
            container lease {
              description
                "lease";
              container infinite {
                must "not(../days)";
                presence "Indicates a infinite node is configured.";
                description
                  "Infinite lease";
              }
              leaf days {
                type uint32 {
                  range "0..365" {
                    description
                      "Days";
                  }
                }
                must "not(../infinite)";
                description
                  "Days";
              }
              leaf hours {
                type uint32 {
                  range "0..23" {
                    description
                      "Hours";
                  }
                }
                must "../days";
                must "../days";
                description
                  "Hours";
              }
              leaf minutes {
                type uint32 {
                  range "0..59" {
                    description
                      "Minutes";
                  }
                }
                must "../hours";
                must "../hours";
                description
                  "Minutes";
              }
            }
            leaf address-pool {
              type xr:Cisco-ios-xr-string {
                length "1..64" {
                  description
                    "Address pool name";
                }
              }
              description
                "Address pool";
            }
            leaf prefix-pool {
              type xr:Cisco-ios-xr-string {
                length "1..64" {
                  description
                    "Prefix pool name";
                }
              }
              description
                "Prefix pool";
            }
            leaf preference {
              type uint32 {
                range "0..255" {
                  description
                    "Preference value";
                }
              }
              description
                "DHCP Server Preference";
            }
            container rapid-commit {
              presence "Indicates a rapid-commit node is configured.";
              description
                "Allow RAPID Commit";
            }
            container aaa {
              description
                "Enable aaa dhcpv6 option force-insert";
              container dhcpv6-option {
                description
                  "Enable aaa dhcpv6 option force-insert";
                container force-insert {
                  presence "Indicates a force-insert node is configured.";
                  description
                    "Enable aaa dhcpv6 option force-insert";
                }
              }
            }
            container sessions {
              description
                "Change sessions configuration";
              container mac {
                presence "Indicates a mac node is configured.";
                description
                  "Throttle DHCP sessions based on MAC address";
                leaf throttle {
                  type uint32 {
                    range "1..65535" {
                      description
                        "Number of solicits at which to throttle";
                    }
                  }
                  must "../throttle-request-period";
                  mandatory true;
                  description
                    "Throttle DHCP sessions from any one MAC address";
                }
                leaf throttle-request-period {
                  type uint32 {
                    range "1..100" {
                      description
                        "Throttle request period (in secs)";
                    }
                  }
                  must "../throttle";
                  mandatory true;
                  description
                    "Throttle request period (in secs)";
                }
                leaf throttle-blocking-period {
                  type uint32 {
                    range "1..100" {
                      description
                        "Throttle blocking period (in secs)";
                    }
                  }
                  mandatory true;
                  description
                    "Throttle blocking period (in secs)";
                }
              }
            }
            container option {
              description
                "DHCPv6 options";
              container option-17-vendor-options {
                description
                  "Vendor options";
                leaf hex {
                  type xr:Cisco-ios-xr-string {
                    length "1..512" {
                      description
                        "Vendor options";
                    }
                  }
                  description
                    "Input value in hex format";
                }
              }
            }
            container duid {
              description
                "Client DUID";
              leaf allowed-type {
                type uint32 {
                  range "1..4" {
                    description
                      "Type of DUID to be allowed";
                  }
                }
                description
                  "Allowed DUID type";
              }
            }
            container match {
              description
                "DHCPv6 match";
              container option {
                description
                  "DHCPv6 match option";
                container enterprise-id {
                  description
                    "match enterprise number";
                  container default {
                    description
                      "defaut action for enterprise number";
                    leaf action {
                      type enumeration {
                        enum "allow" {
                          value 0;
                          description
                            "Allow vendor specific DHCP Solicit";
                        }
                        enum "drop" {
                          value 1;
                          description
                            "Drop vendor specific DHCP Solicit";
                        }
                      }
                      description
                        "action on class-id match";
                    }
                  }
                  container hexes {
                    description
                      "defaut action for enterprise number";
                    list hex {
                      key "enterprise-id";
                      description
                        "defaut action for enterprise number";
                      leaf enterprise-id {
                        type xr:Cisco-ios-xr-string {
                          length "1..8" {
                            description
                              "Enterprise Id";
                          }
                          pattern "[a-zA-Z0-9]+";
                        }
                        description
                          "defaut action for enterprise number";
                      }
                      leaf action {
                        type enumeration {
                          enum "allow" {
                            value 0;
                            description
                              "Allow vendor specific DHCP Solicit";
                          }
                          enum "drop" {
                            value 1;
                            description
                              "Drop vendor specific DHCP Solicit";
                          }
                        }
                        description
                          "action on class-id match";
                      }
                    }
                  }
                }
                container vendor-class {
                  description
                    "match vendor class";
                  container default {
                    description
                      "default action for enterprise number";
                    leaf action {
                      type enumeration {
                        enum "allow" {
                          value 0;
                          description
                            "Allow vendor specific DHCP Solicit";
                        }
                        enum "drop" {
                          value 1;
                          description
                            "Drop vendor specific DHCP Solicit";
                        }
                      }
                      description
                        "action on class-id match";
                    }
                  }
                  container strings {
                    description
                      "string action for vendor number";
                    list string {
                      key "vendor-class";
                      description
                        "string action for vendor number";
                      leaf vendor-class {
                        type string {
                          length "1..64" {
                            description
                              "Vendor class";
                          }
                          pattern "[\"].*.[\"]";
                        }
                        description
                          "string action for vendor number";
                      }
                      leaf action {
                        type enumeration {
                          enum "allow" {
                            value 0;
                            description
                              "Allow vendor specific DHCP Solicit";
                          }
                          enum "drop" {
                            value 1;
                            description
                              "Drop vendor specific DHCP Solicit";
                          }
                        }
                        description
                          "action on class-id match";
                      }
                    }
                  }
                }
              }
            }
            container enable-vlan-intf-session-limit {
              presence "Indicates a enable-vlan-intf-session-limit node is configured.";
              description
                "Enable vlan or interface session limit";
            }
          }
          container relay {
            presence "Indicates a relay node is configured.";
            description
              "Create or enter relay profile";
            container helper-address {
              description
                "Specify the server helper address";
              container vrfs {
                description
                  "Specify server VRF";
                list vrf {
                  key "vrf-name";
                  description
                    "VRF name";
                  leaf vrf-name {
                    type union {
                      type string {
                        pattern "default" {
                          description
                            "Default VRF";
                        }
                      }
                      type xr:Cisco-ios-xr-string {
                        length "1..32" {
                          description
                            "VRF name";
                        }
                      }
                    }
                    description
                      "VRF name";
                  }
                  list ipv6-address {
                    key "address";
                    description
                      "Server Global unicast address";
                    leaf address {
                      type inet:ipv6-address-no-zone;
                      description
                        "Server Global unicast address";
                    }
                    leaf interface {
                      type xr:Interface-name;
                      description
                        "Helper-address Specific Source Interface";
                    }
                  }
                }
              }
            }
            container option {
              description
                "Specify relay option configuration";
              leaf remote-id {
                type xr:Cisco-ios-xr-string {
                  length "1..256" {
                    description
                      "Remote ID";
                  }
                }
                description
                  "Enter remote-id value";
              }
            }
            container iana-route-add {
              presence "Indicates a iana-route-add node is configured.";
              description
                "Enable route addition for IANA";
            }
            leaf source-interface {
              type xr:Interface-name;
              description
                "Relay profile Source Interface Name";
            }
            container route-add-disable {
              presence "Indicates a route-add-disable node is configured.";
              description
                "Disable route add if interface is down";
            }
            container l2ac-route-add-disable {
              presence "Indicates a l2ac-route-add-disable node is configured.";
              description
                "Disable l2ac route add if interface is down";
            }
            leaf link-address {
              type inet:ipv6-address-no-zone;
              description
                "Link Address";
            }
          }
          container base {
            presence "Indicates a base node is configured.";
            description
              "Create or enter base profile";
            container match {
              description
                "Enter match option";
              container mode-classes {
                description
                  "Specify PPP/IPoE class option";
                list mode-class {
                  must "server or proxy";
                  key "mode-class-name";
                  description
                    "Specify PPP/IPoE class option";
                  leaf mode-class-name {
                    type xr:Cisco-ios-xr-string {
                      length "1..64" {
                        description
                          "Class name";
                      }
                    }
                    description
                      "Specify PPP/IPoE class option";
                  }
                  leaf profile {
                    type xr:Cisco-ios-xr-string {
                      length "1..64" {
                        description
                          "Profile name";
                      }
                    }
                    mandatory true;
                    description
                      "Enter proxy or server profile";
                  }
                  container server {
                    must "not(../proxy)";
                    presence "Indicates a server node is configured.";
                    description
                      "Server mode";
                  }
                  container proxy {
                    must "not(../server)";
                    presence "Indicates a proxy node is configured.";
                    description
                      "Proxy mode";
                  }
                }
              }
            }
            container match-default {
              must "profile and server";
              presence "Indicates a match-default node is configured.";
              description
                "Default match option";
              leaf profile {
                type xr:Cisco-ios-xr-string {
                  length "1..64" {
                    description
                      "Profile name";
                  }
                }
                must "../server";
                description
                  "Enter server profile";
              }
              container server {
                must "../profile";
                presence "Indicates a server node is configured.";
                description
                  "Server mode";
              }
            }
            container dhcpv6-to-aaa {
              description
                "Enable to provide the list of options need to send to aaa";
              container option {
                description
                  "option type";
                container list {
                  description
                    "List of options";
                  container all {
                    must "not(../option-number1)";
                    presence "Indicates a all node is configured.";
                    description
                      "Allow all DHCP option to AAA";
                  }
                  leaf option-number1 {
                    type uint32 {
                      range "1..255" {
                        description
                          "Option number";
                      }
                    }
                    must "not(../all)";
                    description
                      "Option number";
                  }
                  leaf option-number2 {
                    type uint32 {
                      range "1..255" {
                        description
                          "Option number";
                      }
                    }
                    must "../option-number1";
                    description
                      "Option number";
                  }
                  leaf option-number3 {
                    type uint32 {
                      range "1..255" {
                        description
                          "Option number";
                      }
                    }
                    must "../option-number2";
                    description
                      "Option number";
                  }
                  leaf option-number4 {
                    type uint32 {
                      range "1..255" {
                        description
                          "Option number";
                      }
                    }
                    must "../option-number3";
                    description
                      "Option number";
                  }
                  leaf option-number5 {
                    type uint32 {
                      range "1..255" {
                        description
                          "Option number";
                      }
                    }
                    must "../option-number4";
                    description
                      "Option number";
                  }
                  leaf option-number6 {
                    type uint32 {
                      range "1..255" {
                        description
                          "Option number";
                      }
                    }
                    must "../option-number5";
                    description
                      "Option number";
                  }
                  leaf option-number7 {
                    type uint32 {
                      range "1..255" {
                        description
                          "Option number";
                      }
                    }
                    must "../option-number6";
                    description
                      "Option number";
                  }
                  leaf option-number8 {
                    type uint32 {
                      range "1..255" {
                        description
                          "Option number";
                      }
                    }
                    must "../option-number7";
                    description
                      "Option number";
                  }
                  leaf option-number9 {
                    type uint32 {
                      range "1..255" {
                        description
                          "Option number";
                      }
                    }
                    must "../option-number8";
                    description
                      "Option number";
                  }
                  leaf option-number10 {
                    type uint32 {
                      range "1..255" {
                        description
                          "Option number";
                      }
                    }
                    must "../option-number9";
                    description
                      "Option number";
                  }
                  leaf option-number11 {
                    type uint32 {
                      range "1..255" {
                        description
                          "Option number";
                      }
                    }
                    must "../option-number10";
                    description
                      "Option number";
                  }
                  leaf option-number12 {
                    type uint32 {
                      range "1..255" {
                        description
                          "Option number";
                      }
                    }
                    must "../option-number11";
                    description
                      "Option number";
                  }
                }
              }
            }
          }
        }
      }
      container interfaces {
        description
          "Assign a profile to interface";
        list interface {
          key "interface-name";
          description
            "Interface to configure";
          leaf interface-name {
            type xr:Interface-name;
            description
              "Interface to configure";
          }
          container base {
            description
              "Assign a base profile to interface";
            leaf profile {
              type xr:Cisco-ios-xr-string {
                length "1..64" {
                  description
                    "Profile name";
                }
              }
              description
                "Enter profile name";
            }
          }
          container proxy {
            description
              "Assign a proxy profile to interface";
            leaf profile {
              type xr:Cisco-ios-xr-string {
                length "1..64" {
                  description
                    "Profile name";
                }
              }
              description
                "Enter profile name";
            }
          }
          container server {
            description
              "Assign a server profile to interface";
            leaf profile {
              type xr:Cisco-ios-xr-string {
                length "1..64" {
                  description
                    "Profile name";
                }
              }
              description
                "Enter profile name";
            }
          }
          container relay {
            description
              "Assign a relay profile to interface";
            leaf profile {
              type xr:Cisco-ios-xr-string {
                length "1..64" {
                  description
                    "Profile name";
                }
              }
              description
                "Enter profile name";
            }
          }
          container cnbng {
            description
              "Assign a cnbng profile to interface";
            leaf profile {
              type xr:Cisco-ios-xr-string {
                length "1..64" {
                  description
                    "Profile name";
                }
              }
              description
                "Enter profile name";
            }
          }
          container subscriber-pppoe {
            description
              "PPPoE subscriber interface";
            leaf profile {
              type xr:Cisco-ios-xr-string {
                length "1..64" {
                  description
                    "Profile name";
                }
              }
              description
                "Enter profile name";
            }
          }
        }
      }
      container allow-duid-change {
        presence "Indicates a allow-duid-change node is configured.";
        description
          "For BNG session, allow duid change for a client MAC";
      }
      leaf inner-cos {
        type uint32 {
          range "0..7" {
            description
              "inner cos value 0-7";
          }
        }
        description
          "Inner cos values for DHCPv6 packets to wards clients";
      }
      leaf outer-cos {
        type uint32 {
          range "0..7" {
            description
              "Outer cos value 0-7";
          }
        }
        description
          "Configure outer cos values for DHCPv6 packet to wards client";
      }
      container database {
        presence "Indicates a database node is configured.";
        description
          "Enable DHCP binding database storage to file system";
        container proxy {
          presence "Indicates a proxy node is configured.";
          description
            "Enable DHCP proxy binding database storage to file system";
        }
        container server {
          presence "Indicates a server node is configured.";
          description
            "Enable DHCP server binding database storage to file system";
        }
        container relay {
          presence "Indicates a relay node is configured.";
          description
            "Enable DHCP relay binding database storage to file system";
        }
        leaf full-write-interval {
          type uint32 {
            range "1..1440" {
              description
                "Enter full file write interval (minutes)";
            }
          }
          description
            "Full file write interval (default 10 minutes)";
        }
        leaf incremental-write-interval {
          type uint32 {
            range "1..1440" {
              description
                "Enter incremental file write interval (minutes)";
            }
          }
          description
            "Incremental file write interval (default 1 minute)";
        }
      }
      container rate-limit {
        description
          "Rate limit ingress packets";
        leaf period {
          type uint32 {
            range "1..1000" {
              description
                "Period in msec (Default: 200 msec)";
            }
          }
          must "../solicit";
          description
            "Rate limiter period in msec";
        }
        leaf solicit {
          type uint32 {
            range "0..1000" {
              description
                "Number of Solicit packets (Default: 100, 0: No limit)";
            }
          }
          must "../period";
          description
            "Rate limit SOLICIT packets";
        }
      }
      container hop-count-seed {
        presence "Indicates a hop-count-seed node is configured.";
        description
          "Start hop count to 0 in relay-forward msg for SOLICIT";
      }
      leaf ipoe-dhcp-client-reboot {
        type uint32 {
          range "10..30" {
            description
              "timed wait in seconds";
          }
        }
        description
          "For BNG, timed wait for term a session";
      }
      container handle-jumbo-packet {
        presence "Indicates a handle-jumbo-packet node is configured.";
        description
          "Handle packets of huge size";
      }
    }
  }
}
