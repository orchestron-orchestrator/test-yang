module Cisco-IOS-XR-hw-module-cfg-deviations {
  namespace "http://cisco.com/ns/yang/Cisco-IOS-XR-hw-module-cfg-deviations";
  prefix cisco-ios-xr-hw-module-cfg-dev;

  import Cisco-IOS-XR-hw-module-cfg {
    prefix hw-module-cfg;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a set of deviations of HW-module cfg data
     model set for Cisco IOS-XR.

     Copyright (c) 2013-2020, 2022-2023 by Cisco Systems, Inc.
     All rights reserved.";

  revision 2022-02-24 {
    description
      "Added deviation for ejector close";
  }
  revision 2020-05-27 {
    description
      "Initial revision applicable to IOS-XR 7. 3. 1 and older releases";
  }

  deviation "/hw-module-cfg:hw-module/hw-module-cfg:nodes/hw-module-cfg:node/hw-module-cfg:config/hw-module-cfg:auto-reset-disable" {
    deviate not-supported;
  }
  deviation "/hw-module-cfg:hw-module/hw-module-cfg:nodes/hw-module-cfg:node/hw-module-cfg:config/hw-module-cfg:attention-led" {
    deviate not-supported;
  }
  deviation "/hw-module-cfg:wait-ejector-close" {
    deviate not-supported;
  }
  deviation "/hw-module-cfg:hw-module/hw-module-cfg:nodes/hw-module-cfg:node/hw-module-cfg:config/hw-module-cfg:fault-recovery-count" {
    deviate not-supported;
  }
}
