module Cisco-IOS-XR-uea-optics-driver-im-mode-cfg {
  namespace "http://cisco.com/ns/yang/Cisco-IOS-XR-uea-optics-driver-im-mode-cfg";
  prefix uea-optics-driver-im-mode-cfg;

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR uea-optics-driver-im-mode package configuration.

     This module contains definitions
     for the following management objects:
       node: HW module IM mode Config

     Copyright (c) 2013-2021 by Cisco Systems, Inc.
     All rights reserved.";

  revision 2021-07-13 {
    semver:module-version "1.0.0";
    description
      "Schema added.";
  }
  revision 2019-04-05 {
    description
      "Establish semantic version baseline.";
  }
  revision 2015-11-09 {
    description
      "IOS XR 6.0 revision.";
  }

  container node {
    description
      "HW module IM mode Config";
    container slot-configs {
      description
        "slot configuration";
      list slot-config {
        key "id1";
        description
          "none";
        leaf im-mode {
          type uint32;
          description
            "im-mode 0 or 1";
        }
        leaf id1 {
          type uint32;
          description
            "none";
        }
      }
    }
  }
}
