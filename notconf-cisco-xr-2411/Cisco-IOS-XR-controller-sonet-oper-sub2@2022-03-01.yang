submodule Cisco-IOS-XR-controller-sonet-oper-sub2 {
  belongs-to Cisco-IOS-XR-controller-sonet-oper {
    prefix Cisco-IOS-XR-controller-sonet-oper;
  }

  import ietf-yang-types {
    prefix yang;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR controller-sonet package operational data.

     Copyright (c) 2013-2022 by Cisco Systems, Inc.
     All rights reserved.";

  revision 2022-03-01 {
    semver:module-version "1.0.0";
    description
      "Added LED state field to port common info";
  }
  revision 2022-02-15 {
    description
      "64 byte trace mode added to j0_info";
  }
  revision 2019-04-05 {
    description
      "Establish semantic version baseline.";
  }
  revision 2015-11-09 {
    description
      "IOS XR 6.0 revision.";
  }

  typedef Sonet-path-ains-state-et {
    type enumeration {
      enum "none" {
        value 0;
        description
          "None";
      }
      enum "active-running" {
        value 1;
        description
          "Running";
      }
      enum "active-pending" {
        value 2;
        description
          "Pending";
      }
    }
    description
      "Sonet path ains state et";
  }

  typedef Service-type-info {
    type enumeration {
      enum "mde-unequip" {
        value 0;
        description
          "mde unequip";
      }
      enum "mde-equip-unspecified" {
        value 1;
        description
          "mde equip unspecified";
      }
      enum "mde-c12" {
        value 2;
        description
          "mde c12";
      }
      enum "mde-c12-e1" {
        value 3;
        description
          "mde c12 e1";
      }
      enum "mde-c11" {
        value 4;
        description
          "mde c11";
      }
      enum "mde-c11-t1" {
        value 5;
        description
          "mde c11 t1";
      }
      enum "mde-vt15" {
        value 6;
        description
          "mde vt15";
      }
      enum "mde-vt15-t1" {
        value 7;
        description
          "mde vt15 t1";
      }
      enum "mde-vt2" {
        value 8;
        description
          "mde vt2";
      }
      enum "mde-t3" {
        value 9;
        description
          "mde t3";
      }
      enum "mde-e3" {
        value 10;
        description
          "mde e3";
      }
      enum "mde-pos-scrambled" {
        value 11;
        description
          "mde pos scrambled";
      }
      enum "mde-pos-unscrambled" {
        value 12;
        description
          "mde pos unscrambled";
      }
      enum "mde-atm" {
        value 13;
        description
          "mde atm";
      }
      enum "mde-tug3" {
        value 14;
        description
          "mde tug3";
      }
      enum "mde-unknown" {
        value 15;
        description
          "mde unknown";
      }
    }
    description
      "Service type info";
  }

  typedef Trace-mode-info-enum {
    type enumeration {
      enum "trace-mode-invalid" {
        description
          "trace mode invalid";
      }
      enum "trace-mode-16" {
        description
          "trace mode 16";
      }
      enum "trace-mode-64" {
        description
          "trace mode 64";
      }
    }
    description
      "Trace mode info enum";
  }

  typedef Sonet-path-state-et {
    type enumeration {
      enum "not-ready" {
        value 0;
        description
          "Not Ready";
      }
      enum "admin-down" {
        value 1;
        description
          "Admin Down";
      }
      enum "down" {
        value 2;
        description
          "Down";
      }
      enum "up" {
        value 3;
        description
          "Up";
      }
      enum "shutdown" {
        value 4;
        description
          "Shutdown";
      }
      enum "error-disable" {
        value 5;
        description
          "Error Disable";
      }
      enum "down-immediate" {
        value 6;
        description
          "Down Immediate";
      }
      enum "down-immediate-admin" {
        value 7;
        description
          "Down Immediate Admin";
      }
      enum "down-graceful" {
        value 8;
        description
          "Down Graceful";
      }
      enum "begin-shutdown" {
        value 9;
        description
          "Begin Shutdown";
      }
      enum "end-shutdown" {
        value 10;
        description
          "End Shutdown";
      }
      enum "begin-error-disable" {
        value 11;
        description
          "Begin Error Disable";
      }
      enum "end-error-disable" {
        value 12;
        description
          "End Error Disable";
      }
      enum "begin-down-graceful" {
        value 13;
        description
          "Begin Down Graceful";
      }
      enum "reset" {
        value 14;
        description
          "Reset";
      }
      enum "operational" {
        value 15;
        description
          "Operational";
      }
      enum "not-operational" {
        value 16;
        description
          "Not Operational";
      }
      enum "unknown" {
        value 17;
        description
          "Unknown";
      }
      enum "last" {
        value 18;
        description
          "Last";
      }
    }
    description
      "Sonet path state et";
  }

  typedef Sonet-path-sec-state {
    type enumeration {
      enum "normal" {
        value 0;
        description
          "Normal";
      }
      enum "maintenance" {
        value 1;
        description
          "Maintenance";
      }
      enum "ains" {
        value 2;
        description
          "Automatic In Service";
      }
    }
    description
      "Sonet path sec state";
  }

  typedef Sonet-derived-admin-state {
    type enumeration {
      enum "in-service" {
        description
          "In Service";
      }
      enum "out-of-service" {
        description
          "Out of Service";
      }
      enum "maintenance" {
        description
          "Maintenance";
      }
    }
    description
      "Sonet derived admin state";
  }

  grouping SONET-PATH-AINS-HW-INFO {
    description
      "AINS information";
    leaf ains-state {
      type Sonet-path-ains-state-et;
      description
        "AINS State";
    }
    leaf ains-timer-minutes {
      type uint32;
      units "minute";
      description
        "AINS Timer in Minutes";
    }
    leaf ains-remaining-secs {
      type uint32;
      units "second";
      description
        "AINS Remaining Seconds";
    }
  }

  grouping PTR-INFO {
    description
      "SPE pointer info";
    leaf new-pointer {
      type uint64;
      description
        "New Pointer events counter";
    }
    leaf pse {
      type uint64;
      description
        "Positive Stuffing Events counter";
    }
    leaf nse {
      type uint64;
      description
        "Negative Stuffing Events counter";
    }
  }

  grouping C2-INFO {
    description
      "C2 overhead byte (path signal label) info";
    leaf is-stable {
      type boolean;
      description
        "If stable C2 byte";
    }
    leaf receive-c2 {
      type yang:hex-string;
      description
        "Received C2 byte";
    }
    leaf transmit-c2 {
      type yang:hex-string;
      description
        "Transmitted C2 byte";
    }
    leaf source-c2 {
      type int8;
      description
        "Source of the C2 value";
    }
  }

  grouping J1-INFO {
    description
      "J1 overhead byte (path trace) info";
    leaf is-stable {
      type boolean;
      description
        "If stable J1 trace";
    }
    leaf mode {
      type Trace-mode-info-enum;
      description
        "J1 Trace mode";
    }
    leaf trace-buffer {
      type string {
        length "0..62";
      }
      description
        "J1 trace buffer";
    }
  }

  grouping SONET-PATH-BER-INFO {
    description
      "error block info";
    leaf is-masked {
      type boolean;
      description
        "Are errors masked?";
    }
    leaf is-asserted {
      type boolean;
      description
        "Is threshold crossed?";
    }
    leaf threshold {
      type uint8;
      description
        "Error threshold power";
    }
    leaf count {
      type uint64;
      description
        "Error counter";
    }
  }

  grouping SONET-PATH-ALARM-INFO {
    description
      "defect/alarm info";
    leaf alarm-name {
      type string {
        length "0..10";
      }
      description
        "Name of alarm";
    }
    leaf is-masked {
      type boolean;
      description
        "Is defect masked?";
    }
    leaf is-detected {
      type boolean;
      description
        "Is defect detected?";
    }
    leaf count {
      type uint64;
      description
        "Alarm counter";
    }
  }

  grouping SONET-PATH-INFO {
    description
      "Path operational info";
    container path-bip {
      description
        "Path BIP (B3) BER info";
      uses SONET-PATH-BER-INFO;
    }
    container febe {
      description
        "FEBE info";
      uses SONET-PATH-BER-INFO;
    }
    container j1-trasmit {
      description
        "J1 Transmit info";
      uses J1-INFO;
    }
    container j1-receive {
      description
        "J1 Receive info";
      uses J1-INFO;
    }
    container j1-expected {
      description
        "J1 Expected info";
      uses J1-INFO;
    }
    container c2 {
      description
        "C2 byte info";
      uses C2-INFO;
    }
    container spe-pointer {
      description
        "SPE pointer info";
      uses PTR-INFO;
    }
    container au-pointer {
      description
        "AU pointer info";
      uses PTR-INFO;
    }
    container ains-info {
      description
        "AINS information";
      uses SONET-PATH-AINS-HW-INFO;
    }
    leaf data-rate {
      type uint32;
      description
        "Data rate";
    }
    leaf scrambling-mode {
      type uint32;
      description
        "Scrambling mode";
    }
    leaf derived-state {
      type Sonet-derived-admin-state;
      description
        "derived state";
    }
    leaf sec-admin-state {
      type Sonet-path-sec-state;
      description
        "sec admin state";
    }
    leaf operational-state {
      type Sonet-path-state-et;
      description
        "Port's IM state";
    }
    leaf service {
      type Service-type-info;
      description
        "Service Type";
    }
    leaf pm {
      type boolean;
      description
        "PM enable/Disable";
    }
    list alarm {
      max-elements 6;
      description
        "List of alarms";
      uses SONET-PATH-ALARM-INFO;
    }
  }
}
