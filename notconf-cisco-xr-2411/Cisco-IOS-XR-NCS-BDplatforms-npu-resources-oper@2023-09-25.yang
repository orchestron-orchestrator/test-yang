module Cisco-IOS-XR-NCS-BDplatforms-npu-resources-oper {
  namespace "http://cisco.com/ns/yang/Cisco-IOS-XR-NCS-BDplatforms-npu-resources-oper";
  prefix ncs-bdplatforms-npu-resources-oper;

  import cisco-semver {
    prefix semver;
  }
  import Cisco-IOS-XR-platforms-ofa-oper {
    prefix a1;
  }

  include Cisco-IOS-XR-NCS-BDplatforms-npu-resources-oper-sub1 {
    revision-date 2023-09-25;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR NCS-BDplatforms-npu-resources package operational data.

     This YANG module augments the
       Cisco-IOS-XR-platforms-ofa-oper
     module with state data.

     Copyright (c) 2013-2023 by Cisco Systems, Inc.
     All rights reserved.";

  revision 2023-09-25 {
    semver:module-version "3.0.0";
    description
      "Updated to add high watermark for resources
       2022-11-29
         Updated yang structure to include keyed lists
       2022-09-26
         Updated to remove unused fields
       2022-08-25
         mcid ingress and egress tracking added
       2022-05-11
         encap all phases resources tracking added
       2022-05-09
         sexem2 and isem1,isem2 resource tracking added
       2022-04-01
         rif and inlif tracking added";
  }
  revision 2020-10-09 {
    semver:module-version "2.0.0";
    description
      "Updated task id in root oper";
  }
  revision 2019-12-14 {
    semver:module-version "1.2.0";
    description
      "Updated date for npu resources model";
  }
  revision 2019-04-05 {
    semver:module-version "1.0.0";
    description
      "Establish semantic version baseline.";
  }
  revision 2015-11-09 {
    description
      "IOS XR 6.0 revision.";
  }

  typedef Resource {
    type enumeration {
      enum "lem" {
        value 0;
        description
          "lem";
      }
      enum "lpm" {
        value 1;
        description
          "lpm";
      }
      enum "encap" {
        value 2;
        description
          "encap";
      }
      enum "ext-tcam-ipv4" {
        value 3;
        description
          "ext tcam ipv4";
      }
      enum "ext-tcam-ipv6-short" {
        value 4;
        description
          "ext tcam ipv6 short";
      }
      enum "ext-tcam-ipv6-long" {
        value 5;
        description
          "ext tcam ipv6 long";
      }
      enum "fec" {
        value 6;
        description
          "fec";
      }
      enum "ecmp-fec" {
        value 7;
        description
          "ecmp fec";
      }
      enum "ext-tcam-ipv6" {
        value 8;
        description
          "ext tcam ipv6";
      }
      enum "rif" {
        value 9;
        description
          "rif";
      }
      enum "inlif" {
        value 10;
        description
          "inlif";
      }
      enum "inlif1" {
        value 11;
        description
          "inlif1";
      }
      enum "inlif2" {
        value 12;
        description
          "inlif2";
      }
      enum "sexem2" {
        value 13;
        description
          "sexem2";
      }
      enum "isem1" {
        value 14;
        description
          "isem1";
      }
      enum "isem2" {
        value 15;
        description
          "isem2";
      }
      enum "encap-arp" {
        value 16;
        description
          "encap ARP";
      }
      enum "encap-tunnel-s" {
        value 17;
        description
          "encap tunnels";
      }
      enum "encap-ac" {
        value 18;
        description
          "encap AC";
      }
      enum "encap-pwe" {
        value 19;
        description
          "encap PWE";
      }
      enum "mcid-ingress" {
        value 20;
        description
          "mcid ingress";
      }
      enum "mcid-egress" {
        value 21;
        description
          "mcid egress";
      }
    }
    description
      "Resource";
  }

  augment "/a1:ofa/a1:stats/a1:nodes/a1:node" {
    description
      "This augment extends the operational data of
       'Cisco-IOS-XR-platforms-ofa-oper'";
    container hw-resources-datas {
      description
        "OFA hw resources stats ";
      list hw-resources-data {
        key "resource";
        description
          "Hardware resources table";
        leaf resource {
          type Resource;
          description
            "Resource type";
        }
        uses OFA-SYSDB-HW-RESOURCE;
      }
    }
  }
}
