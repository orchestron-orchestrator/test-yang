module Cisco-IOS-XR-um-dynamic-template-cfg {
  namespace "http://cisco.com/ns/yang/Cisco-IOS-XR-um-dynamic-template-cfg";
  prefix um-dynamic-template-cfg;

  import Cisco-IOS-XR-types {
    prefix xr;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR dynamic-template package configuration.

     This YANG module augments the
     modules with configuration data.

     Copyright (c) 2021-2022 by Cisco Systems, Inc.
     All rights reserved.";

  revision 2021-05-10 {
    semver:module-version "1.0.0";
    description
      "Initial release";
  }

  container dynamic-template {
    description
      "Dynamically Applied Configuration Template Definition";
    container type {
      description
        "'type' keyword";
      container ppp {
        description
          "PPP dynamic template type";
        list template {
          key "template-name";
          description
            "Dynamic Template Name";
          leaf template-name {
            type string {
              length "1..64" {
                description
                  "Dynamic Template Name";
              }
            }
            description
              "Dynamic Template Name";
          }
        }
      }
      container ipsubscriber {
        description
          "IP Subscriber dynamic template type";
        list template {
          key "template-name";
          description
            "Dynamic Template Name";
          leaf template-name {
            type string {
              length "1..64" {
                description
                  "Dynamic Template Name";
              }
            }
            description
              "Dynamic Template Name";
          }
        }
      }
      container service {
        description
          "Service dynamic template type";
        list template {
          key "template-name";
          description
            "Dynamic Template Name";
          leaf template-name {
            type xr:Cisco-ios-xr-string {
              length "1..64" {
                description
                  "Dynamic Template Name";
              }
            }
            description
              "Dynamic Template Name";
          }
        }
      }
    }
  }
}
