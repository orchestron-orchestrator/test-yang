submodule Cisco-IOS-XR-osa-hwmod-linesys-oper-sub1 {
  belongs-to Cisco-IOS-XR-osa-hwmod-linesys-oper {
    prefix Cisco-IOS-XR-osa-hwmod-linesys-oper;
  }

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR osa-hwmod-linesys package operational data.

     Copyright (c) 2013-2022 by Cisco Systems, Inc.
     All rights reserved.";

  revision 2022-06-08 {
    semver:module-version "1.0.0";
    description
      "Show Hwmod Enhancement.";
  }
  revision 2019-04-05 {
    description
      "Establish semantic version baseline.";
  }
  revision 2015-11-09 {
    description
      "IOS XR 6.0 revision.";
  }

  typedef Osa-data-chan-state {
    type enumeration {
      enum "nxc" {
        value 0;
        description
          "Channel not cross-connected";
      }
      enum "active" {
        value 1;
        description
          "Channel cross-connected to data port";
      }
      enum "fail" {
        value 2;
        description
          "Channel filled with ASE";
      }
      enum "ase" {
        value 3;
        description
          "Data channel failed, pending transition to ASE";
      }
    }
    description
      "Osa data chan state";
  }

  typedef Slice-config-states {
    type enumeration {
      enum "slice-no-config" {
        value 0;
        description
          "Not Provisioned";
      }
      enum "slice-config-in-progress" {
        value 1;
        description
          "Provisioning In Progress";
      }
      enum "slice-config-complete" {
        value 2;
        description
          "Provisioned";
      }
      enum "slice-config-failure" {
        value 3;
        description
          "Provisioning Failed";
      }
      enum "slice-unconfig-in-progress" {
        value 4;
        description
          "Unprovisioning In Progress";
      }
    }
    description
      "Slice config states";
  }

  grouping OSA-FLEXI-CHAN-INLINE-AMPLI-INFO-B {
    description
      "Inline Ampli Flexi Channel Information";
    leaf channel-number {
      type uint32;
      description
        "ChannelNumber";
    }
    leaf centre-frequency-thz {
      type string {
        length "0..11";
      }
      description
        "CentreFrequencyThz";
    }
    leaf channel-width-ghz {
      type string {
        length "0..11";
      }
      description
        "ChannelWidthGhz";
    }
    list overlapping-channel-info {
      description
        "overlapping channel info";
      uses OSA-FLEXI-CHAN-OVERLAPPING-CHANNEL-INFO-B;
    }
  }

  grouping OSA-HWMOD-INLINE-AMPLI-INFO-B {
    description
      "HWMOD In-Line Amplifier Information";
    leaf status {
      type Slice-config-states;
      description
        "Status";
    }
    list flexi-grid-info {
      description
        "flexi grid info";
      uses OSA-FLEXI-CHAN-INLINE-AMPLI-INFO-B;
    }
  }

  grouping OSA-FLEXI-CHAN-OVERLAPPING-CHANNEL-INFO-B {
    description
      "Overlapping Channels Information";
    leaf left-overlapping-channel {
      type string {
        length "0..5";
      }
      description
        "LeftOverlappingChannel";
    }
    leaf right-overlapping-channel {
      type string {
        length "0..5";
      }
      description
        "RightOverlappingChannel";
    }
  }

  grouping OSA-FLEXI-CHAN-TERMINAL-AMPLI-INFO-B {
    description
      "Terminal Ampli Flexi Channel Information";
    leaf channel-number {
      type uint32;
      description
        "ChannelNumber";
    }
    leaf centre-frequency-thz {
      type string {
        length "0..11";
      }
      description
        "CentreFrequencyThz";
    }
    leaf channel-width-ghz {
      type string {
        length "0..11";
      }
      description
        "ChannelWidthGhz";
    }
    leaf channel-status {
      type Osa-data-chan-state;
      description
        "ChannelStatus";
    }
    list overlapping-channel-info {
      description
        "overlapping channel info";
      uses OSA-FLEXI-CHAN-OVERLAPPING-CHANNEL-INFO-B;
    }
  }

  grouping OSA-HWMOD-TERMINAL-AMPLI-INFO-B {
    description
      "HWMOD Terminal Amplifier Information";
    leaf status {
      type Slice-config-states;
      description
        "Status";
    }
    list flexi-grid-info {
      description
        "flexi grid info";
      uses OSA-FLEXI-CHAN-TERMINAL-AMPLI-INFO-B;
    }
  }
}
