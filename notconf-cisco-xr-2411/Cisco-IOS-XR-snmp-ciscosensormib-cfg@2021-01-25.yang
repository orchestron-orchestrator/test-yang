module Cisco-IOS-XR-snmp-ciscosensormib-cfg {
  namespace "http://cisco.com/ns/yang/Cisco-IOS-XR-snmp-ciscosensormib-cfg";
  prefix snmp-ciscosensormib-cfg;

  import cisco-semver {
    prefix semver;
  }
  import Cisco-IOS-XR-snmp-agent-cfg {
    prefix a1;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR snmp-ciscosensormib package configuration.

     This YANG module augments the
       Cisco-IOS-XR-snmp-agent-cfg
     module with configuration data.

     Copyright (c) 2013-2021 by Cisco Systems, Inc.
     All rights reserved.";

  revision 2021-01-25 {
    semver:module-version "1.0.1";
    description
      "Removed deprecated command CSCvx05102";
  }
  revision 2019-04-05 {
    semver:module-version "1.0.1";
    description
      "Establish semantic version baseline.";
  }
  revision 2017-05-01 {
    description
      "Fixing backward compatibility error in module.";
  }
  revision 2015-11-09 {
    description
      "IOS XR 6.0 revision.";
  }

  augment "/a1:mib" {
    description
      "This augment extends the configuration data of
       'Cisco-IOS-XR-snmp-agent-cfg'";
    leaf sensor-mib-cache {
      type empty;
      description
        "Get cached Sesnsor MIB statistics";
    }
  }
  augment "/a1:snmp/a1:notification" {
    description
      "This augment extends the configuration data of
       'Cisco-IOS-XR-snmp-agent-cfg'";
    container sensor {
      description
        "CISCO-ENTITY-SENSOR-MIB notification
         configuration";
      leaf enable {
        type empty;
        description
          "Enable entitySensorMIB notifications";
      }
    }
  }
}
