module Cisco-IOS-XR-iedge4710-oper {
  namespace "http://cisco.com/ns/yang/Cisco-IOS-XR-iedge4710-oper";
  prefix iedge4710-oper;

  import ietf-inet-types {
    prefix inet;
  }
  import ietf-yang-types {
    prefix yang;
  }
  import Cisco-IOS-XR-types {
    prefix xr;
  }
  import cisco-semver {
    prefix semver;
  }

  include Cisco-IOS-XR-iedge4710-oper-sub2 {
    revision-date 2023-06-03;
  }
  include Cisco-IOS-XR-iedge4710-oper-sub1 {
    revision-date 2023-06-03;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR iedge4710 package operational data.

     This module contains definitions
     for the following management objects:
       subscriber: Subscriber operational data
       iedge-license-manager: Session License Manager Configuration
         data

     Copyright (c) 2013-2023 by Cisco Systems, Inc.
     All rights reserved.";

  revision 2023-06-03 {
    semver:module-version "4.1.0";
    description
      "Added leaf nodes related to COA request, response counts
       2023-02-20
         Added new leaf related to subscriber COA perf stats
       2022-12-22
         Added new leaf related to coa stats.
       2022-09-12
         Added new leaf related to subscriber performance stats
       2022-08-17
         Added srg peer EOMS status in detail internal and disconnect history.
       2021-09-27
         New CLI added to display session summary counters";
  }
  revision 2021-09-03 {
    semver:module-version "4.0.0";
    description
      "Disconnect last sensor path get the chunk of 200 items so enhance this path to per entry to avoid tcp connection flaps between telemetry server and BNG.";
  }
  revision 2020-12-24 {
    semver:module-version "3.0.0";
    description
      "Updated acct stop internal stats.
       2020-11-21
           Added statsd event to session export.
       2020-11-02
           Added yang paths to support ADT
       2020-10-23
           Added disc queue statistics.
       2020-10-09
           Added acct stop statistics.
       2020-08-24
           Added Feature ID to session export.";
  }
  revision 2020-02-20 {
    semver:module-version "2.0.0";
    description
      "Added FADB statistics.
       2020-01-04
         Added disconnect history support.";
  }
  revision 2019-04-05 {
    semver:module-version "1.0.1";
    description
      "Establish semantic version baseline.";
  }
  revision 2018-09-20 {
    description
      "Fixed yang gaps.";
  }
  revision 2015-11-09 {
    description
      "IOS XR 6.0 revision.";
  }

  typedef Subscriber-author-state-filter-flag {
    type enumeration {
      enum "un-authorized" {
        value 0;
        description
          "UnAuthorized";
      }
      enum "authorized" {
        value 1;
        description
          "Authorized";
      }
    }
    description
      "Subscriber author state filter flag";
  }

  typedef Subscriber-srg-oper-filter-flag {
    type enumeration {
      enum "srg-none" {
        value 0;
        description
          "SRG Role None";
      }
      enum "srg-master" {
        value 16384;
        description
          "SRG Role Master";
      }
      enum "srg-slave" {
        value 65536;
        description
          "SRG Role Slave";
      }
      enum "srg-both" {
        value 81920;
        description
          "SRG Role Master Slave";
      }
    }
    description
      "Subscriber srg oper filter flag";
  }

  typedef Subscriber-address-family-filter-flag {
    type enumeration {
      enum "ipv4-only" {
        value 0;
        description
          "IPv4 only";
      }
      enum "ipv6-only" {
        value 1;
        description
          "IPv6 only";
      }
      enum "ipv4-all" {
        value 2;
        description
          "IPv4 all";
      }
      enum "ipv6-all" {
        value 3;
        description
          "IPv6 all";
      }
      enum "dual-all" {
        value 4;
        description
          "Dual all";
      }
      enum "dual-part-up" {
        value 5;
        description
          "Dual part up";
      }
      enum "dual-up" {
        value 6;
        description
          "Dual up";
      }
      enum "lac" {
        value 7;
        description
          "LAC";
      }
    }
    description
      "Subscriber address family filter flag";
  }

  typedef Subscriber-state-filter-flag {
    type enumeration {
      enum "initializing" {
        value 0;
        description
          "Initializing";
      }
      enum "connecting" {
        value 1;
        description
          "Connecting";
      }
      enum "connected" {
        value 2;
        description
          "Connected";
      }
      enum "activated" {
        value 3;
        description
          "Activated";
      }
      enum "idle" {
        value 4;
        description
          "Idle";
      }
      enum "disconnecting" {
        value 5;
        description
          "Disconnecting";
      }
      enum "end" {
        value 6;
        description
          "End";
      }
    }
    description
      "Subscriber state filter flag";
  }

  typedef Subscriber-authen-state-filter-flag {
    type enumeration {
      enum "un-authenticated" {
        value 0;
        description
          "UnAuthenticated";
      }
      enum "authenticated" {
        value 1;
        description
          "Authenticated";
      }
    }
    description
      "Subscriber authen state filter flag";
  }

  container subscriber {
    config false;
    description
      "Subscriber operational data";
    container manager {
      description
        "Subscriber manager operational data";
      container nodes {
        description
          "Subscriber manager list of nodes";
        list node {
          key "node-name";
          description
            "Subscriber manager operational data for a
             particular node";
          container statistics {
            description
              "Subscriber manager statistics";
            container aaa {
              description
                "AAA statistics";
              container aggregate-accounting {
                description
                  "Aggregate accounting statistics";
                uses IEDGE-STATS-COORD-ACCT-DATA;
              }
              container authentication {
                description
                  "Authentication statistics";
                uses IEDGE-STATS-COORD-AUTH-DATA;
              }
              container aggregate-mobility {
                description
                  "Aggregate mobility statistics";
                uses IEDGE-STATS-MOB-DATA;
              }
              container accounting-stop-storage {
                description
                  "Accounting stop storage statistics";
                container stop-details {
                  description
                    "Accounting stop detail statistics";
                  list stop-detail {
                    key "offset-idx";
                    description
                      "Accounting stop detail per record
                       statistics";
                    leaf offset-idx {
                      type xr:Hex-integer;
                      description
                        "Offset index";
                    }
                    uses IEDGE-COORD-STOP-STORAGE-DETAIL-DATA;
                  }
                }
                container stop-summaries {
                  description
                    "Accounting stop summary table statistics";
                  list stop-summary {
                    key "mlist";
                    description
                      "Accounting stop summary per method list
                       statistics";
                    leaf mlist {
                      type xr:Cisco-ios-xr-string;
                      description
                        "method list name";
                    }
                    uses IEDGE-COORD-STOP-STORAGE-SUM-DATA;
                  }
                }
                container stop-internal {
                  description
                    "Accounting stop internal statistics";
                  uses IEDGE-COORD-STOP-STORAGE-INT-DATA;
                }
                container stop-accounting {
                  description
                    "Accounting stop accounting statistics";
                  uses IEDGE-COORD-STOP-STORAGE-ACCT-STATS-DATA;
                }
              }
              container aggregate-authentication {
                description
                  "Aggregate authentication statistics";
                uses IEDGE-STATS-COORD-AUTH-DATA;
              }
              container accounting-stats-all {
                description
                  "Display all subscriber management
                   statistics";
                uses IEDGE-STATS-COORD-ALL-DATA;
              }
              container change-of-authorization {
                description
                  "Change of authorization (COA) statistics";
                uses IEDGE-STATS-CH-DATA;
              }
              container authorization {
                description
                  "Authorization statistics";
                uses IEDGE-STATS-COORD-AUTH-DATA;
              }
              container aggregate-authorization {
                description
                  "Aggregate authorization statistics";
                uses IEDGE-STATS-COORD-AUTH-DATA;
              }
              container aggregate-accounting-stats-all {
                description
                  "Display all subscriber management total
                   statistics";
                uses IEDGE-STATS-COORD-ALL-DATA;
              }
              container accounting {
                description
                  "Accounting statistics";
                uses IEDGE-STATS-COORD-ACCT-DATA;
              }
              container mobility {
                description
                  "Mobility statistics";
                uses IEDGE-STATS-MOB-DATA;
              }
              container aggregate-change-of-authorization {
                description
                  "Aggregate change of authorization (COA)
                   statistics";
                uses IEDGE-STATS-CH-DATA;
              }
            }
            container disconn-last-entries {
              description
                "Disconnect Last Detail";
              list disconn-last-entry {
                key "arrayindex";
                description
                  "Disconnect Last Detail per entry";
                leaf arrayindex {
                  type uint32;
                  description
                    "disconnect array index";
                }
                uses IEDGE-STATS-DISCONNECT-DATA;
              }
            }
            container aggregate-summary {
              description
                "Aggregate summary of statistics";
              uses IEDGE-STATS-SUMMARY-DATA;
            }
            container disconn-unique {
              description
                "Disconnect Unique Summary statistics";
              uses IEDGE-STATS-DISCONNECT-DATA;
            }
            container tracepoints {
              description
                "iedge trace point details";
              list tracepoint {
                key "traceindex";
                description
                  "Specific Taskgroup Information";
                leaf traceindex {
                  type uint32;
                  description
                    "Trace index";
                }
                uses IEDGE-DEBUG-TRACEPOINT-DATA;
              }
            }
            container disc-queue {
              description
                "Disconnect queue statistics";
              uses IEDGE-STATS-DISC-QUEUE-DATA;
            }
            container disconnect-reasons {
              description
                "Disconnect Unique Summary statistics";
              list disconnect-reason {
                key "disc-reason";
                description
                  "Disconnect Unique info";
                leaf disc-reason {
                  type xr:Cisco-ios-xr-string;
                  description
                    "disconnect unique reason details";
                }
                uses IEDGE-DISCONNECT-DATA;
              }
            }
            container fadb {
              description
                "FADB statistics";
              uses IEDGE-STATS-FADB-DATA;
            }
            container srg {
              description
                "Geo Redundancy statistics";
              uses IEDGE-STATS-SRG-DATA;
            }
          }
          leaf node-name {
            type xr:Node-id;
            description
              "Node name";
          }
        }
      }
    }
    container session {
      description
        "Subscriber session operational data";
      container nodes {
        description
          "List of subscriber session supported nodes";
        list node {
          key "node-name";
          description
            "Subscriber session operational data for a
             particular node";
          container srg-roles {
            description
              "List of subscriber session supported srg
               roles";
            list srg-role {
              key "srg";
              description
                "Subscriber session operational data based on
                 srg role";
              container author-summaries {
                description
                  "Summary information filtered by
                   authorization state";
                list author-summary {
                  key "author-state";
                  description
                    "authorization summary";
                  leaf author-state {
                    type Subscriber-author-state-filter-flag;
                    description
                      "Authorization state";
                  }
                  uses SUBSCRIBER-SESSION-SUMMARY;
                }
              }
              container username-summaries {
                description
                  "Summary information filtered by username";
                list username-summary {
                  key "username";
                  description
                    "Username summary";
                  leaf username {
                    type xr:Cisco-ios-xr-string;
                    description
                      "Subscriber username";
                  }
                  uses SUBSCRIBER-SESSION-SUMMARY;
                }
              }
              container mac-summaries {
                description
                  "Summary information filtered by MAC address";
                list mac-summary {
                  key "mac-address";
                  description
                    "MAC address summary";
                  leaf mac-address {
                    type yang:mac-address;
                    description
                      "Subscriber MAC address";
                  }
                  uses SUBSCRIBER-SESSION-SUMMARY;
                }
              }
              container interface-summaries {
                description
                  "Summary information filtered by interface";
                list interface-summary {
                  key "interface-name";
                  description
                    "Interface summary";
                  leaf interface-name {
                    type xr:Interface-name;
                    description
                      "Interface name";
                  }
                  uses SUBSCRIBER-SESSION-SUMMARY;
                }
              }
              container state-summaries {
                description
                  "Summary information filtered by session
                   state";
                list state-summary {
                  key "state";
                  description
                    "State summary";
                  leaf state {
                    type Subscriber-state-filter-flag;
                    description
                      "Subscriber state";
                  }
                  uses SUBSCRIBER-SESSION-SUMMARY;
                }
              }
              container authentication-summaries {
                description
                  "Summary information filtered by
                   authentication state";
                list authentication-summary {
                  key "authentication-state";
                  description
                    "authentication summary";
                  leaf authentication-state {
                    type Subscriber-authen-state-filter-flag;
                    description
                      "Authentication state";
                  }
                  uses SUBSCRIBER-SESSION-SUMMARY;
                }
              }
              container subscriber-sessions {
                description
                  "IP subscriber sessions";
                list subscriber-session {
                  key "session-id";
                  description
                    "Subscriber session information";
                  leaf session-id {
                    type xr:Hex-integer;
                    description
                      "Session ID";
                  }
                  uses SUBSCRIBER-SESSION-DATA;
                }
              }
              container ipv4-address-vrf-summaries {
                description
                  "Summary information filtered by IPv4
                   address and VRF";
                list ipv4-address-vrf-summary {
                  description
                    "IPv4 address and VRF summary";
                  leaf vrf-name {
                    type xr:Cisco-ios-xr-string;
                    description
                      "VRF name";
                  }
                  leaf address {
                    type inet:ipv4-address-no-zone;
                    description
                      "Subscriber IPv4 address";
                  }
                  uses SUBSCRIBER-SESSION-SUMMARY;
                }
              }
              container srg-summary {
                description
                  "Subscriber session summary information";
                uses SUBSCRIBER-SESSION-SUMMARY;
              }
              container access-interface-summaries {
                description
                  "Summary information filtered by access
                   interface";
                list access-interface-summary {
                  key "interface-name";
                  description
                    "Access interface summary";
                  leaf interface-name {
                    type xr:Interface-name;
                    description
                      "Interface name";
                  }
                  uses SUBSCRIBER-SESSION-SUMMARY;
                }
              }
              container address-family-summaries {
                description
                  "Summary information filtered by address
                   family";
                list address-family-summary {
                  key "address-family";
                  description
                    "Address family summary";
                  leaf address-family {
                    type Subscriber-address-family-filter-flag;
                    description
                      "Address family";
                  }
                  uses SUBSCRIBER-SESSION-SUMMARY;
                }
              }
              container ipv4-address-summaries {
                description
                  "Summary information filtered by subscriber
                   IPv4 address";
                list ipv4-address-summary {
                  key "address";
                  description
                    "IPv4 address summary";
                  leaf address {
                    type inet:ipv4-address-no-zone;
                    description
                      "Subscriber IPv4 address";
                  }
                  uses SUBSCRIBER-SESSION-SUMMARY;
                }
              }
              container vrf-summaries {
                description
                  "Summary information filtered by VRF";
                list vrf-summary {
                  key "vrf-name";
                  description
                    "VRF summary";
                  leaf vrf-name {
                    type xr:Cisco-ios-xr-string;
                    description
                      "VRF name";
                  }
                  uses SUBSCRIBER-SESSION-SUMMARY;
                }
              }
              leaf srg {
                type Subscriber-srg-oper-filter-flag;
                description
                  "Subscriber srg role";
              }
            }
          }
          container author-summaries {
            description
              "Summary information filtered by authorization
               state";
            list author-summary {
              key "author-state";
              description
                "authorization summary";
              leaf author-state {
                type Subscriber-author-state-filter-flag;
                description
                  "Authorization state";
              }
              uses SUBSCRIBER-SESSION-SUMMARY;
            }
          }
          container summary {
            description
              "Subscriber session summary information";
            uses SUBSCRIBER-SESSION-SUMMARY;
          }
          container mac-summaries {
            description
              "Summary information filtered by MAC address";
            list mac-summary {
              key "mac-address";
              description
                "MAC address summary";
              leaf mac-address {
                type yang:mac-address;
                description
                  "Subscriber MAC address";
              }
              uses SUBSCRIBER-SESSION-SUMMARY;
            }
          }
          container interface-summaries {
            description
              "Summary information filtered by interface";
            list interface-summary {
              key "interface-name";
              description
                "Interface summary";
              leaf interface-name {
                type xr:Interface-name;
                description
                  "Interface name";
              }
              uses SUBSCRIBER-SESSION-SUMMARY;
            }
          }
          container authentication-summaries {
            description
              "Summary information filtered by
               authentication state";
            list authentication-summary {
              key "authentication-state";
              description
                "authentication summary";
              leaf authentication-state {
                type Subscriber-authen-state-filter-flag;
                description
                  "Authentication state";
              }
              uses SUBSCRIBER-SESSION-SUMMARY;
            }
          }
          container state-summaries {
            description
              "Summary information filtered by session state";
            list state-summary {
              key "state";
              description
                "State summary";
              leaf state {
                type Subscriber-state-filter-flag;
                description
                  "Subscriber state";
              }
              uses SUBSCRIBER-SESSION-SUMMARY;
            }
          }
          container ipv4-address-vrf-summaries {
            description
              "Summary information filtered by IPv4 address
               and VRF";
            list ipv4-address-vrf-summary {
              description
                "IPv4 address and VRF summary";
              leaf vrf-name {
                type xr:Cisco-ios-xr-string;
                description
                  "VRF name";
              }
              leaf address {
                type inet:ipv4-address-no-zone;
                description
                  "Subscriber IPv4 address";
              }
              uses SUBSCRIBER-SESSION-SUMMARY;
            }
          }
          container address-family-summaries {
            description
              "Summary information filtered by address
               family";
            list address-family-summary {
              key "address-family";
              description
                "Address family summary";
              leaf address-family {
                type Subscriber-address-family-filter-flag;
                description
                  "Address family";
              }
              uses SUBSCRIBER-SESSION-SUMMARY;
            }
          }
          container username-summaries {
            description
              "Summary information filtered by username";
            list username-summary {
              key "username";
              description
                "Username summary";
              leaf username {
                type xr:Cisco-ios-xr-string;
                description
                  "Subscriber username";
              }
              uses SUBSCRIBER-SESSION-SUMMARY;
            }
          }
          container access-interface-summaries {
            description
              "Summary information filtered by access
               interface";
            list access-interface-summary {
              key "interface-name";
              description
                "Access interface summary";
              leaf interface-name {
                type xr:Interface-name;
                description
                  "Interface name";
              }
              uses SUBSCRIBER-SESSION-SUMMARY;
            }
          }
          container ipv4-address-summaries {
            description
              "Summary information filtered by subscriber
               IPv4 address";
            list ipv4-address-summary {
              key "address";
              description
                "IPv4 address summary";
              leaf address {
                type inet:ipv4-address-no-zone;
                description
                  "Subscriber IPv4 address";
              }
              uses SUBSCRIBER-SESSION-SUMMARY;
            }
          }
          container vrf-summaries {
            description
              "Summary information filtered by VRF";
            list vrf-summary {
              key "vrf-name";
              description
                "VRF summary";
              leaf vrf-name {
                type xr:Cisco-ios-xr-string;
                description
                  "VRF name";
              }
              uses SUBSCRIBER-SESSION-SUMMARY;
            }
          }
          container sessions {
            description
              "IP subscriber sessions";
            list session {
              key "session-id";
              description
                "Subscriber session information";
              leaf session-id {
                type xr:Hex-integer;
                description
                  "Session ID";
              }
              uses SUBSCRIBER-SESSION-DATA;
            }
          }
          leaf node-name {
            type xr:Node-id;
            description
              "Node name";
          }
        }
      }
    }
  }
  container iedge-license-manager {
    config false;
    description
      "Session License Manager Configuration data";
    container nodes {
      description
        "Session License Manager operational data for a
         location";
      list node {
        key "nodeid";
        description
          "Location. For example, 0/1/CPU0";
        container iedge-license-manager-summary {
          description
            "Display Session License Manager summary data";
          uses ISLM-SUMMARY-DATA;
        }
        leaf nodeid {
          type xr:Node-id;
          description
            "The node id to filter on. For example,
             0/1/CPU0";
        }
      }
    }
  }
}
