module Cisco-IOS-XR-um-asr9k-fabric-cfg {
  namespace "http://cisco.com/ns/yang/Cisco-IOS-XR-um-asr9k-fabric-cfg";
  prefix um-asr9k-fabric-cfg;

  import Cisco-IOS-XR-types {
    prefix xr;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR asr9k-fabric package configuration.

     This YANG module augments the
     modules with configuration data.

     Copyright (c) 2023 by Cisco Systems, Inc.
     All rights reserved.";

  revision 2023-02-15 {
    semver:module-version "2.0.0";
    description
      "Added fabmgr fc_isolation get-config support.
       2022-11-18
         Added arbiter stuck vqi monitor get-config support.
       2022-10-13
         Added fia soft-error-monitor get-config support.
       2022-03-25
         Removed container admin.Removed container highbandwidth from container mode.";
  }
  revision 2020-06-25 {
    semver:module-version "1.0.0";
    description
      "Initial release";
  }

  container fabric {
    description
      "Configure Fabric";
    container enable {
      description
        "Enable fabric operation mode";
      container mode {
        description
          "Choose mode";
        container a99-highbandwidth {
          presence "Indicates a a99-highbandwidth node is configured.";
          description
            "A99 High bandwidth cards only";
        }
      }
    }
    container fabmgr {
      description
        "Configure fabricmgr Settings";
      container fc-isolation {
        presence "Indicates a fc-isolation node is configured.";
        description
          "Isolate FC card if system has N+1 redundancy.";
      }
    }
    container fia {
      description
        "Configure FIA Settings";
      container locations {
        description
          "Location";
        list location {
          key "location-name";
          description
            "Location";
          leaf location-name {
            type xr:Node-id;
            description
              "Location";
          }
          leaf soft-error-monitor {
            type uint32 {
              range "1..2" {
                description
                  "Set 1 to shut ports, 2 to reload LC";
              }
            }
            description
              "Monitor soft errors on FIA and south bound interface of FIA";
          }
        }
      }
    }
    container arbiter {
      description
        "Configure arbiter Settings";
      container stuck-vqi-monitor {
        presence "Indicates a stuck-vqi-monitor node is configured.";
        description
          "Monitor for stuck vqis on central arbiter";
      }
    }
  }
}
