module Cisco-IOS-XR-um-password6-cfg {
  namespace "http://cisco.com/ns/yang/Cisco-IOS-XR-um-password6-cfg";
  prefix um-password6-cfg;

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR password6 package configuration.

     This YANG module augments the
     modules with configuration data.

     Copyright (c) 2020, 2022 by Cisco Systems, Inc.
     All rights reserved.";

  revision 2020-03-23 {
    semver:module-version "1.0.0";
    description
      "Initial release";
  }

  feature type6_parser_check_input_type_with_platform_aes_msg {
    description
      "type6 parser check input type with platform aes msg";
  }

  container password6 {
    description
      "Configure a key password";
    container encryption {
      description
        "Configure a key encryption";
      container aes {
        if-feature "type6_parser_check_input_type_with_platform_aes_msg";
        presence "Indicates a aes node is configured.";
        description
          "Configure a key type aes";
      }
    }
  }
}
