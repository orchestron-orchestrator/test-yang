module Cisco-IOS-XR-timing-sets-hwmod-cfg {
  namespace "http://cisco.com/ns/yang/Cisco-IOS-XR-timing-sets-hwmod-cfg";
  prefix timing-sets-hwmod-cfg;

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR timing-sets-hwmod package configuration.

     This module contains definitions
     for the following management objects:
       tmg-sets-hw-module: Configure timing SETS PD h/w module

     Copyright (c) 2013-2023 by Cisco Systems, Inc.
     All rights reserved.";

  revision 2023-01-31 {
    semver:module-version "1.0.0";
    description
      "Schema added for SETS HW-Mod Config.";
  }
  revision 2019-04-05 {
    description
      "Establish semantic version baseline.";
  }
  revision 2015-11-09 {
    description
      "IOS XR 6.0 revision.";
  }

  typedef Tmg-sets-flt-act {
    type enumeration {
      enum "reload" {
        value 1;
        description
          "Reload the card if SETS fault or trap is
           detected";
      }
    }
    description
      "Tmg sets flt act";
  }

  container tmg-sets-hw-module {
    description
      "Configure timing SETS PD h/w module";
    container tmg-sets-configuration {
      description
        "SETS/TIMING-IC PD configuration";
      leaf fault-act-configuration {
        type Tmg-sets-flt-act;
        description
          "Configure action in case fault is detected";
      }
    }
  }
}
