module Cisco-IOS-XR-um-iidmgr-cfg {
  namespace "http://cisco.com/ns/yang/Cisco-IOS-XR-um-iidmgr-cfg";
  prefix um-iidmgr-cfg;

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR iidmgr package configuration.

     This YANG module augments the
     modules with configuration data.

     Copyright (c) 2021-2022 by Cisco Systems, Inc.
     All rights reserved.";

  revision 2021-06-25 {
    semver:module-version "1.0.0";
    description
      "Initial release";
  }

  container iidmgr {
    description
      "Internal ID Manager";
    container iid {
      description
        "Internal ID configuration";
      leaf holdtime {
        type uint32 {
          range "0..60" {
            description
              "Length of timeout in minutes";
          }
        }
        description
          "Holdtime for stale/freed IID";
      }
    }
  }
}
