module Cisco-IOS-XR-um-hostname-cfg {
  namespace "http://cisco.com/ns/yang/Cisco-IOS-XR-um-hostname-cfg";
  prefix um-hostname-cfg;

  import Cisco-IOS-XR-types {
    prefix xr;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR hostname package configuration.

     This YANG module augments the
     modules with configuration data.

     Copyright (c) 2021-2022 by Cisco Systems, Inc.
     All rights reserved.";

  revision 2021-04-21 {
    semver:module-version "1.0.0";
    description
      "Initial release";
  }

  container hostname {
    description
      "Set system's network name";
    leaf system-network-name {
      type xr:Cisco-ios-xr-string {
        length "1..253" {
          description
            "This system's network name";
        }
        pattern "[a-zA-Z0-9_.-]+";
      }
      description
        "Set system's network name";
    }
  }
}
