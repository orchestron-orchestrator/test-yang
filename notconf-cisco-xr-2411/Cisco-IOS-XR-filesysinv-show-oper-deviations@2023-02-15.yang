module Cisco-IOS-XR-filesysinv-show-oper-deviations {
  namespace "http://cisco.com/ns/yang/Cisco-IOS-XR-filesysinv-show-oper-deviations";
  prefix filesysinv-show-oper-dev;

  import Cisco-IOS-XR-filesysinv-show-oper {
    prefix fsinv;
  }
  import cisco-semver {
    prefix semver;
  }

  organization
    "Cisco Systems, Inc.";
  contact
    "Cisco Systems, Inc.
     Customer Service
     E-mail: cs-yang@cisco.com";
  description
    "This module contains a set of deviations for
     on Cisco IOS-XR devices.
     Copyright (c) 2016-2017, 2019, 2021, 2023 by Cisco Systems, Inc.
     All rights reserved.";

  revision 2023-02-15 {
    semver:module-version "1.0.1";
    description
      "Remove `fsinv:admin/fsinv:snapshot-id` deviation as this is a
       child of a path already marked as `deviate not-supported`";
  }

  deviation "/fsinv:file-system-inventory/fsinv:rack-slots" {
    deviate not-supported;
  }
  deviation "/fsinv:file-system-inventory/fsinv:nodes/fsinv:node/fsinv:snapshot/fsinv:current/fsinv:admin" {
    deviate not-supported;
  }
  deviation "/fsinv:file-system-inventory/fsinv:nodes/fsinv:node/fsinv:snapshot/fsinv:on-demand-all/fsinv:admin" {
    deviate not-supported;
  }
  deviation "/fsinv:file-system-inventory/fsinv:nodes/fsinv:node/fsinv:snapshot/fsinv:all/fsinv:admin" {
    deviate not-supported;
  }
}
