module Cisco-IOS-XR-um-hw-module-early-fast-discard-cfg {
  namespace "http://cisco.com/ns/yang/Cisco-IOS-XR-um-hw-module-early-fast-discard-cfg";
  prefix um-hw-module-early-fast-discard-cfg;

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR hw-module-early-fast-discard package configuration.

     This model is deprecated in 24.1.1 and will be removed
     in a future release.

     This YANG module augments the
     modules with configuration data.

     Copyright (c) 2021-2022, 2024 by Cisco Systems, Inc.
     All rights reserved.";

  revision 2024-01-23 {
    semver:module-version "1.1.0";
    description
      "Deprecated early-fast-discard Yang module in release 24.1.1";
  }
  revision 2020-05-01 {
    semver:module-version "1.0.0";
    description
      "Initial release";
  }

  container hw-module {
    status deprecated;
    description
      "Configure h/w module";
    container early-fast-discard {
      presence "Indicates a early-fast-discard node is configured.";
      description
        "Enable prioritized packet drop during congestion";
      leaf vlan-cos {
        type uint32 {
          range "0..7" {
            description
              "Specify VLAN COS threshold (default = 6)";
          }
        }
        must "../vlan-op";
        description
          "Select VLAN COS values to be treated as high priority";
      }
      leaf vlan-op {
        type enumeration {
          enum "lt" {
            value 2;
            description
              "Less-than";
          }
          enum "ge" {
            value 3;
            description
              "Greater-than-or-equal";
          }
        }
        must "../vlan-cos";
        description
          "Select VLAN operation (default = greater-than-or-equal)";
      }
      leaf ip-prec {
        type uint32 {
          range "0..7" {
            description
              "Specify IP TOS Precedence threshold (default = 6)";
          }
        }
        must "../ip-op";
        description
          "Select IP precedence values to be treated as high priority";
      }
      leaf ip-op {
        type enumeration {
          enum "lt" {
            value 2;
            description
              "Less-than";
          }
          enum "ge" {
            value 3;
            description
              "Greater-than-or-equal";
          }
        }
        must "../ip-prec";
        description
          "Select IP operation (default = greater-than-or-equal)";
      }
      leaf mpls-exp {
        type uint32 {
          range "0..7" {
            description
              "Specify MPLS EXP threshold (default = 6)";
          }
        }
        must "../mpls-op";
        description
          "Select MPLS EXP values to be treated as high priority";
      }
      leaf mpls-op {
        type enumeration {
          enum "lt" {
            value 2;
            description
              "Less-than";
          }
          enum "ge" {
            value 3;
            description
              "Greater-than-or-equal";
          }
        }
        must "../mpls-exp";
        description
          "Select MPLS operation (default = greater-than-or-equal)";
      }
    }
  }
}
