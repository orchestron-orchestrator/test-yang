module Cisco-IOS-XR-um-spanning-tree-cfg {
  namespace "http://cisco.com/ns/yang/Cisco-IOS-XR-um-spanning-tree-cfg";
  prefix um-spanning-tree-cfg;

  import Cisco-IOS-XR-types {
    prefix xr;
  }
  import ietf-yang-types {
    prefix yang;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco spanning-tree package package configuration.

     Copyright (c) 2023 by Cisco Systems, Inc.
     All rights reserved.";

  revision 2023-09-20 {
    semver:module-version "1.0.0";
    description
      "Updating model for um2 changes";
  }
  revision 2022-10-31 {
    description
      "Add in MSTAG startup-bpdus config item";
  }
  revision 2022-09-08 {
    description
      "Initial release";
  }

  container spanning-tree {
    description
      "Configure Spanning Tree Protocol.";
    container repags {
      description
        "Configure REP Access Gateway";
      list repag {
        key "protocol-instance-name interface-name";
        description
          "Enable and Configure REPAG on an interface.";
        leaf protocol-instance-name {
          type xr:Cisco-ios-xr-string {
            length "1..1024";
          }
          description
            "Protocol Instance name";
        }
        leaf interface-name {
          type xr:Interface-name {
            pattern "(((Fast|Gigabit)Ethernet|.*GigE|CPRIoE|CemoHundredGigE)|Bundle-Ether)[^.]*";
          }
          description
            "Interface to REPAG-enable";
        }
        leaf auto-configure-edge {
          type empty;
          description
            "Auto-configure RENN on the edge node of a REP segment.";
        }
        container instances {
          description
            "Enable and Configure an instance on this interface.";
          list instance {
            key "instance-name";
            description
              "Enable and Configure an instance on this interface.";
            leaf instance-name {
              type uint32 {
                range "0..4094" {
                  description
                    "MSTI ID";
                }
              }
              description
                "Enable and Configure an instance on this interface.";
            }
            leaf vlan-ids {
              when "../instance-name != '0'";
              type xr:Cisco-ios-xr-string {
                length "1..1024" {
                  description
                    "List of VLAN Ranges in the form a-b,c,d,e-f,g";
                }
              }
              description
                "Assign ranges of VLANs to the specified MSTI.";
            }
            container root-id {
              description
                "Set the Bridge ID of the root for this instance";
              leaf root-id-mac-address {
                type yang:mac-address;
                description
                  "Set the Bridge ID of the root for this instance";
              }
              leaf startup-value {
                type yang:mac-address;
                must "../root-id-mac-address";
                description
                  "Set the Bridge ID to be used during pre-empt delay";
              }
            }
            container priority {
              description
                "MSTI Priority.";
              leaf priority-number {
                type uint32 {
                  range "0..61440" {
                    description
                      "MSTI Priority. Must be a multiple of 4096.";
                  }
                }
                description
                  "MSTI Priority.";
              }
              leaf startup-value {
                type uint32 {
                  range "0..61440" {
                    description
                      "MSTI Priority. Must be a multiple of 4096.";
                  }
                }
                must "../priority-number";
                description
                  "Set the MSTI Priority to be used during pre-empt delay";
              }
            }
            container port-priority {
              description
                "Priority of this port on this MSTI.";
              leaf port-priority-number {
                type uint32 {
                  range "0..240" {
                    description
                      "Port Priority. Must be a multiple of 16.";
                  }
                }
                description
                  "Priority of this port on this MSTI.";
              }
              leaf startup-value {
                type uint32 {
                  range "0..240" {
                    description
                      "Port Priority. Must be a multiple of 16.";
                  }
                }
                must "../port-priority-number";
                description
                  "Set the priority of this port on this MSTI to be used during pre-empt delay";
              }
            }
            container cost {
              description
                "Cost of this port on this MSTI.";
              leaf cost-number {
                type uint32 {
                  range "1..200000000" {
                    description
                      "Port Cost";
                  }
                }
                description
                  "Cost of this port on this MSTI.";
              }
              leaf startup-value {
                type uint32 {
                  range "1..200000000" {
                    description
                      "Port Cost";
                  }
                }
                must "../cost-number";
                description
                  "Set the cost of this port on this MSTI to be used during pre-empt delay";
              }
            }
            container root-priority {
              description
                "Priority of the root for this instance.";
              leaf root-priority-number {
                type uint32 {
                  range "0..61440" {
                    description
                      "MSTI Priority. Must be a multiple of 4096.";
                  }
                }
                description
                  "Priority of the root for this instance.";
              }
              leaf startup-value {
                type uint32 {
                  range "0..61440" {
                    description
                      "MSTI Priority. Must be a multiple of 4096.";
                  }
                }
                must "../root-priority-number";
                description
                  "Set the priority of the root for this instance to be used during pre-empt delay";
              }
            }
            leaf edge-mode {
              type empty;
              description
                "Enable Access Gateway Edge Mode for this MSTI.";
            }
          }
        }
      }
    }
    container msts {
      description
        "Configure Multiple Spanning Tree Protocol.";
      list mst {
        key "protocol-instance-name";
        description
          "Configure Multiple Spanning Tree Protocol.";
        leaf protocol-instance-name {
          type xr:Cisco-ios-xr-string {
            length "1..1024";
          }
          description
            "Protocol Instance name";
        }
        leaf name {
          type xr:Cisco-ios-xr-string {
            length "1..1024" {
              description
                "Configuration name";
            }
          }
          description
            "Configuration name";
        }
        container bringup {
          description
            "Bringup options.";
          container delay {
            description
              "Bringup delay for newly created interfaces.";
            leaf for {
              type uint32 {
                range "0..3600" {
                  description
                    "Length of time to delay for (hours, minutes, or seconds)";
                }
              }
              must "../time-unit";
              description
                "Specify length of time to delay bringup for";
            }
            leaf time-unit {
              type enumeration {
                enum "SECONDS" {
                  value 0;
                  description
                    "Time is in seconds";
                }
                enum "MINUTES" {
                  value 1;
                  description
                    "Time is in minutes";
                }
                enum "HOURS" {
                  value 2;
                  description
                    "Time is in hours";
                }
              }
              must "(. = 'SECONDS') or (. = 'MINUTES' and ../for <='60') or (. = 'HOURS' and ../for <='1')";
              description
                "Specify length of time to delay bringup for";
            }
          }
        }
        leaf revision-number {
          type uint32 {
            range "0..65535" {
              description
                "Revision number.";
            }
          }
          description
            "Revision number.";
        }
        leaf forward-delay {
          type uint32 {
            range "4..30" {
              description
                "Forward delay time in seconds.";
            }
          }
          description
            "Bridge forward delay time.";
        }
        container maximum {
          description
            "Bridge maximums, such as max-age";
          leaf hops {
            type uint32 {
              range "6..40" {
                description
                  "Bridge Maximum number of hops.";
              }
            }
            description
              "Bridge maximum number of hops.";
          }
          leaf age {
            type uint32 {
              range "6..40" {
                description
                  "Bridge Maximum Age time in seconds.";
              }
            }
            description
              "Bridge Maximum Age time in seconds.";
          }
        }
        container transmit {
          description
            "Bridge transmit options";
          leaf hold-count {
            type uint32 {
              range "1..10" {
                description
                  "Bridge Transmit Hold Count.";
              }
            }
            description
              "Bridge Transmit Hold Count.";
          }
        }
        leaf provider-bridge {
          type empty;
          description
            "Provider Bridge mode.";
        }
        container flush {
          description
            "Flush options";
          container containment {
            description
              "Flush containment options";
            leaf disable {
              type empty;
              description
                "Disable flush containment";
            }
          }
        }
        leaf allow-legacy-bpdu {
          type empty;
          description
            "Permit legacy STP BDPU TCNs to cause flushes";
        }
        container instances {
          description
            "Configure an MSTP instance.";
          list instance {
            key "instance-name";
            description
              "Configure an MSTP instance.";
            leaf instance-name {
              type uint32 {
                range "0..4094" {
                  description
                    "MSTI ID";
                }
              }
              description
                "MSTI ID";
            }
            leaf vlan-ids {
              when "../instance-name != '0'";
              type xr:Cisco-ios-xr-string {
                length "1..1024" {
                  description
                    "List of VLAN Ranges in the form a-b,c,d,e-f,g";
                }
              }
              description
                "Assign ranges of VLANs to the specified MSTI.";
            }
            leaf priority {
              type uint32 {
                range "0..61440" {
                  description
                    "MSTI Priority. Must be a multiple of 4096.";
                }
              }
              description
                "MSTI Priority.";
            }
          }
        }
        container interfaces {
          description
            "Enable and Configure MSTP on an interface.";
          list interface {
            key "interface-name";
            description
              "Enable and Configure MSTP on an interface.";
            leaf interface-name {
              type xr:Interface-name {
                pattern "(((Fast|Gigabit)Ethernet|.*GigE|CPRIoE|CemoHundredGigE)|Bundle-Ether)[^.]*";
              }
              description
                "Interface to MSTP enable";
            }
            leaf external-cost {
              type uint32 {
                range "1..200000000" {
                  description
                    "Interface External Cost.";
                }
              }
              description
                "Interface External Cost.";
            }
            leaf hello-time {
              type uint32 {
                range "1..2" {
                  description
                    "Interface Hello Time in seconds.  Only 2 is supported on bundles.";
                }
              }
              description
                "Interface Hello Time.";
            }
            leaf link-type {
              type enumeration {
                enum "POINT-TO-POINT" {
                  value 0;
                  description
                    "Point to Point link.";
                }
                enum "MULTIPOINT" {
                  value 1;
                  description
                    "Multipoint link.";
                }
              }
              description
                "Configure the Link Type of an Interface.";
            }
            leaf portfast {
              type enumeration {
                enum "PORTFAST-ENABLE" {
                  value 0;
                  description
                    "enable";
                }
                enum "BPDUGUARD" {
                  value 1;
                  description
                    "Enable BPDU Guard on Interface.";
                }
              }
              description
                "Set PortFast on Interface.";
            }
            container guard {
              description
                "Configure bridge guard features";
              leaf root {
                type empty;
                description
                  "Set Guard Root on Interface.";
              }
              leaf topology-change {
                type empty;
                description
                  "Set Guard topology-change on Interface.";
              }
            }
            container instances {
              description
                "MSTI Specific configuration for this interface.";
              list instance {
                key "instance-name";
                description
                  "MSTI Specific configuration for this interface.";
                leaf instance-name {
                  type uint32 {
                    range "0..4094" {
                      description
                        "MSTI ID";
                    }
                  }
                  description
                    "MSTI ID";
                }
                leaf port-priority {
                  type uint32 {
                    range "0..240" {
                      description
                        "Port Priority. Must be a multiple of 16.";
                    }
                  }
                  description
                    "Priority of this port on this MSTI.";
                }
                leaf cost {
                  type uint32 {
                    range "1..200000000" {
                      description
                        "Port Cost";
                    }
                  }
                  description
                    "Cost of this port on this MSTI.";
                }
              }
            }
          }
        }
      }
    }
    container pvrsts {
      description
        "Configure Per-VLAN Rapid Spaning Tree Protocol.";
      list pvrst {
        key "protocol-instance-name";
        description
          "Configure Per-VLAN Rapid Spaning Tree Protocol.";
        leaf protocol-instance-name {
          type xr:Cisco-ios-xr-string {
            length "1..1024";
          }
          description
            "Protocol Instance name";
        }
        leaf forward-delay {
          type uint32 {
            range "4..30" {
              description
                "Forward delay time in seconds.";
            }
          }
          description
            "Bridge forward delay time.";
        }
        container maximum {
          description
            "Bridge maximums";
          leaf age {
            type uint32 {
              range "6..40" {
                description
                  "Bridge Maximum Age time in seconds.";
              }
            }
            description
              "Bridge maximum age time.";
          }
        }
        container transmit {
          description
            "Bridge transmit options";
          leaf hold-count {
            type uint32 {
              range "1..10" {
                description
                  "Bridge Transmit Hold Count.";
              }
            }
            description
              "Bridge Transmit Hold Count.";
          }
        }
        container interfaces {
          description
            "Enable and Configure PVRST on an interface.";
          list interface {
            key "interface-name";
            description
              "Enable and Configure PVRST on an interface.";
            leaf interface-name {
              type xr:Interface-name {
                pattern "(((Fast|Gigabit)Ethernet|.*GigE|CPRIoE|CemoHundredGigE)|Bundle-Ether)[^.]*";
              }
              description
                "Interface to be protected by PVRST";
            }
            leaf hello-time {
              type uint32 {
                range "1..2" {
                  description
                    "Interface Hello Time in seconds.  Only 2 is supported on bundles.";
                }
              }
              description
                "Interface Hello Time.";
            }
            leaf link-type {
              type enumeration {
                enum "POINT-TO-POINT" {
                  value 0;
                  description
                    "Point to Point link.";
                }
                enum "MULTIPOINT" {
                  value 1;
                  description
                    "Multipoint link.";
                }
              }
              description
                "Configure the Link Type of an Interface.";
            }
            leaf portfast {
              type enumeration {
                enum "PORTFAST-ENABLE" {
                  value 0;
                  description
                    "enable";
                }
                enum "BPDUGUARD" {
                  value 1;
                  description
                    "Enable BPDU Guard on Interface.";
                }
              }
              description
                "Set PortFast on Interface.";
            }
            container guard {
              description
                "Configure bridge guard features";
              leaf root {
                type empty;
                description
                  "Set Guard Root on Interface.";
              }
            }
            container vlans {
              description
                "VLAN Specific configuration for this interface.";
              list vlan {
                key "vlan-id";
                description
                  "VLAN Specific configuration for this interface.";
                leaf vlan-id {
                  type uint32 {
                    range "1..4094" {
                      description
                        "VLAN ID";
                    }
                  }
                  description
                    "VLAN ID";
                }
                leaf port-priority {
                  type uint32 {
                    range "0..240" {
                      description
                        "Port Priority. Must be a multiple of 16.";
                    }
                  }
                  description
                    "Priority of this port on this VLAN.";
                }
                leaf cost {
                  type uint32 {
                    range "1..200000000" {
                      description
                        "Port Cost";
                    }
                  }
                  description
                    "Cost of this port on this VLAN.";
                }
              }
            }
          }
        }
        container vlans {
          description
            "Configure PVRST on a VLAN.";
          list vlan {
            key "vlan-id";
            description
              "Configure PVRST on a VLAN.";
            leaf vlan-id {
              type uint32 {
                range "1..4094" {
                  description
                    "VLAN ID";
                }
              }
              description
                "VLAN ID";
            }
            leaf priority {
              type uint32 {
                range "0..61440" {
                  description
                    "Bridge Priority. Must be a multiple of 4096.";
                }
              }
              description
                "Bridge Priority.";
            }
          }
        }
      }
    }
    container pvrstags {
      description
        "Configure PVRST Access Gateway";
      list pvrstag {
        key "protocol-instance-name";
        description
          "Configure PVRST Access Gateway";
        leaf protocol-instance-name {
          type xr:Cisco-ios-xr-string {
            length "1..1024";
          }
          description
            "Protocol Instance name";
        }
        container preempt {
          description
            "Configure pre-empt behavior";
          container delay {
            description
              "Specify delay period during which startup BPDUs should be sent, before pre-empting";
            choice DELAY {
              description
                "Specify delay period during which startup BPDUs should be sent, before pre-empting";
              case UNTIL {
                container until {
                  description
                    "Specify time to delay preempting until, as 24-hour hh:mm:ss";
                  leaf hours {
                    type uint32 {
                      range "0..23" {
                        description
                          "Hours (hh:mm:ss)";
                      }
                    }
                    description
                      "Hours (hh:mm:ss)";
                  }
                  leaf minutes {
                    type uint32 {
                      range "0..59" {
                        description
                          "Minutes (hh:mm:ss)";
                      }
                    }
                    must "../hours";
                    description
                      "Minutes (hh:mm:ss)";
                  }
                  leaf seconds {
                    type uint32 {
                      range "0..59" {
                        description
                          "Seconds (hh:mm:ss)";
                      }
                    }
                    must "../minutes";
                    description
                      "Seconds (hh:mm:ss)";
                  }
                }
              }
              case FOR {
                leaf for {
                  type uint32 {
                    range "0..86400" {
                      description
                        "Length of time to delay for (hours, minutes, or seconds)";
                    }
                  }
                  must "../time-unit";
                  description
                    "Specify length of time to delay bringup for";
                }
                leaf time-unit {
                  type enumeration {
                    enum "SECONDS" {
                      value 0;
                      description
                        "Time is in seconds";
                    }
                    enum "MINUTES" {
                      value 1;
                      description
                        "Time is in minutes";
                    }
                    enum "HOURS" {
                      value 2;
                      description
                        "Time is in hours";
                    }
                  }
                  description
                    "Specify length of time to delay bringup for";
                }
              }
            }
          }
        }
        container issu {
          description
            "Configure behavior during ISSU operations";
          container send {
            description
              "Specify the type of BPDUs to send during ISSU operations";
            leaf startup-bpdus {
              type empty;
              description
                "Send startup BPDUs during ISSU operations";
            }
          }
        }
        container interfaces {
          description
            "Enable and Configure PVRSTAG on an interface";
          list interface {
            key "interface-name";
            description
              "Enable and Configure PVRSTAG on an interface";
            leaf interface-name {
              type xr:Interface-name {
                pattern "(((Fast|Gigabit)Ethernet|.*GigE|CPRIoE|CemoHundredGigE)|Bundle-Ether)[^.]*";
              }
              description
                "Interface on which to enable PVRSTAG";
            }
            container vlans {
              description
                "Enable and Configure a VLAN on this interface";
              list vlan {
                key "vlan-id";
                description
                  "Enable and Configure a VLAN on this interface";
                leaf vlan-id {
                  type uint32 {
                    range "1..4094" {
                      description
                        "VLAN ID";
                    }
                  }
                  description
                    "VLAN ID";
                }
                container root-priority {
                  description
                    "Priority of the root to send in BPDUs";
                  leaf root-priority-number {
                    type uint32 {
                      range "0..61440" {
                        description
                          "Root Priority. For PVRSTAG, must be a multiple of 4096.";
                      }
                    }
                    description
                      "Priority of the root to send in BPDUs";
                  }
                  leaf startup-value {
                    type uint32 {
                      range "0..61440" {
                        description
                          "Root Priority. For PVRSTAG, must be a multiple of 4096.";
                      }
                    }
                    must "../root-priority-number";
                    description
                      "Set the priority of the root to be used during pre-empt delay";
                  }
                }
                container root-id {
                  description
                    "Bridge ID of the root to send in BPDUs";
                  leaf root-id-mac-address {
                    type yang:mac-address;
                    description
                      "Bridge ID of the root to send in BPDUs";
                  }
                  leaf startup-value {
                    type yang:mac-address;
                    must "../root-id-mac-address";
                    description
                      "Set the root bridge ID to be used during pre-empt delay";
                  }
                }
                container root-cost {
                  description
                    "Root cost to send in BPDUs";
                  leaf root-cost-number {
                    type uint32 {
                      range "0..4294967295" {
                        description
                          "Root Cost";
                      }
                    }
                    description
                      "Root cost to send in BPDUs";
                  }
                  leaf startup-value {
                    type uint32 {
                      range "0..4294967295" {
                        description
                          "Root Cost";
                      }
                    }
                    description
                      "Set the cost of the root to send in BPDUs to be used during pre-empt delay";
                  }
                }
                container priority {
                  description
                    "Priority of the Bridge to send in BPDUs";
                  leaf priority-number {
                    type uint32 {
                      range "0..61440" {
                        description
                          "Bridge Priority. For PVRSTAG, must be a multiple of 4096.";
                      }
                    }
                    description
                      "Priority of the Bridge to send in BPDUs";
                  }
                  leaf startup-value {
                    type uint32 {
                      range "0..61440" {
                        description
                          "Bridge Priority. For PVRSTAG, must be a multiple of 4096.";
                      }
                    }
                    description
                      "Set the priority of this bridge to be used during pre-empt delay";
                  }
                }
                container bridge-id {
                  description
                    "Bridge ID to use in BPDUs";
                  leaf bridge-id-mac-address {
                    type yang:mac-address;
                    description
                      "MAC address";
                  }
                  leaf startup-value {
                    type yang:mac-address;
                    must "../bridge-id-mac-address";
                    description
                      "Set the root bridge ID to be used during pre-empt delay";
                  }
                }
                container port-priority {
                  description
                    "Port priority to send in BPDUs";
                  leaf port-priority-number {
                    type uint32 {
                      range "0..240" {
                        description
                          "Port Priority. For PVRSTAG, must be a multiple of 16.";
                      }
                    }
                    description
                      "Port priority to send in BPDUs";
                  }
                  leaf startup-value {
                    type uint32 {
                      range "0..240" {
                        description
                          "Port Priority. For PVRSTAG, must be a multiple of 16.";
                      }
                    }
                    must "../port-priority-number";
                    description
                      "Set the priority of this port to be used during pre-empt delay";
                  }
                }
                container port-id {
                  description
                    "Interface Port ID to send in BPDUs";
                  leaf port-id-number {
                    type uint32 {
                      range "0..4095" {
                        description
                          "Port ID.";
                      }
                    }
                    description
                      "Port ID.";
                  }
                  leaf startup-value {
                    type uint32 {
                      range "0..4095" {
                        description
                          "Port ID.";
                      }
                    }
                    must "../port-id-number";
                    description
                      "Set the Port ID to be used during pre-empt delay";
                  }
                }
                leaf hello-time {
                  type uint32 {
                    range "1..2" {
                      description
                        "How often to send BPDUs";
                    }
                  }
                  description
                    "How often to send BPDUs";
                }
                container maximum {
                  description
                    "Maximum age to send in BPDUs";
                  leaf age {
                    type uint32 {
                      range "6..40" {
                        description
                          "Maximum Age time in seconds";
                      }
                    }
                    description
                      "Maximum age to send in BPDUs";
                  }
                }
              }
            }
          }
        }
      }
    }
    container pvstags {
      description
        "Configure PVST+ Access Gateway";
      list pvstag {
        key "protocol-instance-name";
        description
          "Configure PVST+ Access Gateway";
        leaf protocol-instance-name {
          type xr:Cisco-ios-xr-string {
            length "1..1024";
          }
          description
            "Protocol Instance name";
        }
        container preempt {
          description
            "Configure pre-empt behavior";
          container delay {
            description
              "Specify delay period during which startup BPDUs should be sent, before pre-empting";
            choice DELAY {
              description
                "Specify delay period during which startup BPDUs should be sent, before pre-empting";
              case UNTIL {
                container until {
                  description
                    "Specify time to delay preempting until, as 24-hour hh:mm:ss";
                  leaf hours {
                    type uint32 {
                      range "0..23" {
                        description
                          "Hours (hh:mm:ss)";
                      }
                    }
                    description
                      "Hours (hh:mm:ss)";
                  }
                  leaf minutes {
                    type uint32 {
                      range "0..59" {
                        description
                          "Minutes (hh:mm:ss)";
                      }
                    }
                    must "../hours";
                    description
                      "Minutes (hh:mm:ss)";
                  }
                  leaf seconds {
                    type uint32 {
                      range "0..59" {
                        description
                          "Seconds (hh:mm:ss)";
                      }
                    }
                    must "../minutes";
                    description
                      "Seconds (hh:mm:ss)";
                  }
                }
              }
              case FOR {
                leaf for {
                  type uint32 {
                    range "0..86400" {
                      description
                        "Length of time to delay for (hours, minutes, or seconds)";
                    }
                  }
                  must "../time-unit";
                  description
                    "Specify length of time to delay bringup for";
                }
                leaf time-unit {
                  type enumeration {
                    enum "SECONDS" {
                      value 0;
                      description
                        "Time is in seconds";
                    }
                    enum "MINUTES" {
                      value 1;
                      description
                        "Time is in minutes";
                    }
                    enum "HOURS" {
                      value 2;
                      description
                        "Time is in hours";
                    }
                  }
                  description
                    "Specify length of time to delay bringup for";
                }
              }
            }
          }
        }
        container issu {
          description
            "Configure behavior during ISSU operations";
          container send {
            description
              "Specify the type of BPDUs to send during ISSU operations";
            leaf startup-bpdus {
              type empty;
              description
                "Send startup BPDUs during ISSU operations";
            }
          }
        }
        container interfaces {
          description
            "Enable and Configure PVST+AG on an interface";
          list interface {
            key "interface-name";
            description
              "Enable and Configure PVST+AG on an interface";
            leaf interface-name {
              type xr:Interface-name {
                pattern "(((Fast|Gigabit)Ethernet|.*GigE|CPRIoE|CemoHundredGigE)|Bundle-Ether)[^.]*";
              }
              description
                "Interface on which to enable PVST+AG";
            }
            container vlans {
              description
                "Enable and Configure a VLAN on this interface";
              list vlan {
                key "vlan-id";
                description
                  "Enable and Configure a VLAN on this interface";
                leaf vlan-id {
                  type uint32 {
                    range "1..4094" {
                      description
                        "VLAN ID";
                    }
                  }
                  description
                    "VLAN ID";
                }
                container root-priority {
                  description
                    "Priority of the root to send in BPDUs";
                  leaf root-priority-number {
                    type uint32 {
                      range "0..61440" {
                        description
                          "Root Priority. For PVRSTAG, must be a multiple of 4096.";
                      }
                    }
                    description
                      "Priority of the root to send in BPDUs";
                  }
                  leaf startup-value {
                    type uint32 {
                      range "0..61440" {
                        description
                          "Root Priority. For PVRSTAG, must be a multiple of 4096.";
                      }
                    }
                    must "../root-priority-number";
                    description
                      "Set the priority of the root to be used during pre-empt delay";
                  }
                }
                container root-id {
                  description
                    "Bridge ID of the root to send in BPDUs";
                  leaf root-id-mac-address {
                    type yang:mac-address;
                    description
                      "Bridge ID of the root to send in BPDUs";
                  }
                  leaf startup-value {
                    type yang:mac-address;
                    must "../root-id-mac-address";
                    description
                      "Set the root bridge ID to be used during pre-empt delay";
                  }
                }
                container root-cost {
                  description
                    "Root cost to send in BPDUs";
                  leaf root-cost-number {
                    type uint32 {
                      range "0..4294967295" {
                        description
                          "Root Cost";
                      }
                    }
                    description
                      "Root cost to send in BPDUs";
                  }
                  leaf startup-value {
                    type uint32 {
                      range "0..4294967295" {
                        description
                          "Root Cost";
                      }
                    }
                    description
                      "Set the cost of the root to send in BPDUs to be used during pre-empt delay";
                  }
                }
                container priority {
                  description
                    "Priority of the Bridge to send in BPDUs";
                  leaf priority-number {
                    type uint32 {
                      range "0..61440" {
                        description
                          "Bridge Priority. For PVRSTAG, must be a multiple of 4096.";
                      }
                    }
                    description
                      "Priority of the Bridge to send in BPDUs";
                  }
                  leaf startup-value {
                    type uint32 {
                      range "0..61440" {
                        description
                          "Bridge Priority. For PVRSTAG, must be a multiple of 4096.";
                      }
                    }
                    description
                      "Set the priority of this bridge to be used during pre-empt delay";
                  }
                }
                container bridge-id {
                  description
                    "Bridge ID to use in BPDUs";
                  leaf bridge-id-mac-address {
                    type yang:mac-address;
                    description
                      "MAC address";
                  }
                  leaf startup-value {
                    type yang:mac-address;
                    must "../bridge-id-mac-address";
                    description
                      "Set the root bridge ID to be used during pre-empt delay";
                  }
                }
                container port-priority {
                  description
                    "Port priority to send in BPDUs";
                  leaf port-priority-number {
                    type uint32 {
                      range "0..240" {
                        description
                          "Port Priority. For PVRSTAG, must be a multiple of 16.";
                      }
                    }
                    description
                      "Port priority to send in BPDUs";
                  }
                  leaf startup-value {
                    type uint32 {
                      range "0..240" {
                        description
                          "Port Priority. For PVRSTAG, must be a multiple of 16.";
                      }
                    }
                    must "../port-priority-number";
                    description
                      "Set the priority of this port to be used during pre-empt delay";
                  }
                }
                container port-id {
                  description
                    "Interface Port ID to send in BPDUs";
                  leaf port-id-number {
                    type uint32 {
                      range "0..4095" {
                        description
                          "Port ID.";
                      }
                    }
                    description
                      "Port ID.";
                  }
                  leaf startup-value {
                    type uint32 {
                      range "0..4095" {
                        description
                          "Port ID.";
                      }
                    }
                    must "../port-id-number";
                    description
                      "Set the Port ID to be used during pre-empt delay";
                  }
                }
                leaf hello-time {
                  type uint32 {
                    range "1..2" {
                      description
                        "How often to send BPDUs";
                    }
                  }
                  description
                    "How often to send BPDUs";
                }
                container maximum {
                  description
                    "Maximum age to send in BPDUs";
                  leaf age {
                    type uint32 {
                      range "6..40" {
                        description
                          "Maximum Age time in seconds";
                      }
                    }
                    description
                      "Maximum age to send in BPDUs";
                  }
                }
              }
            }
          }
        }
      }
    }
    container mstags {
      description
        "Configure PVST+ Access Gateway";
      list mstag {
        key "protocol-instance-name";
        description
          "Configure PVST+ Access Gateway";
        leaf protocol-instance-name {
          type xr:Cisco-ios-xr-string {
            length "1..1024";
          }
          description
            "Protocol Instance name";
        }
        container preempt {
          description
            "Configure pre-empt behavior";
          container delay {
            description
              "Specify delay period during which startup BPDUs should be sent, before pre-empting";
            choice DELAY {
              description
                "Specify delay period during which startup BPDUs should be sent, before pre-empting";
              case UNTIL {
                container until {
                  description
                    "Specify time to delay preempting until, as 24-hour hh:mm:ss";
                  leaf hours {
                    type uint32 {
                      range "0..23" {
                        description
                          "Hours (hh:mm:ss)";
                      }
                    }
                    description
                      "Hours (hh:mm:ss)";
                  }
                  leaf minutes {
                    type uint32 {
                      range "0..59" {
                        description
                          "Minutes (hh:mm:ss)";
                      }
                    }
                    must "../hours";
                    description
                      "Minutes (hh:mm:ss)";
                  }
                  leaf seconds {
                    type uint32 {
                      range "0..59" {
                        description
                          "Seconds (hh:mm:ss)";
                      }
                    }
                    must "../minutes";
                    description
                      "Seconds (hh:mm:ss)";
                  }
                }
              }
              case FOR {
                leaf for {
                  type uint32 {
                    range "0..86400" {
                      description
                        "Length of time to delay for (hours, minutes, or seconds)";
                    }
                  }
                  must "../time-unit";
                  description
                    "Specify length of time to delay bringup for";
                }
                leaf time-unit {
                  type enumeration {
                    enum "SECONDS" {
                      value 0;
                      description
                        "Time is in seconds";
                    }
                    enum "MINUTES" {
                      value 1;
                      description
                        "Time is in minutes";
                    }
                    enum "HOURS" {
                      value 2;
                      description
                        "Time is in hours";
                    }
                  }
                  description
                    "Specify length of time to delay bringup for";
                }
              }
            }
          }
        }
        container interfaces {
          description
            "Enable and Configure MSTAG on an interface.";
          list interface {
            key "interface-name";
            description
              "Enable and Configure MSTAG on an interface.";
            leaf interface-name {
              type xr:Interface-name {
                pattern "(((Fast|Gigabit)Ethernet|.*GigE|CPRIoE|CemoHundredGigE)|Bundle-Ether)[^.]*";
              }
              description
                "Interface to MSTAG-enable";
            }
            container instances {
              description
                "Enable and Configure an instance on this interface.";
              list instance {
                key "instance-name";
                description
                  "Enable and Configure an instance on this interface.";
                leaf instance-name {
                  type uint32 {
                    range "0..4094" {
                      description
                        "MSTI ID";
                    }
                  }
                  description
                    "MSTI ID";
                }
                leaf vlan-ids {
                  when "../instance-name != '0'";
                  type xr:Cisco-ios-xr-string {
                    length "1..1024" {
                      description
                        "List of VLAN Ranges in the form a-b,c,d,e-f,g";
                    }
                  }
                  description
                    "Assign ranges of VLANs to the specified MSTI.";
                }
                container root-id {
                  description
                    "Set the Bridge ID of the root for this instance";
                  leaf root-id-mac-address {
                    type yang:mac-address;
                    description
                      "Set the Bridge ID of the root for this instance";
                  }
                  leaf startup-value {
                    type yang:mac-address;
                    must "../root-id-mac-address";
                    description
                      "Set the Bridge ID to be used during pre-empt delay";
                  }
                }
                container priority {
                  description
                    "MSTI Priority.";
                  leaf priority-number {
                    type uint32 {
                      range "0..61440" {
                        description
                          "MSTI Priority. Must be a multiple of 4096.";
                      }
                    }
                    description
                      "MSTI Priority.";
                  }
                  leaf startup-value {
                    type uint32 {
                      range "0..61440" {
                        description
                          "MSTI Priority. Must be a multiple of 4096.";
                      }
                    }
                    must "../priority-number";
                    description
                      "Set the MSTI Priority to be used during pre-empt delay";
                  }
                }
                container port-priority {
                  description
                    "Priority of this port on this MSTI.";
                  leaf port-priority-number {
                    type uint32 {
                      range "0..240" {
                        description
                          "Port Priority. Must be a multiple of 16.";
                      }
                    }
                    description
                      "Priority of this port on this MSTI.";
                  }
                  leaf startup-value {
                    type uint32 {
                      range "0..240" {
                        description
                          "Port Priority. Must be a multiple of 16.";
                      }
                    }
                    must "../port-priority-number";
                    description
                      "Set the priority of this port on this MSTI to be used during pre-empt delay";
                  }
                }
                container cost {
                  description
                    "Cost of this port on this MSTI.";
                  leaf cost-number {
                    type uint32 {
                      range "1..200000000" {
                        description
                          "Port Cost";
                      }
                    }
                    description
                      "Cost of this port on this MSTI.";
                  }
                  leaf startup-value {
                    type uint32 {
                      range "1..200000000" {
                        description
                          "Port Cost";
                      }
                    }
                    must "../cost-number";
                    description
                      "Set the cost of this port on this MSTI to be used during pre-empt delay";
                  }
                }
                container root-priority {
                  description
                    "Priority of the root for this instance.";
                  leaf root-priority-number {
                    type uint32 {
                      range "0..61440" {
                        description
                          "MSTI Priority. Must be a multiple of 4096.";
                      }
                    }
                    description
                      "Priority of the root for this instance.";
                  }
                  leaf startup-value {
                    type uint32 {
                      range "0..61440" {
                        description
                          "MSTI Priority. Must be a multiple of 4096.";
                      }
                    }
                    must "../root-priority-number";
                    description
                      "Set the priority of the root for this instance to be used during pre-empt delay";
                  }
                }
                leaf edge-mode {
                  type empty;
                  description
                    "Enable Access Gateway Edge Mode for this MSTI.";
                }
              }
            }
            container name {
              description
                "Configuration name";
              leaf configuration-name {
                type xr:Cisco-ios-xr-string {
                  length "1..1024" {
                    description
                      "Configuration name";
                  }
                }
                description
                  "Configuration name";
              }
              leaf none {
                type empty;
                description
                  "Use a NULL MST name";
              }
            }
            container bridge-id {
              description
                "Set the Bridge ID this port should use";
              leaf bridge-id-mac-address {
                type yang:mac-address;
                description
                  "MAC address";
              }
              leaf startup-value {
                type yang:mac-address;
                must "../bridge-id-mac-address";
                description
                  "Set the root bridge ID to be used during pre-empt delay";
              }
            }
            container port-id {
              description
                "Interface Port ID";
              leaf port-id-number {
                type uint32 {
                  range "1..4095" {
                    description
                      "Interface Port ID";
                  }
                }
                description
                  "Interface Port ID";
              }
              leaf startup-value {
                type uint32 {
                  range "1..4095" {
                    description
                      "Port ID.";
                  }
                }
                must "../port-id-number";
                description
                  "Set the Port ID to be used during pre-empt delay";
              }
            }
            container external-cost {
              description
                "Interface External Cost.";
              leaf external-cost-number {
                type uint32 {
                  range "1..200000000" {
                    description
                      "Interface External Cost.";
                  }
                }
                description
                  "Interface External Cost.";
              }
              leaf startup-value {
                type uint32 {
                  range "1..200000000" {
                    description
                      "Interface External Cost.";
                  }
                }
                must "../external-cost-number";
                description
                  "Set the External Cost to be used during pre-empt delay";
              }
            }
            leaf revision-number {
              type uint32 {
                range "0..65535" {
                  description
                    "Revision number.";
                }
              }
              description
                "Revision number.";
            }
            container maximum {
              description
                "Bridge maximums, such as max-age";
              leaf age {
                type uint32 {
                  range "6..40" {
                    description
                      "Bridge Maximum Age time in seconds.";
                  }
                }
                description
                  "Bridge maximum age time.";
              }
            }
            leaf provider-bridge {
              type empty;
              description
                "Provider Bridge mode.";
            }
            leaf hello-time {
              type uint32 {
                range "1..2" {
                  description
                    "Interface Hello Time in seconds.  Only 2 is supported on bundles.";
                }
              }
              description
                "Interface Hello Time.";
            }
          }
        }
        container track {
          description
            "Configure core connectivity tracking";
          container interfaces {
            description
              "Configure an interface as core facing for MSTAG";
            list interface {
              key "interface-name";
              description
                "Configure an interface as core facing for MSTAG";
              leaf interface-name {
                type xr:Interface-name;
                description
                  "Interface to configure as core-facing for MSTAG endofcommand";
              }
            }
          }
        }
      }
    }
  }
}
