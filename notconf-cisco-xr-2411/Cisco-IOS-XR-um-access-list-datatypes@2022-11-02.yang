module Cisco-IOS-XR-um-access-list-datatypes {
  namespace "http://cisco.com/ns/yang/Cisco-IOS-XR-um-access-list-datatypes";
  prefix um-access-list-datatypes;

  import cisco-semver {
    prefix semver;
  }
  import Cisco-IOS-XR-types {
    prefix xr2;
  }

  organization
    "Cisco Systems, Inc.";
  contact
    "
     Cisco Systems, Inc.
     Customer Service

     Postal: 170 W Tasman Drive
     San Jose, CA 95134

     Tel: +1 1800 553-NETS

     E-mail: cs-yang@cisco.com
     ";
  description
    "
     This module contains a collection of IOS-XR YANG model derived from CLI.

     Copyright (c) 2013-2022 by Cisco Systems, Inc.
     All rights reserved.
     ";

  revision 2022-11-02 {
    semver:module-version "2.2.0";
    description
      "Fixed  typos in description
       2022-08-15
         Added icmpv6 enum string to ipv4-protocol
       2022-07-11
         Added missing description statement to nodes
       2022-07-08
         Adding dscp bitmask";
  }
  revision 2021-03-17 {
    semver:module-version "2.1.0";
    description
      "Adding new protocols - vrrp, rsvp";
  }
  revision 2019-06-10 {
    semver:module-version "2.0.0";
    description
      "Establish semantic version baseline.";
  }
  revision 2019-04-01 {
    description
      "Initial version";
  }

  typedef ipv4-protocol {
    type union {
      type uint8 {
        range "0..255" {
          description
            "An IPv4 Protocol Number";
        }
      }
      type enumeration {
        enum "ahp" {
          value 51;
          description
            "Authentication Header Protocol";
        }
        enum "eigrp" {
          value 88;
          description
            "Cisco's EIGRP Routing Protocol";
        }
        enum "esp" {
          value 50;
          description
            "Encapsulation Security Payload";
        }
        enum "gre" {
          value 47;
          description
            "Cisco's GRE Tunneling";
        }
        enum "icmp" {
          value 1;
          description
            "Internet Control Message Protocol";
        }
        enum "icmpv6" {
          value 58;
          description
            "Internet Control Message Protocol - IPV6";
        }
        enum "igmp" {
          value 2;
          description
            "Internet Gateway Message Protocol";
        }
        enum "igrp" {
          value 9;
          description
            "Cisco's IGRP Routing Protocol";
        }
        enum "ipinip" {
          value 4;
          description
            "IP in IP tunneling";
        }
        enum "ipv4" {
          value 512;
          description
            "Any IPv4 Protocol";
        }
        enum "nos" {
          value 94;
          description
            "KA9Q NOS Compatible IP over IP Tunneling";
        }
        enum "ospf" {
          value 89;
          description
            "OSPF Routing Protocol";
        }
        enum "pcp" {
          value 108;
          description
            "Payload Compression Protocol";
        }
        enum "pim" {
          value 103;
          description
            "Protocol Independent Multicast";
        }
        enum "sctp" {
          value 132;
          description
            "Stream Control Transmission Protocol";
        }
        enum "tcp" {
          value 6;
          description
            "Transport Control Protocol";
        }
        enum "udp" {
          value 17;
          description
            "User Datagram Protocol";
        }
        enum "rsvp" {
          value 46;
          description
            "Router Reservation Protocol";
        }
        enum "vrrp" {
          value 112;
          description
            "Virtual Router Redundancy Protocol";
        }
      }
    }
    description
      "ipv4-protocol";
  }

  typedef ipv4-port-number {
    type union {
      type ipv4-tcp-port-number;
      type ipv4-udp-port-number;
    }
    description
      "ipv4-port-number";
  }

  typedef ipv4-tcp-port-number {
    type union {
      type uint16 {
        range "0..65535";
      }
      type enumeration {
        enum "Echo" {
          value 7;
          description
            "Echo";
        }
        enum "Discard" {
          value 9;
          description
            "Discard";
        }
        enum "Daytime" {
          value 13;
          description
            "Daytime";
        }
        enum "CharGen" {
          value 19;
          description
            "Character generator";
        }
        enum "FTPData" {
          value 20;
          description
            "FTP data connections (used infrequently)";
        }
        enum "FTP" {
          value 21;
          description
            "File Transfer Protocol";
        }
        enum "SSH" {
          value 22;
          description
            "Secure Shell";
        }
        enum "Telnet" {
          value 23;
          description
            "Telnet";
        }
        enum "SMTP" {
          value 25;
          description
            "Simple Mail Transport Protocol";
        }
        enum "Time" {
          value 37;
          description
            "Time";
        }
        enum "WhoIs" {
          value 43;
          description
            "Nicname";
        }
        enum "TACACS" {
          value 49;
          description
            "TAC Access Control System";
        }
        enum "DNS" {
          value 53;
          description
            "Domain Name Service";
        }
        enum "Gopher" {
          value 70;
          description
            "Gopher";
        }
        enum "Finger" {
          value 79;
          description
            "Finger";
        }
        enum "WWW" {
          value 80;
          description
            "World Wide Web (HTTP)";
        }
        enum "Hostname" {
          value 101;
          description
            "NIC hostname server";
        }
        enum "POP2" {
          value 109;
          description
            "Post Office Protocol v2";
        }
        enum "POP3" {
          value 110;
          description
            "Post Office Protocol v3";
        }
        enum "SunRPC" {
          value 111;
          description
            "Sun Remote Procedure Call";
        }
        enum "Ident" {
          value 113;
          description
            "Ident Protocol";
        }
        enum "NNTP" {
          value 119;
          description
            "Network News Transport Protocol";
        }
        enum "BGP" {
          value 179;
          description
            "Border Gateway Protocol";
        }
        enum "IRC" {
          value 194;
          description
            "Internet Relay Chat";
        }
        enum "HTTPS" {
          value 443;
          description
            "HTTPS";
        }
        enum "PIMAutoRP" {
          value 496;
          description
            "PIM Auto-RP";
        }
        enum "ExecOrBiff" {
          value 512;
          description
            "Exec (rsh)";
        }
        enum "LoginOrWho" {
          value 513;
          description
            "Login (rlogin)";
        }
        enum "CmdOrSyslog" {
          value 514;
          description
            "Remote commands (rcmd)";
        }
        enum "LPD" {
          value 515;
          description
            "Printer service";
        }
        enum "UUCP" {
          value 540;
          description
            "Unix-to-Unix Copy Program";
        }
        enum "KLogin" {
          value 543;
          description
            "Kerberos login";
        }
        enum "KShell" {
          value 544;
          description
            "Kerberos shell";
        }
        enum "Talk" {
          value 517;
          description
            "Talk";
        }
        enum "LDP" {
          value 646;
          description
            "LDP session connection attempts (MPLS)";
        }
        enum "RADIUS" {
          value 1812;
          description
            "Radius Authentication protocolTalk";
        }
        enum "RADIUS_ACCT" {
          value 1813;
          description
            "Radius accounting Protocol";
        }
      }
    }
    description
      "ipv4-tcp-port-number";
  }

  typedef ipv4-udp-port-number {
    type union {
      type uint16 {
        range "0..65535";
      }
      type enumeration {
        enum "BFD" {
          value 3784;
          description
            "BFD Port";
        }
        enum "ExecOrBiff" {
          value 512;
          description
            "Biff (mail notification, comsat";
        }
        enum "BootPC" {
          value 68;
          description
            "Bootstrap Protocol (BOOTP) client";
        }
        enum "BootPS" {
          value 67;
          description
            "Bootstrap Protocol (BOOTP) server";
        }
        enum "Discard" {
          value 9;
          description
            "Discard";
        }
        enum "DNSIX" {
          value 195;
          description
            "DNSIX security protocol auditing";
        }
        enum "DNS" {
          value 53;
          description
            "Domain Name Service (DNS)";
        }
        enum "Echo" {
          value 7;
          description
            "Echo";
        }
        enum "ISAKMP" {
          value 500;
          description
            "Internet Security Association and Key Management Protocol";
        }
        enum "LDP" {
          value 646;
          description
            "LDP hello packets (MPLS)";
        }
        enum "MobileIP" {
          value 434;
          description
            "Mobile IP registration";
        }
        enum "NameServer" {
          value 42;
          description
            "IEN116 name service (obsolete)";
        }
        enum "NetBIOS_DGS" {
          value 138;
          description
            "NetBios datagram service";
        }
        enum "NetBIOS_NS" {
          value 137;
          description
            "NetBios name service";
        }
        enum "NetBIOS_SS" {
          value 139;
          description
            "NetBios session service";
        }
        enum "NTP" {
          value 123;
          description
            "Network Time Protocol";
        }
        enum "PIMAutoRP" {
          value 496;
          description
            "PIM Auto-RP";
        }
        enum "RIP" {
          value 520;
          description
            "Routing Information Protocol (router, in.routed)";
        }
        enum "SNMP" {
          value 161;
          description
            "Simple Network Management Protocol";
        }
        enum "SNMPTrap" {
          value 162;
          description
            "SNMP Traps";
        }
        enum "SSH" {
          value 22;
          description
            "Secure Shell service";
        }
        enum "SunRPC" {
          value 111;
          description
            "Sun Remote Procedure Call";
        }
        enum "CmdOrSyslog" {
          value 514;
          description
            "System Logger";
        }
        enum "TACACS" {
          value 49;
          description
            "TAC Access Control System";
        }
        enum "Talk" {
          value 517;
          description
            "Talk";
        }
        enum "TFTP" {
          value 69;
          description
            "Trivial File Transfer Protocol";
        }
        enum "Time" {
          value 37;
          description
            "Time";
        }
        enum "LoginOrWho" {
          value 513;
          description
            "Who service (rwho)";
        }
        enum "XDMCP" {
          value 177;
          description
            "X Display Manager Control Protocol";
        }
      }
    }
    description
      "ipv4-udp-port-number";
  }

  typedef precedence-value {
    type union {
      type uint8 {
        range "0..7";
      }
      type enumeration {
        enum "Critical" {
          value 5;
          description
            "Match packets with critical precedence";
        }
        enum "Flash" {
          value 3;
          description
            "Match packets with flash precedence";
        }
        enum "FlashOverride" {
          value 4;
          description
            "Match packets with flash override precedence";
        }
        enum "Immediate" {
          value 2;
          description
            "Match packets with immediate precedence";
        }
        enum "Internet" {
          value 6;
          description
            "Match packets with internetwork control precedence";
        }
        enum "Network" {
          value 7;
          description
            "Match packets with network control precedence";
        }
        enum "Priority" {
          value 1;
          description
            "Match packets with priority precedence";
        }
        enum "Routine" {
          value 0;
          description
            "Match packets with routine precedence";
        }
      }
    }
    description
      "precedence-value";
  }

  typedef dscp-value {
    type union {
      type uint8 {
        range "0..63";
      }
      type enumeration {
        enum "af11" {
          value 10;
          description
            "Match packets with AF11 dscp (001010)";
        }
        enum "af12" {
          value 12;
          description
            "Match packets with AF12 dscp (001100)";
        }
        enum "af13" {
          value 14;
          description
            "Match packets with AF13 dscp (001110)";
        }
        enum "af21" {
          value 18;
          description
            "Match packets with AF21 dscp (010010)";
        }
        enum "af22" {
          value 20;
          description
            "Match packets with AF22 dscp (010100)";
        }
        enum "af23" {
          value 22;
          description
            "Match packets with AF23 dscp (010110)";
        }
        enum "af31" {
          value 26;
          description
            "Match packets with AF31 dscp (011010)";
        }
        enum "af32" {
          value 28;
          description
            "Match packets with AF32 dscp (011100)";
        }
        enum "af33" {
          value 30;
          description
            "Match packets with AF33 dscp (011110)";
        }
        enum "af41" {
          value 34;
          description
            "Match packets with AF41 dscp (100010)";
        }
        enum "af42" {
          value 36;
          description
            "Match packets with AF42 dscp (100100)";
        }
        enum "af43" {
          value 38;
          description
            "Match packets with AF43 dscp (100110)";
        }
        enum "cs1" {
          value 8;
          description
            "Match packets with CS1(precedence 1) dscp (001000)";
        }
        enum "cs2" {
          value 16;
          description
            "Match packets with CS2(precedence 2) dscp (010000)";
        }
        enum "cs3" {
          value 24;
          description
            "Match packets with CS3(precedence 3) dscp (011000)";
        }
        enum "cs4" {
          value 32;
          description
            "Match packets with CS4(precedence 4) dscp (100000)";
        }
        enum "cs5" {
          value 40;
          description
            "Match packets with CS5(precedence 5) dscp (101000)";
        }
        enum "cs6" {
          value 48;
          description
            "Match packets with CS6(precedence 6) dscp (110000)";
        }
        enum "cs7" {
          value 56;
          description
            "Match packets with CS7(precedence 7) dscp (111000)";
        }
        enum "default" {
          value 0;
          description
            "Match packets with default DSCP (000000)";
        }
        enum "ef" {
          value 46;
          description
            "Match packets with EF dscp (101110)";
        }
      }
    }
    description
      "dscp-value";
  }

  typedef dscp-bitmask-value {
    type union {
      type xr2:Hex-integer;
      type enumeration {
        enum "af11" {
          value 10;
          description
            "Match packets with AF11 dscp (001010)";
        }
        enum "af12" {
          value 12;
          description
            "Match packets with AF12 dscp (001100)";
        }
        enum "af13" {
          value 14;
          description
            "Match packets with AF13 dscp (001110)";
        }
        enum "af21" {
          value 18;
          description
            "Match packets with AF21 dscp (010010)";
        }
        enum "af22" {
          value 20;
          description
            "Match packets with AF22 dscp (010100)";
        }
        enum "af23" {
          value 22;
          description
            "Match packets with AF23 dscp (010110)";
        }
        enum "af31" {
          value 26;
          description
            "Match packets with AF31 dscp (011010)";
        }
        enum "af32" {
          value 28;
          description
            "Match packets with AF32 dscp (011100)";
        }
        enum "af33" {
          value 30;
          description
            "Match packets with AF33 dscp (011110)";
        }
        enum "af41" {
          value 34;
          description
            "Match packets with AF41 dscp (100010)";
        }
        enum "af42" {
          value 36;
          description
            "Match packets with AF42 dscp (100100)";
        }
        enum "af43" {
          value 38;
          description
            "Match packets with AF43 dscp (100110)";
        }
        enum "cs1" {
          value 8;
          description
            "Match packets with CS1(precedence 1) dscp (001000)";
        }
        enum "cs2" {
          value 16;
          description
            "Match packets with CS2(precedence 2) dscp (010000)";
        }
        enum "cs3" {
          value 24;
          description
            "Match packets with CS3(precedence 3) dscp (011000)";
        }
        enum "cs4" {
          value 32;
          description
            "Match packets with CS4(precedence 4) dscp (100000)";
        }
        enum "cs5" {
          value 40;
          description
            "Match packets with CS5(precedence 5) dscp (101000)";
        }
        enum "cs6" {
          value 48;
          description
            "Match packets with CS6(precedence 6) dscp (110000)";
        }
        enum "cs7" {
          value 56;
          description
            "Match packets with CS7(precedence 7) dscp (111000)";
        }
        enum "default" {
          value 0;
          description
            "Match packets with default DSCP (000000)";
        }
        enum "ef" {
          value 46;
          description
            "Match packets with EF dscp (101110)";
        }
      }
    }
    description
      "dscp-bitmask-value";
  }

  typedef tcp-bits-type {
    type bits {
      bit fin {
        position 0;
        description
          "Match on the FIN bit (0x01)";
      }
      bit syn {
        position 1;
        description
          "Match on the SYN bit (0x02)";
      }
      bit rst {
        position 2;
        description
          "Match on the RST bit (0x04)";
      }
      bit psh {
        position 3;
        description
          "Match on the PSH bit (0x08)";
      }
      bit ack {
        position 4;
        description
          "Match on the ACK bit (0x10)";
      }
      bit urg {
        position 5;
        description
          "Match on the URG bit (0x20)";
      }
    }
    description
      "acl tcp bits number";
  }

  typedef ipv4-icmp-message-type {
    type enumeration {
      enum "MobileRedirect" {
        value 2162687;
        description
          "Mobile host redirect";
      }
      enum "ConversionError" {
        value 2097151;
        description
          "Datagram conversion";
      }
      enum "Traceroute" {
        value 2031615;
        description
          "Traceroute";
      }
      enum "MaskReply" {
        value 1245183;
        description
          "Mask replies";
      }
      enum "MaskRequest" {
        value 1179647;
        description
          "Mask requests";
      }
      enum "InformationReply" {
        value 1114111;
        description
          "Information replies";
      }
      enum "InformationRequest" {
        value 1048575;
        description
          "Information request";
      }
      enum "TimestampReply" {
        value 983039;
        description
          "Timestamp replies";
      }
      enum "TimestampRequest" {
        value 917503;
        description
          "Timestamp requests";
      }
      enum "ParameterProblem" {
        value 851967;
        description
          "All parameter problems";
      }
      enum "TimeExceeded" {
        value 786431;
        description
          "All time exceeds";
      }
      enum "RouterSolicitation" {
        value 720895;
        description
          "Router discovery solicitations";
      }
      enum "RouterAdvertisement" {
        value 655359;
        description
          "Router discovery advertisements";
      }
      enum "AlternateAddress" {
        value 458751;
        description
          "Alternate address";
      }
      enum "Echo" {
        value 589823;
        description
          "Echo (ping)";
      }
      enum "Redirect" {
        value 393215;
        description
          "All redirects";
      }
      enum "SourceQuench" {
        value 327679;
        description
          "Source quenches";
      }
      enum "Unreachable" {
        value 262143;
        description
          "All unreachables";
      }
      enum "EchoReply" {
        value 65535;
        description
          "Echo reply";
      }
      enum "NetworkUnreachable" {
        value 196608;
        description
          "Net unreachable";
      }
      enum "HostUnreachable" {
        value 196609;
        description
          "Host unreachable";
      }
      enum "ProtocolUnreachable" {
        value 196610;
        description
          "Protocol unreachable";
      }
      enum "PortUnreachable" {
        value 196611;
        description
          "Port unreachable";
      }
      enum "PacketTooBig" {
        value 196612;
        description
          "Fragmentation needed and DF set";
      }
      enum "SourceRouteFailed" {
        value 196613;
        description
          "Source route failed";
      }
      enum "NetworkUnknown" {
        value 196614;
        description
          "Network unknown";
      }
      enum "HostUnknown" {
        value 196615;
        description
          "Host unknown";
      }
      enum "HostIsolated" {
        value 196616;
        description
          "Host isolated";
      }
      enum "DODNetProhibited" {
        value 196617;
        description
          "Net prohibited";
      }
      enum "DODHostProhibited" {
        value 196618;
        description
          "Host prohibited";
      }
      enum "NetTOSUnreachable" {
        value 196620;
        description
          "Network unreachable for TOS";
      }
      enum "HostTOSUnreachable" {
        value 196619;
        description
          "Host unreachable for TOS";
      }
      enum "AdministrativelyProhibited" {
        value 196621;
        description
          "Administratively prohibited";
      }
      enum "HostPrecedenceUnreachable" {
        value 196622;
        description
          "Host unreachable for precedence";
      }
      enum "PrecedenceUnreachable" {
        value 196623;
        description
          "Precedence cutoff";
      }
      enum "NetworkRedirect" {
        value 327680;
        description
          "Network redirect";
      }
      enum "HostRedirect" {
        value 327681;
        description
          "Host redirect";
      }
      enum "NetTOSRedirect" {
        value 327682;
        description
          "Net redirect for TOS";
      }
      enum "HostTOSRedirect" {
        value 327683;
        description
          "Host redirect for TOS";
      }
      enum "TTLExceeded" {
        value 720896;
        description
          "TTL exceeded";
      }
      enum "ReassemblyTimeout" {
        value 720897;
        description
          "Reassembly timeout";
      }
      enum "GeneralParameterProblem" {
        value 786432;
        description
          "Parameter problem";
      }
      enum "OptionMissing" {
        value 786433;
        description
          "Parameter required but not present";
      }
      enum "NoRoomForOption" {
        value 786434;
        description
          "Parameter required but no room";
      }
    }
    description
      "ipv4-icmp-message-type";
  }

  typedef ipv6-protocol {
    type union {
      type uint8 {
        range "0..255" {
          description
            "An IPv6 Protocol Number";
        }
      }
      type enumeration {
        enum "ahp" {
          value 51;
          description
            "Authentication Header Protocol";
        }
        enum "eigrp" {
          value 88;
          description
            "Cisco's EIGRP Routing Protocol";
        }
        enum "esp" {
          value 50;
          description
            "Encapsulation Security Payload";
        }
        enum "gre" {
          value 47;
          description
            "Cisco's GRE Tunneling";
        }
        enum "icmpv6" {
          value 58;
          description
            "Internet Control Message Protocol";
        }
        enum "igrp" {
          value 9;
          description
            "Cisco's IGRP Routing Protocol";
        }
        enum "ipv6" {
          value 513;
          description
            "Any IPv6 Protocol";
        }
        enum "ospf" {
          value 89;
          description
            "OSPF Routing Protocol";
        }
        enum "pcp" {
          value 108;
          description
            "Payload Compression Protocol";
        }
        enum "pim" {
          value 103;
          description
            "Protocol Independent Multicast";
        }
        enum "sctp" {
          value 132;
          description
            "Stream Control Transmission Protocol";
        }
        enum "tcp" {
          value 6;
          description
            "Transport Control Protocol";
        }
        enum "udp" {
          value 17;
          description
            "User Datagram Protocol";
        }
        enum "rsvp" {
          value 46;
          description
            "Router Reservation Protocol";
        }
        enum "vrrp" {
          value 112;
          description
            "Virtual Router Redundancy Protocol";
        }
      }
    }
    description
      "ipv6-protocol";
  }

  typedef ipv6-port-number {
    type union {
      type ipv6-tcp-port-number;
      type ipv6-udp-port-number;
    }
    description
      "ipv6-port-number";
  }

  typedef ipv6-tcp-port-number {
    type union {
      type uint16 {
        range "0..65535";
      }
      type enumeration {
        enum "Echo" {
          value 7;
          description
            "Echo";
        }
        enum "Discard" {
          value 9;
          description
            "Discard";
        }
        enum "Daytime" {
          value 13;
          description
            "Daytime";
        }
        enum "CharGen" {
          value 19;
          description
            "Character generator";
        }
        enum "FTPData" {
          value 20;
          description
            "FTP data connections (used infrequently)";
        }
        enum "FTP" {
          value 21;
          description
            "File Transfer Protocol";
        }
        enum "SSH" {
          value 22;
          description
            "Secure Shell";
        }
        enum "Telnet" {
          value 23;
          description
            "Telnet";
        }
        enum "SMTP" {
          value 25;
          description
            "Simple Mail Transport Protocol";
        }
        enum "Time" {
          value 37;
          description
            "Time";
        }
        enum "WhoIs" {
          value 43;
          description
            "Nicname";
        }
        enum "TACACS" {
          value 49;
          description
            "TAC Access Control System";
        }
        enum "DNS" {
          value 53;
          description
            "Domain Name Service";
        }
        enum "Gopher" {
          value 70;
          description
            "Gopher";
        }
        enum "Finger" {
          value 79;
          description
            "Finger";
        }
        enum "WWW" {
          value 80;
          description
            "World Wide Web (HTTP)";
        }
        enum "Hostname" {
          value 101;
          description
            "NIC hostname server";
        }
        enum "POP2" {
          value 109;
          description
            "Post Office Protocol v2";
        }
        enum "POP3" {
          value 110;
          description
            "Post Office Protocol v3";
        }
        enum "SunRPC" {
          value 111;
          description
            "Sun Remote Procedure Call";
        }
        enum "Ident" {
          value 113;
          description
            "Ident Protocol";
        }
        enum "NNTP" {
          value 119;
          description
            "Network News Transport Protocol";
        }
        enum "BGP" {
          value 179;
          description
            "Border Gateway Protocol";
        }
        enum "IRC" {
          value 194;
          description
            "Internet Relay Chat";
        }
        enum "HTTPS" {
          value 443;
          description
            "Internet Relay Chat";
        }
        enum "PIMAutoRP" {
          value 496;
          description
            "PIM Auto-RP";
        }
        enum "ExecOrBiff" {
          value 512;
          description
            "Exec (rsh)";
        }
        enum "LoginOrWho" {
          value 513;
          description
            "Login (rlogin)";
        }
        enum "CmdOrSyslog" {
          value 514;
          description
            "Remote commands (rcmd)";
        }
        enum "LPD" {
          value 515;
          description
            "Printer service";
        }
        enum "UUCP" {
          value 540;
          description
            "Unix-to-Unix Copy Program";
        }
        enum "KLogin" {
          value 543;
          description
            "Kerberos login";
        }
        enum "KShell" {
          value 544;
          description
            "Kerberos shell";
        }
        enum "Talk" {
          value 517;
          description
            "Talk";
        }
        enum "RADIUS" {
          value 1812;
          description
            "Kerberos shell";
        }
        enum "RADIUS_ACCT" {
          value 1813;
          description
            "Talk";
        }
      }
    }
    description
      "ipv6-tcp-port-number";
  }

  typedef ipv6-udp-port-number {
    type union {
      type uint16 {
        range "0..65535";
      }
      type enumeration {
        enum "BFD" {
          value 3784;
          description
            "BFD";
        }
        enum "ExecOrBiff" {
          value 512;
          description
            "Biff (mail notification, comsat";
        }
        enum "BootPC" {
          value 68;
          description
            "Bootstrap Protocol (BOOTP) client";
        }
        enum "BootPS" {
          value 67;
          description
            "Bootstrap Protocol (BOOTP) server";
        }
        enum "Discard" {
          value 9;
          description
            "Discard";
        }
        enum "DNSIX" {
          value 195;
          description
            "DNSIX security protocol auditing";
        }
        enum "DNS" {
          value 53;
          description
            "Domain Name Service (DNS)";
        }
        enum "Echo" {
          value 7;
          description
            "Echo";
        }
        enum "ISAKMP" {
          value 500;
          description
            "Internet Security Association and Key Management Protocol";
        }
        enum "MobileIP" {
          value 434;
          description
            "Mobile IP registration";
        }
        enum "NameServer" {
          value 42;
          description
            "IEN116 name service (obsolete)";
        }
        enum "NetBIOS_DGS" {
          value 138;
          description
            "NetBios datagram service";
        }
        enum "NetBIOS_NS" {
          value 137;
          description
            "NetBios name service";
        }
        enum "NetBIOS_SS" {
          value 139;
          description
            "NetBios session service";
        }
        enum "NTP" {
          value 123;
          description
            "Network Time Protocol";
        }
        enum "PIMAutoRP" {
          value 496;
          description
            "PIM Auto-RP";
        }
        enum "RIP" {
          value 520;
          description
            "Routing Information Protocol (router, in.routed)";
        }
        enum "SNMP" {
          value 161;
          description
            "Simple Network Management Protocol";
        }
        enum "SNMPTrap" {
          value 162;
          description
            "SNMP Traps";
        }
        enum "SSH" {
          value 22;
          description
            "Secure Shell service";
        }
        enum "SunRPC" {
          value 111;
          description
            "Sun Remote Procedure Call";
        }
        enum "CmdOrSyslog" {
          value 514;
          description
            "System Logger";
        }
        enum "TACACS" {
          value 49;
          description
            "TAC Access Control System";
        }
        enum "Talk" {
          value 517;
          description
            "Talk";
        }
        enum "TFTP" {
          value 69;
          description
            "Trivial File Transfer Protocol";
        }
        enum "Time" {
          value 37;
          description
            "Time";
        }
        enum "LoginOrWho" {
          value 513;
          description
            "Who service (rwho)";
        }
        enum "XDMCP" {
          value 177;
          description
            "X Display Manager Control Protocol";
        }
        enum "LDP" {
          value 646;
          description
            "LDP";
        }
      }
    }
    description
      "ipv6-udp-port-number";
  }

  typedef ipv6-icmp-message-type {
    type enumeration {
      enum "ParameterProblem" {
        value 327679;
        description
          "All parameter problems";
      }
      enum "TimeExceeded" {
        value 262143;
        description
          "All time exceeds";
      }
      enum "RouterSolicitation" {
        value 8716288;
        description
          "Router discovery solicitations";
      }
      enum "RouterAdvertisement" {
        value 8781824;
        description
          "Router discovery advertisements";
      }
      enum "Echo" {
        value 8388608;
        description
          "Echo (ping)";
      }
      enum "EchoReply" {
        value 8454144;
        description
          "Echo reply";
      }
      enum "PortUnreachable" {
        value 65540;
        description
          "Port unreachable";
      }
      enum "PacketTooBig" {
        value 131072;
        description
          "Fragmentation needed and DF set";
      }
      enum "AdministrativelyProhibited" {
        value 65537;
        description
          "Administratively prohibited";
      }
      enum "TTLExceeded" {
        value 196608;
        description
          "TTL exceeded";
      }
      enum "ReassemblyOption" {
        value 196609;
        description
          "Reassembly timeout";
      }
      enum "ErroneousHeaderField" {
        value 262144;
        description
          "Erroneous header field";
      }
      enum "UnrecognizedNextHeader" {
        value 262145;
        description
          "Unrecognized Next Header type";
      }
      enum "UnrecognizedOption" {
        value 262146;
        description
          "Unrecognized IPv6 option";
      }
      enum "DestinationUnreachable" {
        value 131071;
        description
          "Destination Unreachable";
      }
      enum "AddressUnreachable" {
        value 65539;
        description
          "Address Unreachable";
      }
      enum "BeyondScopeOfSourceAddress" {
        value 65538;
        description
          "Unreachable beyond scope of address";
      }
      enum "GroupMembershipQuery" {
        value 8585215;
        description
          "Multicast Listener Query";
      }
      enum "GroupMembershipReport" {
        value 8650751;
        description
          "Multicast Listener report";
      }
      enum "GroupMembershipReduction" {
        value 8716287;
        description
          "Multicast Listener Done";
      }
      enum "NeighborRedirect" {
        value 8978432;
        description
          "Neighbor redirect";
      }
      enum "NoRouteToDestination" {
        value 65536;
        description
          "No route to destination";
      }
      enum "NodeInformationSuccessfulReply" {
        value 9175040;
        description
          "Node information successful reply";
      }
      enum "NodeInformationRequestIsRefused" {
        value 9175041;
        description
          "Node information reply rejected";
      }
      enum "RouterRenumbering" {
        value 9109503;
        description
          "Router renumbering";
      }
      enum "RRCommand" {
        value 9043968;
        description
          "Router renumbering command";
      }
      enum "RRResult" {
        value 9043969;
        description
          "Router renumbering result";
      }
      enum "RRSeqnumReset" {
        value 9044223;
        description
          "Router renumbering seqnum";
      }
      enum "QuerySubjectIsIPv6Address" {
        value 9109504;
        description
          "Query subject is ipv6 address";
      }
      enum "QuerySubjectIsDomainName" {
        value 9109505;
        description
          "Query subject is domain name";
      }
      enum "QuerySubjectIsIPv4Address" {
        value 9109506;
        description
          "Query subject is ipv4 address";
      }
      enum "NeighborSolicitation" {
        value 8847360;
        description
          "Neighbor discovery neighbor solicitations";
      }
      enum "NeighborAdvertisement" {
        value 8912896;
        description
          "Neighbor discovery neighbor advertisements";
      }
      enum "WhoAreYouRequest" {
        value 9175039;
        description
          "Who are you request";
      }
      enum "WhoAreYouReply" {
        value 9240575;
        description
          "Who are you reply";
      }
      enum "UnknownQueryType" {
        value 9175042;
        description
          "Unknown query type";
      }
    }
    description
      "ipv6-icmp-message-type";
  }

  typedef header-bits-type {
    type bits {
      bit routing {
        position 0;
        description
          "Match if routing header is present";
      }
      bit destopts {
        position 1;
        description
          "Match if destination opts header is present";
      }
      bit hop-by-hop {
        position 2;
        description
          "Match if hop-by-hop opts header is present";
      }
      bit fragments {
        position 3;
        description
          "Match if fragment extension header contains a non-zero fragment offset";
      }
      bit authen {
        position 5;
        description
          "Match if authentication header is present";
      }
    }
    description
      "IPv6 header bits number";
  }

  typedef vlan-id {
    type union {
      type uint16 {
        range "0..4095" {
          description
            "Vlan Id";
        }
      }
      type string {
        pattern "([0-9]{1,4})-([0-9]{1,4})" {
          description
            "Lower/upper limit of the Vlan Id range (<0-4095>-<0-4095>)";
        }
      }
    }
    description
      "vlan-id";
  }
}
