module Cisco-IOS-XR-sysadmin-aaa-aaa-show {
  namespace "http://www.cisco.com/ns/yang/Cisco-IOS-XR-sysadmin-aaa-aaa-show";
  prefix aaa_show;

  import tailf-aaa {
    prefix aaa;
  }
  import cisco-semver {
    prefix semver;
  }

  organization
    "Cisco Systems Inc.";
  contact
    "clos-mgbl@cisco.com";
  description
    "This module defines yang model
     for logging user/date who accessed
     shell last time

     Copyright (c) 2012-2020 by Cisco Systems, Inc.
     All rights reserved.";

  revision 2019-04-15 {
    semver:module-version "1.0.0";
    description
      "Establish semantic version baseline.";
  }
  revision 2017-05-10 {
    description
      "Namespace changed from aaa_show to Cisco-IOS-XR-sysadmin-aaa-aaa-show";
  }
  revision 2011-06-20 {
    description
      "Initial revision";
  }

  augment "/aaa:aaa" {
    container privileged-access {
      config false;
      leaf shell-access {
        type string;
        mandatory false;
      }
      leaf first-user {
        type string;
        mandatory false;
      }
      leaf first-user-change {
        type string;
        mandatory false;
      }
      leaf current-disaster-recovery-user {
        type string;
        mandatory false;
      }
    }
    container accounting {
      config false;
      leaf log-data {
        type string;
        mandatory false;
      }
    }
    container user-group {
      config false;
      leaf grp-data {
        type string;
        mandatory false;
      }
    }
  }
}
