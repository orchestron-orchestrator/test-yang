submodule Cisco-IOS-XR-ha-eem-policy-oper-sub1 {
  belongs-to Cisco-IOS-XR-ha-eem-policy-oper {
    prefix Cisco-IOS-XR-ha-eem-policy-oper;
  }

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR ha-eem-policy package operational data.

     Copyright (c) 2013-2019 by Cisco Systems, Inc.
     All rights reserved.";

  revision 2019-04-05 {
    semver:module-version "1.0.0";
    description
      "Establish semantic version baseline.";
  }
  revision 2016-02-05 {
    description
      "IOS XR 6.0.1 revision.";
  }
  revision 2015-11-09 {
    description
      "IOS XR 6.0 revision.";
  }

  grouping EEM-POLICY {
    description
      "Event manager policy availabe";
    leaf type {
      type string;
      description
        "policy type";
    }
    leaf time-created {
      type string;
      description
        "time created";
    }
    leaf policy-name {
      type string;
      description
        "policy name";
    }
  }

  grouping EEM-POLICY-REG {
    description
      "Event manager policy Registered";
    leaf type {
      type string;
      description
        "policy type";
    }
    leaf time-created {
      type string;
      description
        "time created";
    }
    leaf policy-name {
      type string;
      description
        "policy name";
    }
    leaf class {
      type string;
      description
        "class";
    }
    leaf event-type {
      type string;
      description
        "event type";
    }
    leaf trap {
      type string;
      description
        "trap";
    }
    leaf persist-time {
      type uint32;
      description
        "PersistTime ";
    }
    leaf username {
      type string;
      description
        "username";
    }
    leaf description {
      type string;
      description
        "description";
    }
  }

  grouping EEM-REFRESH-TIME {
    description
      "Event manager refresh-time";
    leaf refreshtime {
      type uint32;
      description
        "Event manager refresh-time ";
    }
  }

  grouping EEM-ENV {
    description
      "Event manager environmental";
    leaf name-xr {
      type string;
      description
        "variable name";
    }
    leaf value {
      type string;
      description
        "value";
    }
  }

  grouping EEM-DIR-USR {
    description
      "Event manager directory user";
    leaf policy {
      type string;
      description
        "policy";
    }
    leaf library {
      type string;
      description
        "library";
    }
  }
}
