submodule Cisco-IOS-XR-ethernet-cfm-oper-sub4 {
  belongs-to Cisco-IOS-XR-ethernet-cfm-oper {
    prefix Cisco-IOS-XR-ethernet-cfm-oper;
  }

  import cisco-semver {
    prefix semver;
  }

  include Cisco-IOS-XR-ethernet-cfm-oper-sub3 {
    revision-date 2023-10-26;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR ethernet-cfm package operational data.

     Copyright (c) 2013-2023 by Cisco Systems, Inc.
     All rights reserved.";

  revision 2023-10-26 {
    semver:module-version "2.0.0";
    description
      "Fix up peer-mep-v2s table name
       2023-02-01
         Add malformed CCM flag
       2022-01-19
         Add CCM and AIS encapsulation conflict errors.
       2022-01-18
         Added CSF packet counters.
       2021-10-22
         Added counters for missing MEP offload intervals.
       2021-09-02
         Added support for LTM statistics.";
  }
  revision 2020-10-07 {
    semver:module-version "1.3.0";
    description
      "Added the Link Loss Forwarding feature.";
  }
  revision 2020-07-07 {
    semver:module-version "1.2.0";
    description
      "Added SLA summary information.";
  }
  revision 2019-10-02 {
    semver:module-version "1.1.0";
    description
      "Bandwidth notification addition";
  }
  revision 2019-04-05 {
    semver:module-version "1.0.0";
    description
      "Establish semantic version baseline.";
  }
  revision 2018-12-20 {
    description
      "Bandwidth notification class and type name update.";
  }
  revision 2017-10-06 {
    description
      "Traceroute transaction ID changed from int to uint.";
  }
  revision 2015-11-09 {
    description
      "IOS XR 6.0 revision.";
  }

  grouping CGM-CFG-ERRORS {
    description
      "CFM Global Manager Service Error Information";
    container bridge-domain-id {
      description
        "BD/XC ID, or Service name if the Service is
         'down-only'";
      uses CFM-BAG-BDID;
    }
    leaf domain-name {
      type string;
      description
        "Domain name";
    }
    leaf level {
      type Cfm-bag-md-level;
      description
        "Level";
    }
    leaf service-name {
      type string;
      description
        "Service name";
    }
    leaf bridge-domain-is-configured {
      type boolean;
      description
        "The BD/XC is configured globally";
    }
    leaf l2-fib-download-error {
      type boolean;
      description
        "The BD/XC could not be downloaded to L2FIB";
    }
  }
}
