module Cisco-IOS-XR-um-flowspec-cfg {
  namespace "http://cisco.com/ns/yang/Cisco-IOS-XR-um-flowspec-cfg";
  prefix um-flowspec-cfg;

  import Cisco-IOS-XR-types {
    prefix xr;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR flowspec package configuration.

     This YANG module augments the
     modules with configuration data.

     Copyright (c) 2020-2022 by Cisco Systems, Inc.
     All rights reserved.";

  revision 2022-07-11 {
    semver:module-version "2.1.0";
    description
      "Added missing description statement to nodes";
  }
  revision 2021-07-20 {
    semver:module-version "2.0.0";
    description
      "Removed duplicate flowspec container under ipv4/ipv6";
  }
  revision 2021-01-05 {
    semver:module-version "1.0.0";
    description
      "Initial release";
  }

  container flowspec {
    presence "Indicates a flowspec node is configured.";
    description
      "FlowSpec configuration";
    container address-families {
      description
        "Address Family Identifier Type (IPv4/IPv6)";
      list address-family {
        key "af-name";
        description
          "Address Family Identifier Type (IPv4/IPv6)";
        leaf af-name {
          type enumeration {
            enum "ipv4" {
              value 1;
              description
                "IPv4 FlowSpec";
            }
            enum "ipv6" {
              value 2;
              description
                "IPv6 FlowSpec";
            }
          }
          description
            "Address Family Identifier Type (IPv4/IPv6)";
        }
        container service-policies {
          description
            "Service Policy configuration";
          list service-policy {
            key "type policy-name";
            description
              "Service Policy configuration";
            leaf type {
              type enumeration {
                enum "pbr" {
                  value 2;
                  description
                    "PBR policy type";
                }
              }
              description
                "Type of the service policy";
            }
            leaf policy-name {
              type xr:Cisco-ios-xr-string {
                length "1..1024" {
                  description
                    "Policy map name";
                }
              }
              description
                "Policy map name";
            }
            container local {
              presence "Indicates a local node is configured.";
              description
                "Only install locally, do not redistribute.";
            }
          }
        }
        container local-install {
          description
            "Local installation of FlowSpec policy";
          container interface-all {
            presence "Indicates a interface-all node is configured.";
            description
              "Install FlowSpec policy on all interfaces";
          }
        }
      }
    }
    container vrfs {
      description
        "VRF configuration";
      list vrf {
        key "vrf-name";
        description
          "VRF configuration";
        leaf vrf-name {
          type xr:Cisco-ios-xr-string {
            length "1..32" {
              description
                "VRF Name";
            }
          }
          description
            "VRF configuration";
        }
        container address-families {
          description
            "Address Family Identifier Type (IPv4/IPv6)";
          list address-family {
            key "af-name";
            description
              "Address Family Identifier Type (IPv4/IPv6)";
            leaf af-name {
              type enumeration {
                enum "ipv4" {
                  value 1;
                  description
                    "IPv4 FlowSpec";
                }
                enum "ipv6" {
                  value 2;
                  description
                    "IPv6 FlowSpec";
                }
              }
              description
                "Address Family Identifier Type (IPv4/IPv6)";
            }
            container service-policies {
              description
                "Service Policy configuration";
              list service-policy {
                key "type policy-name";
                description
                  "Service Policy configuration";
                leaf type {
                  type enumeration {
                    enum "pbr" {
                      value 2;
                      description
                        "PBR policy type";
                    }
                  }
                  description
                    "Type of the service policy";
                }
                leaf policy-name {
                  type xr:Cisco-ios-xr-string {
                    length "1..1024" {
                      description
                        "Policy map name";
                    }
                  }
                  description
                    "Policy map name";
                }
                container local {
                  presence "Indicates a local node is configured.";
                  description
                    "Only install locally, do not redistribute.";
                }
              }
            }
            container local-install {
              description
                "Local installation of FlowSpec policy";
              container interface-all {
                presence "Indicates a interface-all node is configured.";
                description
                  "Install FlowSpec policy on all interfaces";
              }
            }
          }
        }
      }
    }
    container local-install {
      description
        "Local installation of FlowSpec policy";
      container interface-all {
        presence "Indicates a interface-all node is configured.";
        description
          "Install FlowSpec policy on all interfaces";
      }
    }
  }
}
