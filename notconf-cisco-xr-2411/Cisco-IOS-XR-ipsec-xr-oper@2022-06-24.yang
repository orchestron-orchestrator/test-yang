module Cisco-IOS-XR-ipsec-xr-oper {
  namespace "http://cisco.com/ns/yang/Cisco-IOS-XR-ipsec-xr-oper";
  prefix ipsec-xr-oper;

  import Cisco-IOS-XR-types {
    prefix xr;
  }
  import cisco-semver {
    prefix semver;
  }

  include Cisco-IOS-XR-ipsec-xr-oper-sub1 {
    revision-date 2022-06-24;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ipsec-xr package operational data.

     This module contains definitions
     for the following management objects:
       ipsec: Ipsec sa operational data

     Copyright (c) 2013-2022 by Cisco Systems, Inc.
     All rights reserved.";

  revision 2022-06-24 {
    semver:module-version "1.0.0";
    description
      "Pfs field addition.";
  }
  revision 2021-09-24 {
    description
      "Initial yang support for ipsec oper.";
  }
  revision 2019-04-05 {
    description
      "Establish semantic version baseline.";
  }
  revision 2015-11-09 {
    description
      "IOS XR 6.0 revision.";
  }

  container ipsec {
    config false;
    description
      "Ipsec sa operational data";
    container ipsec-sa {
      description
        "Ipsec Sa Details";
      container interfaces {
        description
          "List of Interface Sas";
        list interface {
          key "name";
          description
            "IPSec interface name";
          leaf name {
            type xr:Interface-name;
            description
              "Interface name";
          }
          uses IPSEC-EDM-INTERFACE-SAS;
        }
      }
    }
  }
}
