submodule Cisco-IOS-XR-cmproxy-oper-sub1 {
  belongs-to Cisco-IOS-XR-cmproxy-oper {
    prefix Cisco-IOS-XR-cmproxy-oper;
  }

  import ietf-inet-types {
    prefix inet;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR cmproxy package operational data.

     Copyright (c) 2013-2020 by Cisco Systems, Inc.
     All rights reserved.";

  revision 2020-03-25 {
    semver:module-version "2.0.0";
    description
      "Moved few of the bag fields to private";
  }
  revision 2019-04-05 {
    semver:module-version "1.0.1";
    description
      "Establish semantic version baseline.";
  }
  revision 2018-03-04 {
    description
      "Added good description for bag fields";
  }
  revision 2015-11-09 {
    description
      "IOS XR 6.0 revision.";
  }

  grouping CMP-INV-ST {
    description
      "cmp inv info";
    leaf card-type {
      type string {
        length "0..32";
      }
      description
        "Type of the card";
    }
    leaf node-name {
      type string {
        length "0..32";
      }
      description
        "Node Name";
    }
    leaf partner-name {
      type string {
        length "0..32";
      }
      description
        "Partner Node";
    }
    leaf red-state {
      type string {
        length "0..32";
      }
      description
        "Redundancy Role";
    }
    leaf node-sw-state {
      type string {
        length "0..32";
      }
      description
        "Current Software State";
    }
    leaf prev-sw-state {
      type string {
        length "0..32";
      }
      description
        "Previous Software State";
    }
    leaf node-address {
      type inet:ipv4-address;
      description
        "Node IPv4 Address";
    }
  }
}
