submodule Cisco-IOS-XR-perf-meas-oper-sub1 {
  belongs-to Cisco-IOS-XR-perf-meas-oper {
    prefix Cisco-IOS-XR-perf-meas-oper;
  }

  import ietf-inet-types {
    prefix inet;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR perf-meas package operational data.

     Copyright (c) 2013-2023 by Cisco Systems, Inc.
     All rights reserved.";

  revision 2023-11-22 {
    semver:module-version "6.0.0";
    description
      "Add flow label to PM profile bags
       2023-11-14
         Add Session ID for Interface, RSVP-TE, SR-Policy telemetry
       2023-10-20
         Add atomic paths to endpoint liveness segment list
       2023-10-19
         Add reverse path in endpoint liveness
       2023-10-16
         Add NetIO status for probe running state
       2023-10-03
         Add anomaly loss to delay profile
       2023-08-16
         Add transport type to distribution database
       2023-07-31
         Add rx tx packet and history counters for delay measurement
       2023-06-14
         Add source port under NPU and source port under local Capability information
       2023-03-20
         Add PM allowed-querier and allowed-responder prefix summary information
       2023-03-15
         Add optional endpoint node sid in SRv6 policy
       2023-03-14
         Add hardware timestamping capability flag
       2023-02-23
         Add probe error for incompatible source-address family config
       2023-01-31
         Deprecate typed profile
       2023-01-24
         Add segment list info for endpoint sessions history
       2022-07-08
         Add segment list liveness info for distribution record
       2022-05-31
         Remove non-related fields for interface PT bag
       2022-05-15
         Change npu-offload-session-eabled to npu-offload-session-enabled in pm_srpolicy_candidate_path_bag.
       2022-04-25
         Add new advertisement reason for PM interface path tracing attribute
       2022-04-06
         Change hardware to npu in offload elements.
       2022-04-05
         Updated error reason for UDP port failure and capability timestamp to usec.
       2022-03-16
         Add new data points.
       2022-03-15
         NPU effective burst and tx timer in profile.
       2022-03-09
         Per transport CPU counters for generic profile.
       2022-02-22
         Change display format in show performance measure profile.
       2022-01-28
         Remove packet counters and add pm_npu_session_packet_counters_bag in pm_npu_counters_info_bag.
       2022-01-15
         npu offload support, npu ports and distribution retry queue.
       2021-11-18
         Added transport specific parameters to profile information.
       2021-10-27
         Added tx-interval to profile information.";
  }
  revision 2021-06-15 {
    semver:module-version "5.0.0";
    description
      "Added default TWAMP port entry in pm_rx_udp_ports_bag.";
  }
  revision 2021-06-02 {
    semver:module-version "4.0.0";
    description
      "Added session id to endpoint liveness bag.
       2021-04-17
           Removed liveness parameters from delay profile bag.
       2021-02-26
           Remove PM hidden show cli, loss, history packet.
       2021-02-16
           Remove liveness history and liveness detection verbose from sr-policy delay schema.
       2021-01-08
           Added srpolicy liveness schema.
       2021-01-08
           Added srpolicy liveness history schema and renamed liveness detection schema.
       2020-12-19
           Added schema for endpoint liveness profile.
       2020-12-02
           Add sr-policy liveness profile bag and oper schema.
       2020-11-26
           Update endpoint show command bags in order to support liveness-detection.
       2020-11-17
           Added new bag for PPS info. IosSetYangSchemaRev Cisco-IOS-XR-perf-meas-oper
       2020-10-27
           Added anomaly support for sr-policy min delay metrics.
       2020-10-27
           Added all endpoint show commands support and respective bags.
       2020-10-15
           Update probe running reason name for link down.
       2020-10-02
           Added anomaly support for interface min delay metrics.
       2020-08-06
           Added liveness session state history information.
       2020-07-23
           Fixed typos in perf-meas oper bag.";
  }
  revision 2020-06-24 {
    semver:module-version "3.0.0";
    description
      "Update perf-meas oper schema task group.
       2020-04-10
         Added new TX error counter for next hop MAC missing.
       2020-03-31
       721 nohelp CLI for liveness, loopback, endpoint, src-port, named profile, distribution.
       2020-03-25
         Add trace id in PM session bag.
       2020-03-17
         Added new types counters to count different types of PM DM sessions.
       2020-03-09
         Added new types of probe running errors and counters for probe running errors.
       2020-02-24
         Modifid type of service knobs from array to integer.
       2020-02-21
         Modify router alert type
       2020-02-19
         Modifiy periodic minimum change value.
       2020-02-13
         Modifiy delay-measurement hisotry key words.
       2020-01-22
         Added a new advertisement reason for interface delay-measurement.
       2019-12-16
         Revision IOS XR 7.2.1 Added responder src address and num of hops for PM DM.
       2019-12-09
         Added new reason for DM probe not running.
       2019-11-18
         Revision IOS XR 7.2.1 Added EDT for Liveness state for SR Policy Candidate path atmoic path.";
  }
  revision 2019-10-19 {
    semver:module-version "2.0.0";
    description
      "Added burst-interval-effective to oper data.";
  }
  revision 2019-04-05 {
    semver:module-version "1.0.0";
    description
      "Establish semantic version baseline.";
  }
  revision 2018-12-13 {
    description
      "Revision IOS XR 7.0.1 Added delay measurment for SR Policy and RSVP-TE LSP.";
  }
  revision 2017-10-17 {
    description
      "Revision Zero.";
  }
  revision 2015-11-09 {
    description
      "IOS XR 6.0 revision.";
  }

  grouping PM-RESP-INTF-BAG {
    description
      "PM Responder Interface bag";
    container interface-counters {
      description
        "Per interface responder counters";
      uses PM-COUNTER-RESP-BAG;
    }
    leaf interface-name-xr {
      type string;
      description
        "Name of the interface";
    }
    leaf interface-handle {
      type uint32;
      description
        "Ifhandle of the interface";
    }
    leaf source-address {
      type inet:ipv4-address;
      description
        "Source Address of the interface";
    }
    leaf source-v6-address {
      type inet:ipv6-address;
      description
        "Source V6 Address of the interface";
    }
    leaf link-local-iv6-address {
      type inet:ipv6-address;
      description
        "Link local IPv6 of the interface";
    }
    leaf packet-rate {
      type uint32;
      description
        "Incoming packet rate of the interface";
    }
    leaf packet-rate-high-water-mark {
      type uint32;
      description
        "Incoming packet rate high water mark of the
         interface";
    }
    leaf cleanup-time-remaining {
      type uint32;
      units "second";
      description
        "Seconds until an inactive interface is cleaned
         up";
    }
  }

  grouping PM-COUNTER-RESP-BAG {
    description
      "PM Responder counters";
    leaf reply-packet-sent {
      type uint64;
      description
        "Number of response packets sent";
    }
    leaf reply-packet-sent-error {
      type uint64;
      description
        "Number of response packets sent error";
    }
    leaf query-packet-received {
      type uint64;
      description
        "Number of response packets received";
    }
    leaf received-packet-error-uro-tlv-not-present {
      type uint64;
      description
        "Number of received packet error caused by URO
         TLV not present";
    }
    leaf received-packet-error-invalid-source-port-number {
      type uint64;
      description
        "Number of received packet error caused by source
         port number is invaid";
    }
    leaf received-packet-error-no-source-address {
      type uint64;
      description
        "Number of received packet error caused by no
         source address";
    }
    leaf received-packet-error-no-return-path {
      type uint64;
      description
        "Number of received packet error caused by no
         return path";
    }
    leaf received-packet-error-invalid-querier-control-code {
      type uint64;
      description
        "Number of received packet error caused by
         querier control code is invalid";
    }
    leaf received-packet-error-unsupported-timestamp-format {
      type uint64;
      description
        "Number of received packet error caused by
         timestamp format in the packet is not supported";
    }
    leaf received-packet-error-timestamp-not-available {
      type uint64;
      description
        "Number of packet error caused by timestamp in
         received packet is not available";
    }
    leaf received-packet-error-unsupported-mandatory-tlv {
      type uint64;
      description
        "Number of received packet error caused by
         unsupported mandatory TLV";
    }
    leaf received-packet-error-invalid-packet {
      type uint64;
      description
        "Number of received packet error caused by
         invalid packet";
    }
  }

  grouping PM-RESP-SUMMARY-BAG {
    description
      "PM Responder summary bag";
    container responder-counters {
      description
        "Global counters of responder";
      uses PM-COUNTER-RESP-BAG;
    }
    leaf total-interfaces {
      type uint32;
      description
        "Number of interfaces in the responder cache";
    }
    leaf packet-rate {
      type uint32;
      description
        "Global incoming packet rate";
    }
    leaf packet-rate-high-water-mark {
      type uint32;
      description
        "Global incoming packet rate high water mark";
    }
  }
}
