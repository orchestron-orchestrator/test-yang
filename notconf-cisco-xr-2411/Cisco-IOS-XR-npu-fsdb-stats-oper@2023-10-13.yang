module Cisco-IOS-XR-npu-fsdb-stats-oper {
  namespace "http://cisco.com/ns/yang/Cisco-IOS-XR-npu-fsdb-stats-oper";
  prefix npu-fsdb-stats-oper;

  import Cisco-IOS-XR-types {
    prefix xr;
  }
  import cisco-semver {
    prefix semver;
  }

  include Cisco-IOS-XR-npu-fsdb-stats-oper-sub1 {
    revision-date 2023-10-13;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR npu-fsdb-stats package operational data.

     This module contains definitions
     for the following management objects:
       npu: Fabric Data

     Copyright (c) 2013-2023 by Cisco Systems, Inc.
     All rights reserved.";

  revision 2023-10-13 {
    semver:module-version "3.0.0";
    description
      "Updated the model for debug-utils options
       2022-03-03
         Updated the yang model for link FSM entry
       2022-02-11
         Added weight distribution to npu driver info";
  }
  revision 2021-05-14 {
    semver:module-version "2.0.0";
    description
      "Updated the type of fabric operational mode in the yang model";
  }
  revision 2020-10-10 {
    semver:module-version "1.0.0";
    description
      "Yang Schema for npu driver link info";
  }
  revision 2019-04-05 {
    description
      "Establish semantic version baseline.";
  }
  revision 2015-11-09 {
    description
      "IOS XR 6.0 revision.";
  }

  typedef Link-option-string {
    type string {
      pattern "(flap)|(topo)|(fsm)";
    }
    description
      "flap:Display link flap info, topo:Display link
       topo info, fsm:Link state FSM info";
  }

  typedef Npu-max-asic-instances {
    type uint32 {
      range "0..255";
    }
    description
      "Npu max asic instances";
  }

  typedef Debug-util-option-string {
    type string {
      pattern "(get-counters)|(counters-drops)|(oq-debug)|(fabric-debug)";
    }
    description
      "get-counters:Get asic's slice level counters,
       counters-drops:topo:Get asic's slice level drop
       counters, oq-debug:Get asic's output debug info,
       fabric-debug: Get fabric debug info";
  }

  typedef Link-info-max-number {
    type uint32 {
      range "0..255";
    }
    description
      "Link info max number";
  }

  container npu {
    config false;
    description
      "Fabric Data";
    list node {
      key "node-name";
      description
        "Data for particular node";
      container rx-link-information {
        description
          "NPU link rx information";
        container link-options {
          description
            "Option table for link rx information";
          list link-option {
            key "option";
            description
              "Option : topo , fsm , flap";
            container rx-asic-instances {
              description
                "Instance table for rx information";
              list rx-asic-instance {
                key "instance";
                description
                  "Instance number for rx link information";
                container rx-links {
                  description
                    "Link table class for rx information";
                  list rx-link {
                    description
                      "Link number for rx link information";
                    leaf start-number {
                      type Link-info-max-number;
                      description
                        "Start number";
                    }
                    leaf end-number {
                      type Link-info-max-number;
                      description
                        "End number";
                    }
                    leaf status-option {
                      type xr:Cisco-ios-xr-string;
                      description
                        "RX link status option";
                    }
                    list rx-link {
                      key "link";
                      description
                        "Single link information";
                      leaf link {
                        type uint32;
                        description
                          "Single link";
                      }
                      uses NPU-EDM-RXLINK;
                    }
                  }
                }
                leaf instance {
                  type Npu-max-asic-instances;
                  description
                    "Receive instance";
                }
              }
            }
            leaf option {
              type Link-option-string;
              description
                "Link option";
            }
          }
        }
      }
      container driver-info {
        description
          "NPU Driver Info";
        uses NPU-EDM-DRIVER-INFO;
      }
      container tx-link-information {
        description
          "NPU link TX information";
        container tx-status-option-table {
          description
            "Link table for tx information";
          container tx-status-option {
            description
              "Option: data, ctrl, all- for now none";
            container tx-asic-instances {
              description
                "Instance table for tx information";
              list tx-asic-instance {
                key "instance";
                description
                  "Instance number for tx link information";
                container tx-links {
                  description
                    "Link table for tx information";
                  list tx-link {
                    description
                      "Link number for tx link information";
                    leaf start-number {
                      type Link-info-max-number;
                      description
                        "Start number";
                    }
                    leaf end-number {
                      type Link-info-max-number;
                      description
                        "End number";
                    }
                    list tx-link {
                      key "link";
                      description
                        "Single link information";
                      leaf link {
                        type uint32;
                        description
                          "Single Link";
                      }
                      uses NPU-EDM-TXLINK;
                    }
                  }
                }
                leaf instance {
                  type Npu-max-asic-instances;
                  description
                    "Transmit instance";
                }
              }
            }
          }
        }
      }
      container instance-tables {
        description
          "NPU statistics";
        list instance-table {
          key "instance";
          description
            "Instance Number";
          container fmac-link-tables {
            description
              "FMAC statistics";
            list fmac-link-table {
              key "link";
              description
                "Link Number";
              container fmac-brief-statistics {
                description
                  "NPU FMAC Statistics";
                uses NPU-EDM-STATS-ASIC-FMAC-INFO;
              }
              leaf link {
                type uint32;
                description
                  "Link Number";
              }
            }
          }
          leaf instance {
            type uint32;
            description
              "Instance Number";
          }
        }
      }
      container debug-utils-asic-instances {
        description
          "Debug Utils";
        list debug-utils-asic-instance {
          key "instance";
          description
            "Instance Number";
          leaf instance {
            type uint32;
            description
              "Instance Number";
          }
          list debug-utils-option {
            key "option";
            description
              "option";
            container debug-utils-output {
              description
                "output";
              uses NPU-EDM-DEBUG-UTILS-INFO;
            }
            leaf option {
              type Debug-util-option-string;
              description
                "debug option";
            }
          }
        }
      }
      leaf node-name {
        type xr:Node-id;
        description
          "Node ID";
      }
    }
  }
}
