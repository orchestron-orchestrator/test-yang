submodule Cisco-IOS-XR-mpls-te-oper-sub8 {
  belongs-to Cisco-IOS-XR-mpls-te-oper {
    prefix Cisco-IOS-XR-mpls-te-oper;
  }

  import ietf-inet-types {
    prefix inet;
  }
  import cisco-semver {
    prefix semver;
  }

  include Cisco-IOS-XR-mpls-te-oper-sub5 {
    revision-date 2023-10-10;
  }
  include Cisco-IOS-XR-mpls-te-oper-sub6 {
    revision-date 2023-10-10;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR mpls-te package operational data.

     Copyright (c) 2013-2023 by Cisco Systems, Inc.
     All rights reserved.";

  revision 2023-10-10 {
    semver:module-version "1.3.0";
    description
      "Added source address to configured P2MP tunnel data
       2023-07-05
         Add knob to configure Autoroute Announce exclude all SR traffic
       2023-06-19
         Added flooding reason stats
       2023-04-24
         Add back TunnelAttributeSetStatic for backward compatibility
       2023-02-02
         Remove hidden commands
       2022-11-07
         Add TE++ over numbered tunnel feature
       2022-08-30
         Extending self-ping statistics bag
       2022-07-07
         Removed TunnelAttributeSetStatic from TunnelAttributeSetType
       2022-03-18
         Added self-ping under named-tunnels";
  }
  revision 2021-08-09 {
    semver:module-version "1.2.0";
    description
      "Added load-interval attribute in the tunnel class. IosSetYangSchemaRev Cisco-IOS-XR-mpls-te-oper";
  }
  revision 2021-01-19 {
    semver:module-version "1.1.0";
    description
      "Added bandwidth-protection for auto-backups. Added signalled-bandwidth and soft-preemption for attribute set of autobackups.
       2020-11-05
           Added secondary router id for TE nodes.";
  }
  revision 2020-03-28 {
    semver:module-version "1.0.0";
    description
      "Added dark bandwidth accounting related oper info. Added stateful PCE static delegation related oper info. Added P2MP TE realted oper info. Added new operational leaves sim-rate-set sim-rate pce-address rewrite-lsd-queue tunnel-id-xr controller-handle backup-tunnel-sig-name protected-interface attribute-set-crc32 error delegation-status error context rewrite-lsd-queue simrate-enabled-in-last-application tunnel-id-xr p2mp-id-xr lsp-id-xr source-address-xr simrate-enabled-in-last-application is-expand-timer-running expand-timer-duration expand-timer-remain egress-interface-handle ingress-interface-handle srdb-check-enabled destination-create-time link-if-index create-time is-config-pending attribute-set-crc32 destination-list-crc32 maximum-destination-count maximum-tunnel-count srlg-number-xr tunnel-interface-name lsp-id-xr tunnel-rewrite-ctype tunnel-load-share tunnel-policy-class tunnel-forward-class lmp-is-allocated topology-node-igp-id topology-node-igp-area topology-node-is-router link-id classification-flags current-lsp-bandwidth-requested current-lsp-bandwidth-requested-type standby-lsp-bandwidth-requested standby-lsp-bandwidth-requested-type reopt-lsp-bandwidth-requested reopt-lsp-bandwidth-requested-type standby-reopt-lsp-bandwidth-requested standby-reopt-lsp-bandwidth-requested-type destination-address error tunnel-name-xr interface-name-xr interface-name";
  }
  revision 2019-04-05 {
    semver:module-version "1.0.0";
    description
      "Establish semantic version baseline.";
  }
  revision 2018-08-01 {
    description
      "Removed empty groupings.";
  }
  revision 2017-09-07 {
    description
      "Fixed type translation error.";
  }
  revision 2017-05-01 {
    description
      "Fixing backward compatibility error in module.";
  }
  revision 2015-11-09 {
    description
      "IOS XR 6.0 revision.";
  }

  typedef Te-stats-sig-filter {
    type enumeration {
      enum "te-stat-sig-filter-vif" {
        description
          "te stat sig filter vif";
      }
      enum "te-stat-sig-filter-lsp" {
        description
          "te stat sig filter lsp";
      }
    }
    description
      "TE Signaling Filter types";
  }

  grouping MPLS-TE-BFD-SESSION-COUNTERS {
    description
      "TE BFDoLM counters";
    leaf session-create-events {
      type uint32;
      description
        "The number of BFDOverLM session create events";
    }
    leaf session-up-events {
      type uint32;
      description
        "The number of BFDOverLM session up events";
    }
    leaf session-creation-failed-events {
      type uint32;
      description
        "The number of BFDOverLM session creation failed
         events";
    }
    leaf session-down-events {
      type uint32;
      description
        "The number of BFDOverLM session down events";
    }
    leaf session-admin-down-events {
      type uint32;
      description
        "The number of BFDOverLM session admin down
         events";
    }
    leaf session-gracefully-delete-events {
      type uint32;
      description
        "The number of BFDOverLM session gracefully
         delete events";
    }
    leaf session-non-gracefully-delete-events {
      type uint32;
      description
        "The number of BFDOverLM session non gracefully
         delete events";
    }
    leaf session-replay-events {
      type uint32;
      description
        "The number of BFDOverLSP session replay events";
    }
  }

  grouping MPLS-TE-BFD-COUNTERS {
    description
      "TE BFD Counters";
    container bfd-over-lsp-head-counters {
      description
        "BFD over Head-end LSPs Cumulative Counters";
      uses MPLS-TE-BFD-LSP-COUNTERS;
    }
    container sbfd-over-lsp-head-counters {
      description
        "SBFD over Head-end LSPs Cumulative Counters";
      uses MPLS-TE-BFD-LSP-COUNTERS;
    }
    container bfd-over-lsp-tail-counters {
      description
        "BFD over Tail-end LSPs Cumulative Counters";
      uses MPLS-TE-BFD-SESSION-COUNTERS;
    }
    container bf-do-lm-counters {
      description
        "BFD over Links Cumulative Counters";
      uses MPLS-TE-BFD-SESSION-COUNTERS;
    }
    leaf last-cleared-timestamp {
      type uint32;
      description
        "The timestamp when these stats are cleared
         relative to Jan 1, 1970";
    }
  }

  grouping SYNC-RETRY-STATS {
    description
      "TE Sync Retry Stats";
    leaf num-sync-retry-timer-started {
      type uint32;
      description
        "Number of times the sync retry timer gets
         started";
    }
    leaf num-sync-retry-timer-expired {
      type uint32;
      description
        "Number of times the sync retry timer expires and
         gets processed";
    }
    leaf num-sync-retry-vif {
      type uint32;
      description
        "Number of times a re-sync is triggered for all
         VIFs";
    }
    leaf num-sync-retry-s2l {
      type uint32;
      description
        "Number of times a re-sync is triggered for all
         S2Ls";
    }
  }

  grouping TE-STATS-DARKBW-INFO {
    description
      "Dark bandwidth counters";
    leaf last-cleared-timestamp {
      type uint32;
      description
        "The timestamp when these stats are cleared
         relative to Jan 1, 1970";
    }
    leaf bandwidth-application-count {
      type uint32;
      description
        "Number of bandwidth accounting applications";
    }
    leaf bandwidth-sample-count {
      type uint32;
      description
        "Number of bandwidth accounting samples";
    }
    leaf invalid-sample-count {
      type uint32;
      description
        "Number of invalid bandwidth accounting samples";
    }
    leaf skipped-application-count {
      type uint32;
      description
        "Number of skipped bandwidth accounting
         applications";
    }
    leaf capped-sample-count {
      type uint32;
      description
        "Number of capped bandwidth accounting samples";
    }
    leaf high-latency-count {
      type uint32;
      description
        "Number of statsd requests that returned with
         high latency";
    }
  }

  grouping TE-P2MP-Q-OP-ARRAY {
    description
      "Array used to store stats for Q enqueues and
       dequeues";
    leaf-list te-p2mp-q-op-array {
      type uint32;
      max-elements 2;
      description
        "te p2mp q op array";
    }
  }

  grouping P2MP-Q-ELEM-OP-STATS {
    description
      "P2MP Q statistics";
    container qdq-counts {
      description
        "Count of the operations";
      uses TE-P2MP-Q-OP-ARRAY;
    }
    leaf maximum-delay {
      type uint64;
      description
        "Maximum delay in an event being processed";
    }
    leaf failed-enqueues {
      type uint32;
      description
        "Failed enqueue of an event";
    }
    leaf high-water-mark {
      type uint32;
      description
        "High water mark of Q'd events";
    }
    leaf total-latency {
      type uint64;
      description
        "Total latency of all events";
    }
    leaf number-of-reschedules {
      type uint32;
      description
        "Number of DQ reschedules";
    }
    leaf failed-reschedules {
      type uint32;
      description
        "Number of failed DQ reschedules";
    }
    leaf unfound-s2-ls {
      type uint32;
      description
        "Number of S2Ls unfound for event processing";
    }
    leaf deleted-s2-ls {
      type uint32;
      description
        "Number of S2Ls deleted";
    }
    leaf propagated-events {
      type uint32;
      description
        "Number of propagated events";
    }
    leaf successfull-processed-events {
      type uint32;
      description
        "Number of events successfully processed by the
         state machine";
    }
    leaf unsuccessfull-processed-events {
      type uint32;
      description
        "Number of events unsuccessfully processed by the
         state machine";
    }
    leaf drop-for-creation-time {
      type uint32;
      description
        "Number of events dropped due to T of event < T
         of S2L creation";
    }
  }

  grouping TE-STATS-SIG-FILTER-DATA-U {
    description
      "Union of TE Signalling Filter data";
    container te-signalling-filter-vif {
      when "../statistics-filter = 'te-stat-sig-filter-vif'" {
        description
          "../StatisticsFilter = 'TE_STAT_SIG_FILTER_VIF'";
      }
      description
        "VIF data";
      uses TE-STATS-BAG-VIF;
    }
    container te-signalling-filter-lsp {
      when "../statistics-filter = 'te-stat-sig-filter-lsp'" {
        description
          "../StatisticsFilter = 'TE_STAT_SIG_FILTER_LSP'";
      }
      description
        "LSP data";
      uses TE-STATS-BAG-LSP;
    }
    leaf statistics-filter {
      type Te-stats-sig-filter;
      description
        "StatisticsFilter";
    }
  }

  grouping TE-STATS-SIG-FILTER {
    description
      "TE Signaling Filter Data";
    container te-signalling-filter-data {
      description
        "TE Signaling Filter data";
      uses TE-STATS-SIG-FILTER-DATA-U;
    }
  }

  grouping TE-STATS-BAG-LSP {
    description
      "MPLS TE LSP Statistics";
    container statistics {
      description
        "LSP statistics";
      uses TE-STATS-SIG;
    }
    leaf tunnel-name {
      type string;
      description
        "Tunnel Name";
    }
    list s2l-statistic {
      description
        "List of S2L Statistics";
      uses TE-STATS-BAG-S2L;
    }
  }

  grouping TE-STATS-BAG-S2L {
    description
      "MPLS TE S2L Statistics";
    container statistics {
      description
        "S2L stats";
      uses TE-STATS-SIG;
    }
    leaf sub-group-originator {
      type inet:ipv4-address;
      description
        "Subgroup Originator";
    }
    leaf sub-group-id {
      type uint16;
      description
        "subgroup ID";
    }
    leaf destination-address {
      type inet:ipv4-address;
      description
        "Destination address";
    }
  }

  grouping TE-STATS-BAG-DEST {
    description
      "MPLS TE Destination Statistics";
    container statistics {
      description
        "Destination stats";
      uses TE-STATS-SIG;
    }
    leaf destination-address {
      type inet:ipv4-address;
      description
        "Destination address";
    }
    list s2l-statistic {
      description
        "List of S2L Stats";
      uses TE-STATS-BAG-S2L;
    }
  }

  grouping TE-STATS-SIG {
    description
      "Send-Recv count for TE Signaling";
    leaf tx-event-unknown {
      type uint32;
      description
        "Unknown TX events";
    }
    leaf tx-path-create-event {
      type uint32;
      description
        "TX Path Create event";
    }
    leaf tx-path-change-event {
      type uint32;
      description
        "TX Path Change event";
    }
    leaf tx-path-delete-event {
      type uint32;
      description
        "TX Path Delete event";
    }
    leaf tx-path-error-event {
      type uint32;
      description
        "TX Path Error event";
    }
    leaf tx-resv-create-event {
      type uint32;
      description
        "TX Resv Create event";
    }
    leaf tx-resv-change-event {
      type uint32;
      description
        "TX Resv Change event";
    }
    leaf tx-resv-delete-event {
      type uint32;
      description
        "TX Resv Delete event";
    }
    leaf tx-resv-error-event {
      type uint32;
      description
        "TX Resv Error event";
    }
    leaf tx-path-reeval-query-event {
      type uint32;
      description
        "TX Path Reeval Query event";
    }
    leaf rx-event-unknown {
      type uint32;
      description
        "RX Unknown events";
    }
    leaf rx-path-create-event {
      type uint32;
      description
        "RX Path Create event";
    }
    leaf rx-path-change-event {
      type uint32;
      description
        "RX Path Change event";
    }
    leaf rx-path-delete-event {
      type uint32;
      description
        "RX Path Delete event";
    }
    leaf rx-path-error-event {
      type uint32;
      description
        "RX Path Error event";
    }
    leaf rx-resv-create-event {
      type uint32;
      description
        "RX Resv Create event";
    }
    leaf rx-resv-change-event {
      type uint32;
      description
        "RX Resv Change event";
    }
    leaf rx-resv-delete-event {
      type uint32;
      description
        "RX Resv Delete event";
    }
    leaf rx-resv-error-event {
      type uint32;
      description
        "RX Resv Error event";
    }
    leaf rx-path-reeval-query-event {
      type uint32;
      description
        "RX Path Reeval Query event";
    }
    leaf tx-backup-assign-event {
      type uint32;
      description
        "Backup Assign event";
    }
    leaf rx-backup-assign-err-event {
      type uint32;
      description
        "Error on Backup Assign event";
    }
    leaf events-total-count {
      type uint32;
      description
        "Total TE Signalling event count";
    }
    leaf events-count {
      type uint32;
      description
        "TE Signaling event count";
    }
  }

  grouping TE-STATS-BAG-VIF {
    description
      "MPLS TE VIF Statistics";
    container statistics {
      description
        "VIF stats";
      uses TE-STATS-SIG;
    }
    leaf tunnel-name {
      type string;
      description
        "Tunnel Name";
    }
    leaf tunnel-sig-name {
      type string;
      description
        "Tunnel Signalled-Name";
    }
    leaf lsp-id {
      type uint16;
      description
        "LSP ID";
    }
    list destination-statistic {
      description
        "List of Destination Stats";
      uses TE-STATS-BAG-DEST;
    }
  }

  grouping TE-S2L-FSM-EVENT-ARRAY {
    description
      "Array to store S2L FSM events for a state";
    leaf-list te-s2l-fsm-event-array {
      type uint32;
      max-elements 55;
      description
        "te s2l fsm event array";
    }
  }

  grouping TE-S2L-FSM-STATS-ARRAY {
    description
      "Array to store S2L FSM stats";
    list te-s2l-fsm-stats-array {
      max-elements 19;
      description
        "te s2l fsm stats array";
      uses TE-S2L-FSM-EVENT-ARRAY;
    }
  }

  grouping TE-FSM-UNEXPECTED-EVENT-STATS {
    description
      "TE S2L FSM Unexpected Event Stats";
    container head-fsm-events {
      description
        "FSM unexpected event stats for headend S2Ls";
      uses TE-S2L-FSM-STATS-ARRAY;
    }
    container mid-fsm-events {
      description
        "FSM unexpected event stats for midpoint S2Ls";
      uses TE-S2L-FSM-STATS-ARRAY;
    }
    container tail-fsm-events {
      description
        "FSM unexpected event stats for tailend S2Ls";
      uses TE-S2L-FSM-STATS-ARRAY;
    }
    leaf last-cleared-time {
      type uint32;
      description
        "Timestamp when the stat has been cleared";
    }
    leaf unexpected-event-num {
      type uint32;
      description
        "Total number of unexpected events";
    }
  }

  grouping MPLS-TE-SYNC-COUNT-INFO {
    description
      "MPLS TE NSR and ISSU counters";
    leaf last-cleared-timestamp {
      type uint32;
      units "second";
      description
        "The timestamp, in seconds, when these statistics
         are cleared              since 00:00:00 UTC,
         January 1, 1970";
    }
    leaf role {
      type Te-proc-role;
      description
        "Process role";
    }
    leaf last-idt-states {
      type uint32;
      description
        "Last IDT States";
    }
    leaf total-states {
      type uint32;
      description
        "Total states";
    }
    leaf total-deletions {
      type uint32;
      description
        "Total deletions";
    }
    leaf total-nac-ks {
      type uint64;
      description
        "Total NACKs";
    }
    leaf total-id-ts {
      type uint32;
      description
        "Total IDTs";
    }
  }

  grouping MPLS-TE-SOFT-PREEMPTION-STATS {
    description
      "Soft preemption stats ";
    leaf last-cleared-timestamp {
      type uint32;
      description
        "The timestamp when these stats are cleared
         relative to Jan 1, 1970";
    }
    leaf soft-preemption-events {
      type uint32;
      description
        "The number of soft preemption events triggered";
    }
    leaf soft-preempted-ls-ps {
      type uint32;
      description
        "The number of LSPs that have been soft preempted
         at this node";
    }
    leaf timed-out-soft-preempted-lsp-ss {
      type uint32;
      description
        "The number of LSPs that have been soft preempted
         and timed out at this node";
    }
    leaf torn-down-soft-preempted-ls-ps {
      type uint32;
      description
        "The number of LSPs that have been soft preempted
         at this node and torn down before timing out";
    }
    leaf frr-triggered-soft-preempted-lsp-ss {
      type uint32;
      description
        "The number of LSPs that have been soft preempted
         and then fast rerouted at this node";
    }
    leaf minimum-time-in-soft-preempted-state {
      type uint16;
      units "second";
      description
        "The minimum number of seconds an LSP remained in
         the soft preempted state";
    }
    leaf time-in-soft-preempted-state-max {
      type uint16;
      units "second";
      description
        "The maximum number of seconds an LSP remained in
         the soft preempted state without being hard
         preempted";
    }
    leaf time-in-soft-preempted-state-avg {
      type uint16;
      units "second";
      description
        "The average number of seconds an LSP remained in
         the soft preempted state. This excludes the
         timed out LSPs";
    }
    leaf soft-preempted-head-ls-ps {
      type uint32;
      description
        "Number of soft preempted LSPs at the headend.
         This is relevant to the headend";
    }
    leaf reoptimized-soft-preempted-ls-ps {
      type uint32;
      description
        "Number of soft preemption LSPs that are
         reoptimized. This is relevant to the headend";
    }
    leaf torndown-soft-preempted-ls-ps {
      type uint32;
      description
        "Number of soft preemption LSPs that are torn
         down instead of being reoptimized. This is
         relevant to the headend.";
    }
    leaf path-protected-switchover-soft-preempted-ls-ps {
      type uint32;
      description
        "Number of soft preemption LSPs that are replaced
         with the path protection LSP. This is relevant
         to the headend";
    }
  }

  grouping TE-STATS-AUTOBACKUP-COUNTERS {
    description
      "TE Auto Backup Counter Types";
    leaf total-tunnels {
      type uint32;
      description
        "Total auto backup tunnels";
    }
    leaf next-hop-tunnels {
      type uint32;
      description
        "Next hop auto backup tunnels only";
    }
    leaf next-next-hop-tunnels {
      type uint32;
      description
        "Next next hop auto backup tunnels only";
    }
  }

  grouping TE-STATS-AUTOBACKUP {
    description
      "Counters for TE Autobackup";
    container created {
      description
        "Number of connected auto backup tunnels";
      uses TE-STATS-AUTOBACKUP-COUNTERS;
    }
    container connected {
      description
        "Number of connected auto backup tunnels";
      uses TE-STATS-AUTOBACKUP-COUNTERS;
    }
    container removed-down {
      description
        "Number of NNHOP auto backup tunnels removed
         while down";
      uses TE-STATS-AUTOBACKUP-COUNTERS;
    }
    container removed-unused {
      description
        "Number of auto backup tunnels removed while
         unused";
      uses TE-STATS-AUTOBACKUP-COUNTERS;
    }
    container removed-in-use {
      description
        "Number of auto backup tunnels removed while up
         and in use";
      uses TE-STATS-AUTOBACKUP-COUNTERS;
    }
    container removed-range-exceeded {
      description
        "Number of auto backup tunnel attempts rejected
         because the total number exceeds the range";
      uses TE-STATS-AUTOBACKUP-COUNTERS;
    }
    leaf last-cleared-time {
      type uint32;
      description
        "Timestamp when the stat has been cleared";
    }
  }

  grouping TE-STATS-AUTOMESH {
    description
      "Counters for TE Automesh";
    leaf created {
      type uint32;
      description
        "Number of connected automesh tunnels";
    }
    leaf connected {
      type uint32;
      description
        "Number of connected automesh tunnels";
    }
    leaf removed-unused {
      type uint32;
      description
        "Number of automesh tunnels removed while unused";
    }
    leaf removed-in-use {
      type uint32;
      description
        "Number of automesh tunnels removed while up and
         in use";
    }
    leaf removed-range-exceeded {
      type uint32;
      description
        "Number of automesh tunnel attempts rejected
         because the total number exceeds the range";
    }
    leaf last-cleared-time {
      type uint32;
      units "second";
      description
        "Time at which these were last cleared in seconds
         since (in seconds since 1st Jan 1970 00:00:00)'";
    }
  }
}
