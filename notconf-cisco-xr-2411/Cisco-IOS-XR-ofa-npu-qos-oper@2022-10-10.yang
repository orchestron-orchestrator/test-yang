module Cisco-IOS-XR-ofa-npu-qos-oper {
  namespace "http://cisco.com/ns/yang/Cisco-IOS-XR-ofa-npu-qos-oper";
  prefix ofa-npu-qos-oper;

  import Cisco-IOS-XR-types {
    prefix xr;
  }
  import cisco-semver {
    prefix semver;
  }

  include Cisco-IOS-XR-ofa-npu-qos-oper-sub1 {
    revision-date 2022-10-10;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ofa-npu-qos package operational data.

     This module contains definitions
     for the following management objects:
       npu-qos: NPU QOS data

     Copyright (c) 2013-2022 by Cisco Systems, Inc.
     All rights reserved.";

  revision 2022-10-10 {
    semver:module-version "1.0.0";
    description
      "Create the initial npu-qos oper yang model.";
  }
  revision 2019-04-05 {
    description
      "Establish semantic version baseline.";
  }
  revision 2015-11-09 {
    description
      "IOS XR 6.0 revision.";
  }

  container npu-qos {
    config false;
    description
      "NPU QOS data";
    container nodes {
      description
        "NPU QOS data for available nodes";
      list node {
        key "node-name";
        description
          "NPU QOS operational data for a particular node";
        container npu-numbers {
          description
            "Punt interface type";
          list npu-number {
            key "npu-id";
            description
              "QOS data for a particular NPU";
            container display {
              description
                "NPU specific QOS data";
              uses OFA-NPU-QOS-SHOW-ST;
            }
            leaf npu-id {
              type uint32;
              description
                "Npu number";
            }
          }
        }
        leaf node-name {
          type xr:Node-id;
          description
            "Node ID";
        }
      }
    }
  }
}
