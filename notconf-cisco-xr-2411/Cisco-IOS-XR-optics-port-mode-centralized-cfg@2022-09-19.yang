module Cisco-IOS-XR-optics-port-mode-centralized-cfg {
  namespace "http://cisco.com/ns/yang/Cisco-IOS-XR-optics-port-mode-centralized-cfg";
  prefix optics-port-mode-centralized-cfg;

  import Cisco-IOS-XR-types {
    prefix xr;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR optics-port-mode-centralized package configuration.

     This module contains definitions
     for the following management objects:
       port-mode-configs: none

     Copyright (c) 2013-2022 by Cisco Systems, Inc.
     All rights reserved.";

  revision 2022-09-19 {
    semver:module-version "1.0.0";
    description
      "Initial Revision";
  }
  revision 2019-04-05 {
    description
      "Establish semantic version baseline.";
  }
  revision 2015-11-09 {
    description
      "IOS XR 6.0 revision.";
  }

  container port-mode-configs {
    description
      "none";
    container locations {
      description
        "Configure port mode.";
      list location {
        key "nodeid";
        description
          "Node Id of portmode configuration";
        leaf nodeid {
          type xr:Node-id;
          description
            "Specify location";
        }
        list port-range {
          key "first-port sec-port";
          description
            "Hardware Module Portmode configuration";
          leaf first-port {
            type uint32;
            description
              "Specify first port number of port-range";
          }
          leaf sec-port {
            type uint32;
            description
              "Specify second port number of port-range";
          }
          list instance {
            key "inst-id";
            description
              "MPA number if a MPA supported card";
            container mode {
              description
                "Mode";
              leaf speed {
                type string;
                description
                  "speed 40-100, 400, 2x100, 4x10-4x25, 4x10,
                   4x25, 1x100, 2x100-PAM4, 3x100, 4x100";
              }
            }
            leaf inst-id {
              type uint32 {
                range "0..5";
              }
              description
                "Instance number";
            }
          }
        }
      }
    }
  }
}
