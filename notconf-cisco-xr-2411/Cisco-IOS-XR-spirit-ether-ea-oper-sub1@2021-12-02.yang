submodule Cisco-IOS-XR-spirit-ether-ea-oper-sub1 {
  belongs-to Cisco-IOS-XR-spirit-ether-ea-oper {
    prefix Cisco-IOS-XR-spirit-ether-ea-oper;
  }

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR spirit-ether-ea package operational data.

     Copyright (c) 2013-2021 by Cisco Systems, Inc.
     All rights reserved.";

  revision 2021-12-02 {
    semver:module-version "1.0.0";
    description
      "Added Stream Name.";
  }
  revision 2019-04-05 {
    description
      "Establish semantic version baseline.";
  }
  revision 2015-11-09 {
    description
      "IOS XR 6.0 revision.";
  }

  grouping VKG-ETHER-EA-SHOW-STATUS-ENTRY {
    description
      "PD Interface Database Status info";
    leaf intf-valid {
      type boolean;
      description
        "intf valid";
    }
    leaf num-nps {
      type uint8;
      description
        "num nps";
    }
    leaf channel-id {
      type uint8;
      description
        "channelId";
    }
    leaf admin-up {
      type uint8;
      description
        "admin up";
    }
    leaf if-state {
      type uint8;
      description
        "if state";
    }
    leaf pd-if-status {
      type uint32;
      description
        "pd if status";
    }
    leaf is-virtual {
      type uint8;
      description
        "is virtual";
    }
    leaf ifhandle {
      type uint32;
      description
        "ifhandle";
    }
    leaf parent-ifhandle {
      type uint32;
      description
        "parent ifhandle";
    }
    leaf np-map {
      type uint16;
      description
        "np map";
    }
    leaf np-map-pm {
      type uint16;
      description
        "np map pm";
    }
    leaf parent-np-map-pm {
      type uint16;
      description
        "parent np map pm";
    }
    leaf num-tcam-entries {
      type uint16;
      description
        "num tcam entries";
    }
    leaf tcam-warning-status {
      type boolean;
      description
        "tcam warning status";
    }
    leaf parent-np-map-mismatch-pm {
      type boolean;
      description
        "parent np map mismatch pm";
    }
    leaf np-map-mismatch-pm {
      type boolean;
      description
        "np map mismatch pm";
    }
    leaf pm-ifhandle-not-found {
      type boolean;
      description
        "pm ifhandle not found";
    }
    leaf uidb-state-mismatch {
      type boolean;
      description
        "uidb state mismatch";
    }
    leaf-list vlan-tcam-status {
      type uint32;
      description
        "vkg eth pd status t";
    }
    leaf-list ingress-uidb-index {
      type uint16;
      max-elements 10;
      description
        "ingress uidb index";
    }
    leaf-list egress-uidb-index {
      type uint16;
      max-elements 10;
      description
        "egress uidb index";
    }
  }
}
