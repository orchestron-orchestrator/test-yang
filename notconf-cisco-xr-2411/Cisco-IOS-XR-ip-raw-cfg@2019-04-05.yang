module Cisco-IOS-XR-ip-raw-cfg {
  namespace "http://cisco.com/ns/yang/Cisco-IOS-XR-ip-raw-cfg";
  prefix ip-raw-cfg;

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ip-raw package configuration.

     This module contains definitions
     for the following management objects:
       ip-raw: Global IP RAW configuration

     Copyright (c) 2013-2019 by Cisco Systems, Inc.
     All rights reserved.";

  revision 2019-04-05 {
    semver:module-version "1.0.1";
    description
      "Establish semantic version baseline.";
  }
  revision 2015-11-09 {
    description
      "IOS XR 6.0 revision.";
  }

  container ip-raw {
    description
      "Global IP RAW configuration";
    container num-thread {
      presence "Indicates a num-thread node is configured.";
      description
        "RAW InQueue and OutQueue threads";
      leaf raw-in-q-threads {
        type uint32 {
          range "1..16";
        }
        mandatory true;
        description
          "InQ Threads";
      }
      leaf raw-out-q-threads {
        type uint32 {
          range "1..16";
        }
        mandatory true;
        description
          "OutQ Threads";
      }
    }
    container directory {
      presence "Indicates a directory node is configured.";
      description
        "RAW directory details";
      leaf directoryname {
        type string;
        mandatory true;
        description
          "Directory name";
      }
      leaf max-raw-debug-files {
        type uint32 {
          range "1..18000";
        }
        default "256";
        description
          "Set number of Debug files";
      }
      leaf max-file-size-files {
        type uint32 {
          range "1024..4294967295";
        }
        units "byte";
        description
          "Set size of debug files in bytes";
      }
    }
    leaf receive-q {
      type uint32 {
        range "40..800";
      }
      description
        "RAW receive Queue Size";
    }
  }
}
