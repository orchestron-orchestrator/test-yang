module Cisco-IOS-XR-ip-rib-gribi-oper {
  namespace "http://cisco.com/ns/yang/Cisco-IOS-XR-ip-rib-gribi-oper";
  prefix ip-rib-gribi-oper;

  import Cisco-IOS-XR-types {
    prefix xr;
  }
  import cisco-semver {
    prefix semver;
  }

  include Cisco-IOS-XR-ip-rib-gribi-oper-sub1 {
    revision-date 2022-12-13;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ip-rib-gribi package operational data.

     This module contains definitions
     for the following management objects:
       gribi: RIB operational data
       gribi-stdby: RIB standby node IPv6 operational data

     Copyright (c) 2013-2022 by Cisco Systems, Inc.
     All rights reserved.";

  revision 2022-12-13 {
    semver:module-version "1.0.0";
    description
      "Modify RIB opaque redist history";
  }
  revision 2022-05-11 {
    description
      "has-aft added to route";
  }
  revision 2022-04-29 {
    description
      "Add AFT NHG info";
  }
  revision 2022-03-02 {
    description
      "Add AFT info";
  }
  revision 2019-04-05 {
    description
      "Establish semantic version baseline.";
  }
  revision 2015-11-09 {
    description
      "IOS XR 6.0 revision.";
  }

  grouping VRF-TABLE {
    description
      "Common node of gribi, gribi-stdby";
    container vrfs {
      description
        "VRF table";
      list vrf {
        key "vrf-name";
        description
          "Specific VRF";
        container aft {
          description
            "Abstract Forwarding Table";
          container aft-next-hops {
            description
              "Next Hops";
            list aft-next-hop {
              key "aft-id";
              description
                "Next Hop AFT with ID in hex";
              leaf aft-id {
                type xr:Cisco-ios-xr-string;
                description
                  "AFT ID";
              }
              uses IPV6-RIB-EDM-OPAQUE-OBJ;
            }
          }
          container aft-next-hop-groups {
            description
              "Next Hops Groups";
            list aft-next-hop-group {
              key "aft-id";
              description
                "Next Hop Group AFT with ID in hex";
              leaf aft-id {
                type xr:Cisco-ios-xr-string;
                description
                  "AFT ID";
              }
              uses IPV6-RIB-EDM-ROUTE;
            }
          }
        }
        leaf vrf-name {
          type string;
          description
            "Name of the VRF";
        }
      }
    }
  }

  container gribi {
    config false;
    description
      "RIB operational data";
    uses VRF-TABLE;
  }
  container gribi-stdby {
    config false;
    description
      "RIB standby node IPv6 operational data";
    uses VRF-TABLE;
  }
}
