module Cisco-IOS-XR-tunnel-l2tun-cfg {
  namespace "http://cisco.com/ns/yang/Cisco-IOS-XR-tunnel-l2tun-cfg";
  prefix tunnel-l2tun-cfg;

  import Cisco-IOS-XR-types {
    prefix xr;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR tunnel-l2tun package configuration.

     This module contains definitions
     for the following management objects:
       l2tp: L2TPv3 class used for L2VPNs

     Copyright (c) 2013-2019 by Cisco Systems, Inc.
     All rights reserved.";

  revision 2019-04-05 {
    semver:module-version "1.0.0";
    description
      "Establish semantic version baseline.";
  }
  revision 2017-09-07 {
    description
      "Fixed type translation error.";
  }
  revision 2015-11-09 {
    description
      "IOS XR 6.0 revision.";
  }

  typedef L2tp-no-user {
    type uint32 {
      range "0..4294967295";
    }
    description
      "L2tp no user";
  }

  typedef L2tp-hash-method {
    type enumeration {
      enum "md5" {
        value 1;
        description
          "MD5";
      }
      enum "sha1" {
        value 2;
        description
          "SHA1";
      }
      enum "none" {
        value 3;
        description
          "None";
      }
    }
    description
      "L2tp hash method";
  }

  typedef L2tp-digest-hash-method {
    type enumeration {
      enum "md5" {
        value 1;
        description
          "MD5";
      }
      enum "sha1" {
        value 2;
        description
          "SHA1";
      }
    }
    description
      "L2tp digest hash method";
  }

  grouping TIMEOUT {
    description
      "Common node of initial, retransmit";
    container timeout {
      description
        "Set timeout value range";
      leaf minimum {
        type uint32 {
          range "1..8";
        }
        description
          "Specify minimum timeout";
      }
      leaf maximum {
        type uint32 {
          range "1..8";
        }
        description
          "Specify maximum timeout";
      }
    }
  }

  container l2tp {
    description
      "L2TPv3 class used for L2VPNs";
    container classes {
      description
        "List of classes";
      list class {
        key "class-name";
        description
          "Configuration for a specific class";
        container security {
          description
            "Security check";
          container ip {
            description
              "Security check for IP";
            leaf address-check {
              type empty;
              description
                "Enable IP address check for L2TP packets";
            }
          }
        }
        container retransmit {
          description
            "Control message retransmission parameters";
          container initial {
            description
              "Set retries and timeouts for initial";
            leaf retry {
              type uint32 {
                range "1..1000";
              }
              description
                "Specify the retry number";
            }
            uses TIMEOUT;
          }
          leaf retry {
            type uint32 {
              range "5..1000";
            }
            description
              "Specify retransmit retry count";
          }
          uses TIMEOUT;
        }
        container tunnel {
          description
            "l2TP tunnel";
          leaf accounting {
            type string;
            description
              "Tunnel accounting";
          }
        }
        container digest {
          description
            "Message digest authentication for the L2TP
             control connection";
          container secrets {
            description
              "Set shared secret for message digest";
            list secret {
              key "secret-name";
              description
                "The encrypted user secret and hash method";
              leaf secret-name {
                type xr:Cisco-ios-xr-string;
                description
                  "Specify the encrypted user secret";
              }
              leaf hash {
                type L2tp-hash-method;
                mandatory true;
                description
                  "Specify hash method";
              }
            }
          }
          leaf hash {
            type L2tp-digest-hash-method;
            description
              "Specify hash method";
          }
          leaf check-disable {
            type empty;
            description
              "Disable digest checking";
          }
        }
        container ip {
          description
            "IP TOS value";
          leaf tos {
            type uint32 {
              range "0..255";
            }
            description
              "IP TOS value (decimal)";
          }
        }
        leaf host-name {
          type string;
          description
            "Local hostname for control connection
             authentication";
        }
        leaf hidden {
          type empty;
          description
            "Specify to hide AVPs in outgoing control
             messages";
        }
        leaf hello-interval {
          type uint32 {
            range "0..1000";
          }
          units "second";
          description
            "Specify interval (in seconds)";
        }
        leaf timeout-setup {
          type uint32 {
            range "60..6000";
          }
          units "second";
          description
            "Time permitted to set up a control connection";
        }
        leaf receive-window {
          type uint32 {
            range "1..16384";
          }
          units "byte";
          description
            "Receive window size for the control connection";
        }
        leaf congestion-control {
          type empty;
          description
            "Congestion control enabled";
        }
        leaf timeout-no-user {
          type L2tp-no-user;
          units "second";
          description
            "Timeout value for no-user in seconds";
        }
        leaf authentication {
          type uint32;
          description
            "Authenticate the L2TP control connection";
        }
        leaf enable {
          type empty;
          description
            "Enable L2TPv3 class used for L2VPNs";
        }
        leaf password {
          type xr:Proprietary-password;
          description
            "Specify the password for control channel
             authentication";
        }
        leaf class-name {
          type xr:Cisco-ios-xr-string {
            length "1..31";
          }
          description
            "Specify the class name. Regexp:
             ^[a-z0-9A-Z][-_.a-z0-9A-Z]*$";
        }
      }
    }
  }
}
