module Cisco-IOS-XR-sysadmin-wd-sysmon {
  namespace "http://www.cisco.com/ns/yang/Cisco-IOS-XR-sysadmin-wd-sysmon";
  prefix wd-sysmon;

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains definitions
     for the Calvados model objects.

     Copyright (c) 2012-2020 by Cisco Systems, Inc.
     All rights reserved.";

  revision 2019-04-15 {
    semver:module-version "1.1.0";
    description
      "Establish semantic version baseline.";
  }
  revision 2018-03-21 {
    description
      "IOS XR 6.5.1 revision.";
  }

  typedef percent {
    type int32 {
      range "0 .. 100";
    }
    description
      "Percentage";
  }

  container cpu {
    config false;
    description
      "CPU Utilization info";
    list all-locations {
      key "location";
      leaf location {
        type string;
      }
      container cpuutils {
        config false;
        description
          "CPU Util";
        list all-utils {
          key "resource";
          leaf resource {
            type string;
            description
              "CPU ";
          }
          leaf cpuutil1Min {
            type percent;
            description
              "cpu utilization for 1 min";
          }
          leaf cpuutil5Min {
            type percent;
            description
              "cpu utilization for 5 min";
          }
          leaf cpuutil15Min {
            type percent;
            description
              "cpu utilization for 15 min";
          }
        }
      }
      container processutils {
        config false;
        description
          "Per Process CPU Util";
        list all-utils {
          key "resource";
          leaf resource {
            type string;
            description
              "CPU ";
          }
          leaf cpuutil1Min {
            type percent;
            description
              "cpu utilization for 1 min";
          }
          leaf cpuutil5Min {
            type percent;
            description
              "cpu utilization for 5 min";
          }
          leaf cpuutil15Min {
            type percent;
            description
              "cpu utilization for 15 min";
          }
        }
        list all-processes {
          key "pid";
          leaf pid {
            type int32;
            description
              "PID ";
          }
          leaf p1Min {
            type percent;
            description
              "1 Min Cpu Utilization";
          }
          leaf p5Min {
            type percent;
            description
              "5 Min Cpu utilization";
          }
          leaf p15Min {
            type percent;
            description
              "15 Min Cpu Utilization";
          }
          leaf Process {
            type string;
            description
              "process name ";
          }
          leaf Timecreated {
            type int32;
            description
              "Timecreated ";
          }
          leaf AverageUsecs {
            type int32;
            description
              "AverageUsecs";
          }
          leaf MemAllocated {
            type int32;
            description
              "memory allocated";
          }
          leaf MemFreed {
            type int32;
            description
              "Mem free";
          }
          leaf Invoked {
            type int32;
            description
              "Invoked";
          }
          leaf Runtime {
            type int32;
            description
              "runtime";
          }
          leaf Priority {
            type int32;
            description
              "priority";
          }
          leaf TextSegSize {
            type int32;
            description
              "Text segment size";
          }
          leaf DataSegSize {
            type int32;
            description
              "Data segment size";
          }
          leaf StackSegSize {
            type int32;
            description
              "Stack Segment size";
          }
          leaf DynMemSize {
            type int32;
            description
              "Dynamic memory size";
          }
        }
      }
    }
  }
}
