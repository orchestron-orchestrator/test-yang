submodule Cisco-IOS-XR-mpls-oam-oper-sub1 {
  belongs-to Cisco-IOS-XR-mpls-oam-oper {
    prefix Cisco-IOS-XR-mpls-oam-oper;
  }

  import ietf-inet-types {
    prefix inet;
  }
  import Cisco-IOS-XR-types {
    prefix xr;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR mpls-oam package operational data.

     Copyright (c) 2013-2019 by Cisco Systems, Inc.
     All rights reserved.";

  revision 2019-04-05 {
    semver:module-version "1.0.1";
    description
      "Establish semantic version baseline.";
  }
  revision 2015-11-09 {
    description
      "IOS XR 6.0 revision.";
  }

  typedef Lspv-dpm-igp {
    type enumeration {
      enum "ospf" {
        description
          "OSPF";
      }
      enum "isis" {
        description
          "ISIS";
      }
    }
    description
      "Lspv dpm igp";
  }

  typedef Lspv-dpm-fault-code {
    type enumeration {
      enum "lspv-dpm-fault-na" {
        value 0;
        description
          "Unset Code";
      }
      enum "lspv-dpm-fault-success" {
        value 33;
        description
          "Success";
      }
      enum "lspv-dpm-fault-timeout" {
        value 46;
        description
          "Timeout";
      }
      enum "lspv-dpm-fault-unlbl-out-intf" {
        value 66;
        description
          "Unlabeled output interface";
      }
      enum "lspv-dpm-fault-ds-mismatch" {
        value 68;
        description
          "DS Map mismatch";
      }
      enum "lspv-dpm-fault-no-fec" {
        value 70;
        description
          "No FEC mapping";
      }
      enum "lspv-dpm-fault-unknown-up-idx" {
        value 73;
        description
          "Unknown upstream index";
      }
      enum "lspv-dpm-fault-lbl-out-intf" {
        value 76;
        description
          "Labeled output interface";
      }
      enum "lspv-dpm-fault-mal" {
        value 77;
        description
          "Malformed request";
      }
      enum "lspv-dpm-fault-no-rx-lbl" {
        value 78;
        description
          "No rx label";
      }
      enum "lspv-dpm-fault-no-rx-intf-lbl-prot" {
        value 80;
        description
          "No rx intf label prot";
      }
      enum "lspv-dpm-fault-un-sent" {
        value 81;
        description
          "Request not sent";
      }
      enum "lspv-dpm-fault-transit" {
        value 82;
        description
          "Transit router";
      }
      enum "lspv-dpm-fault-x" {
        value 88;
        description
          "Unknown return code";
      }
      enum "lspv-dpm-fault-dd-map" {
        value 100;
        description
          "DDMAP";
      }
      enum "lspv-dpm-fault-fec-mismatch" {
        value 102;
        description
          "FEC mismatch";
      }
      enum "lspv-dpm-fault-bad-tlv" {
        value 109;
        description
          "Unsupported TLV";
      }
      enum "lspv-dpm-fault-pre-lsp" {
        value 112;
        description
          "Premature termination of LSP";
      }
      enum "lspv-dpm-fault-rt-0t" {
        value 120;
        description
          "return code 0t";
      }
    }
    description
      "Lspv dpm fault code";
  }

  typedef Lspv-dpm-pfx-validation-status {
    type enumeration {
      enum "never" {
        description
          "Never";
      }
      enum "complete" {
        description
          "Complete";
      }
      enum "in-progress" {
        description
          "In Progress";
      }
      enum "scheduled" {
        description
          "Scheduled";
      }
      enum "stale" {
        description
          "Stale";
      }
      enum "no-upstreams" {
        description
          "No Upstreams";
      }
    }
    description
      "Lspv dpm pfx validation status";
  }

  typedef Static-ipv6-address {
    type inet:ipv6-address;
    description
      "Static ipv6 address";
  }

  typedef Lspv-dpm-addr {
    type enumeration {
      enum "ipv4" {
        description
          "IPv4";
      }
      enum "ipv6" {
        description
          "IPv6";
      }
    }
    description
      "Lspv dpm addr";
  }

  grouping LSPV-DPM-PFX-DB-SUMMARY {
    description
      "LSPV DPM Prefix DB summary";
    leaf pfx-db-size {
      type uint32;
      description
        "Size of Prefix DB";
    }
    leaf validated-prefixes {
      type uint32;
      description
        "Number of Validated Prefixes";
    }
    leaf requests-sent {
      type uint32;
      description
        "Number of Echo Requests Sent";
    }
    leaf requests-rcvd {
      type uint32;
      description
        "Number of Echo Requests Received";
    }
    leaf validation-errors {
      type uint32;
      description
        "Validation Errors";
    }
    leaf validation-start-time {
      type uint64;
      description
        "DPM Start Time";
    }
    leaf validation-end-time {
      type uint64;
      description
        "DPM End Time";
    }
  }

  grouping LSPV-DPM-ADJ-INFO {
    description
      "Adjacency Information";
    leaf local-label {
      type uint32;
      description
        "Label";
    }
    leaf flags {
      type uint32;
      description
        "Flags";
    }
    leaf protected {
      type boolean;
      description
        "Protected";
    }
    leaf static-adj {
      type boolean;
      description
        "Static Adj";
    }
    leaf group {
      type boolean;
      description
        "Group";
    }
    leaf isis-l1 {
      type boolean;
      description
        "ISIS Level 1";
    }
    leaf isis-l2 {
      type boolean;
      description
        "ISIS Level 2";
    }
    leaf success {
      type boolean;
      description
        "Sucess";
    }
  }

  grouping LSPV-DPM-ADJ {
    description
      "LSPV DPM Adjacency";
    container local-address {
      description
        "Local Address";
      uses LSPV-DPM-PREFIX-BAG;
    }
    container remote-address {
      description
        "Remote Address";
      uses LSPV-DPM-PREFIX-BAG;
    }
    leaf interface-name-xr {
      type string;
      description
        "Interface name";
    }
    leaf local-interface-id {
      type uint32;
      description
        "Local Interface Id";
    }
    leaf unprotected-local-label {
      type uint32;
      description
        "Unprotected Local Label";
    }
    leaf remote-interface-id {
      type uint32;
      description
        "Remote Interface Id";
    }
    leaf unprotected-remote-label {
      type uint32;
      description
        "Unprotected Remote Label";
    }
    leaf valid-adj {
      type uint32;
      description
        "Valid Adjacencies";
    }
    leaf total-adj {
      type uint32;
      description
        "Total Adjacencies";
    }
    leaf is-isis {
      type boolean;
      description
        "ISIS enabled";
    }
    leaf is-ipv4 {
      type boolean;
      description
        "IPv4 enabled";
    }
    leaf is-excluded {
      type boolean;
      description
        "Skipped for the current run";
    }
    leaf last-fault-time {
      type uint64;
      description
        "Last Fault Time";
    }
    list local-adj {
      description
        "Local Adjacencies";
      uses LSPV-DPM-ADJ-INFO;
    }
    list remote-adj {
      description
        "Remote Adjacencies";
      uses LSPV-DPM-ADJ-INFO;
    }
  }

  grouping LSPV-DPM-ADJ-FAULT {
    description
      "LSPV DPM ADJ fault";
    container ip {
      xr:event-telemetry "Subscribe Telemetry Event";
      description
        "IP Address";
      uses LSPV-DPM-PREFIX-BAG;
    }
    leaf interface-name-xr {
      type string;
      description
        "Interface name";
    }
    leaf igp {
      xr:event-telemetry "Subscribe Telemetry Event";
      type Lspv-dpm-igp;
      description
        "IGP";
    }
    leaf local-adj-sid {
      xr:event-telemetry "Subscribe Telemetry Event";
      type uint32;
      description
        "Local Adj SID";
    }
    leaf error-code {
      xr:event-telemetry "Subscribe Telemetry Event";
      type Lspv-dpm-fault-code;
      description
        "DPM Error code";
    }
  }

  grouping LSPV-DPM-SUMMARY {
    description
      "LSPV DPM summary";
    leaf v4rib-reg {
      xr:event-telemetry "Subscribe Telemetry Event";
      type boolean;
      description
        "Registration to IPv4 RIB";
    }
    leaf v4rib-con {
      xr:event-telemetry "Subscribe Telemetry Event";
      type boolean;
      description
        "Connection to IPv4 RIB";
    }
    leaf sysdb-reg {
      xr:event-telemetry "Subscribe Telemetry Event";
      type boolean;
      description
        "Registration to SYSDB";
    }
    leaf sysdb-con {
      xr:event-telemetry "Subscribe Telemetry Event";
      type boolean;
      description
        "Connection to SYSDB";
    }
    leaf im-reg {
      xr:event-telemetry "Subscribe Telemetry Event";
      type boolean;
      description
        "Registration to IM";
    }
    leaf im-con {
      xr:event-telemetry "Subscribe Telemetry Event";
      type boolean;
      description
        "Connection to IM";
    }
    leaf lspv-con {
      xr:event-telemetry "Subscribe Telemetry Event";
      type boolean;
      description
        "Connection to LSPV";
    }
    leaf num-of-adj {
      xr:event-telemetry "Subscribe Telemetry Event";
      type uint32;
      description
        "Number of Adjacencies in DB";
    }
    leaf validated-adjs {
      xr:event-telemetry "Subscribe Telemetry Event";
      type uint32;
      description
        "Number of Validated Adjacencies";
    }
    leaf dpm-eligible-intfs {
      type uint32;
      description
        "Number of DPM allowed interfaces";
    }
    leaf error-adjs {
      xr:event-telemetry "Subscribe Telemetry Event";
      type uint32;
      description
        "Errored Adjacencies";
    }
    leaf num-of-pfx {
      xr:event-telemetry "Subscribe Telemetry Event";
      type uint32;
      description
        "Number of Prefixes in DB";
    }
    leaf validated-pfxs {
      xr:event-telemetry "Subscribe Telemetry Event";
      type uint32;
      description
        "Number of Validated Prefixes";
    }
    leaf error-pfxs {
      xr:event-telemetry "Subscribe Telemetry Event";
      type uint32;
      description
        "Errored Prefixes";
    }
    leaf total-requests {
      xr:event-telemetry "Subscribe Telemetry Event";
      type uint32;
      description
        "Total Requests";
    }
    leaf total-responses {
      xr:event-telemetry "Subscribe Telemetry Event";
      type uint32;
      description
        "Total Responses";
    }
    leaf total-prop-req {
      type uint32;
      description
        "Total Property Requests";
    }
    leaf total-prop-errs {
      type uint32;
      description
        "Total Property Errors";
    }
    leaf total-prop-resp {
      type uint32;
      description
        "Total Property Responses";
    }
    leaf dpm-interval {
      xr:event-telemetry "Subscribe Telemetry Event";
      type uint32;
      description
        "DPM Run Interval";
    }
    leaf dpm-packets-per-second {
      xr:event-telemetry "Subscribe Telemetry Event";
      type uint32;
      units "packet/s";
      description
        "DPM Packets Per Second";
    }
    leaf total-retries {
      type uint32;
      description
        "Total Retries";
    }
    leaf validation-complete {
      xr:event-telemetry "Subscribe Telemetry Event";
      type boolean;
      description
        "DPM Validation Complete";
    }
    leaf last-dpm-run-time {
      xr:event-telemetry "Subscribe Telemetry Event";
      type uint64;
      description
        "Last DPM interation time in nanosec";
    }
    leaf last-dpm-fault-time {
      xr:event-telemetry "Subscribe Telemetry Event";
      type uint64;
      description
        "Last DPM fault time in nanosec";
    }
    leaf last-dpm-fault-time-ever {
      xr:event-telemetry "Subscribe Telemetry Event";
      type uint64;
      description
        "Last Ever DPM fault time in nanosec";
    }
  }

  grouping LSPV-DPM-FAULT {
    description
      "LSPV DPM Pfx NH fault";
    container prefix-xr {
      description
        "Prefix";
      uses LSPV-DPM-PREFIX-INFO;
    }
    container downlink-fault {
      xr:event-telemetry "Subscribe Telemetry Event";
      description
        "Downlink associated with the fault";
      uses LSPV-DPM-PREFIX-BAG;
    }
    container uplink-fault {
      xr:event-telemetry "Subscribe Telemetry Event";
      description
        "Uplink associated with the fault";
      uses LSPV-DPM-PREFIX-BAG;
    }
    leaf prefix-sid {
      type uint32;
      description
        "Prefix SID";
    }
    leaf error-code {
      xr:event-telemetry "Subscribe Telemetry Event";
      type Lspv-dpm-fault-code;
      description
        "DPM Error code";
    }
  }

  grouping LSPV-DPM-COUNTERS {
    description
      "LSPV DPM Counters";
    leaf requests-sent {
      type uint32;
      description
        "Requests Last Sent";
    }
    leaf requests-last-pending {
      type uint32;
      description
        "Requests Last Pending";
    }
    leaf requests-last-returned {
      type uint32;
      description
        "Requests Last Returned";
    }
    leaf requests-unsent {
      type uint32;
      description
        "Requests Unsent";
    }
    leaf requests-retry-unsent {
      type uint32;
      description
        "Requests Retry Unsent";
    }
    leaf requests-pending {
      type uint32;
      description
        "Requests Pending";
    }
  }

  grouping LSPV-DPM-PFX-ADJ {
    description
      "LSPV DPM Prefix Adj";
    container next-hop {
      description
        "NextHop";
      uses LSPV-DPM-PREFIX-BAG;
    }
    leaf requests-sent {
      type uint32;
      description
        "Requests Sent";
    }
    leaf errors {
      type uint32;
      description
        "Errors";
    }
    leaf last-fault-time {
      type uint64;
      description
        "Last Fault Time";
    }
    leaf status {
      type Lspv-dpm-pfx-validation-status;
      description
        "Status";
    }
    leaf stale {
      type boolean;
      description
        "Stale";
    }
  }

  grouping LSPV-DPM-PREFIX-BAG {
    description
      "LSPV DPM PREFIX BAG";
    leaf af-name {
      type Lspv-dpm-addr;
      description
        "AFName";
    }
    leaf ipv4-prefix {
      when "../af-name = 'ipv4'" {
        description
          "../AFName = 'IPv4'";
      }
      type inet:ipv4-address;
      description
        "IPv4 prefix";
    }
    leaf ipv6-prefix {
      when "../af-name = 'ipv6'" {
        description
          "../AFName = 'IPv6'";
      }
      type Static-ipv6-address;
      description
        "IPv6 prefix";
    }
  }

  grouping LSPV-DPM-PREFIX-INFO {
    description
      "Prefix Information";
    container prefix {
      description
        "Prefix";
      uses LSPV-DPM-PREFIX-BAG;
    }
    leaf prefix-length {
      type uint8;
      description
        "Prefix length";
    }
  }

  grouping LSPV-DPM-PFX {
    description
      "LSPV DPM Prefix";
    container prefix-xr {
      xr:event-telemetry "Subscribe Telemetry Event";
      description
        "Prefix";
      uses LSPV-DPM-PREFIX-INFO;
    }
    leaf pfx-sid {
      xr:event-telemetry "Subscribe Telemetry Event";
      type uint32;
      description
        "Prefix SID";
    }
    leaf requests-sent {
      type uint32;
      description
        "Requests Sent";
    }
    leaf requests-rcvd {
      type uint32;
      description
        "Requests Rcvd";
    }
    leaf errors {
      type uint32;
      description
        "Errors";
    }
    leaf last-fault-time {
      type uint64;
      description
        "Last Fault Time";
    }
    leaf status {
      type Lspv-dpm-pfx-validation-status;
      description
        "Status";
    }
    list upstream-adj {
      description
        "Upstream Adjacency";
      uses LSPV-DPM-PREFIX-BAG;
    }
    list downstream-adj-info {
      description
        "Downstream Adjacency Info";
      uses LSPV-DPM-PFX-ADJ;
    }
  }

  grouping LSPV-DPM-ADJ-DB-SUMMARY {
    description
      "LSPV DPM Adjacency DB summary";
    leaf adj-db-size {
      type uint32;
      description
        "Size of Adjacency DB";
    }
    leaf dpm-eligible-intfs {
      type uint32;
      description
        "Number of DPM allowed interfaces";
    }
    leaf err-intfs {
      type uint32;
      description
        "Number of Interfaces with Errors";
    }
    leaf validation-start-time {
      type uint64;
      description
        "Validation Start Time";
    }
    leaf validation-end-time {
      type uint64;
      description
        "Validation End Time";
    }
  }
}
