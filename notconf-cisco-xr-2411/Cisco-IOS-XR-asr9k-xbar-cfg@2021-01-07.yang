module Cisco-IOS-XR-asr9k-xbar-cfg {
  namespace "http://cisco.com/ns/yang/Cisco-IOS-XR-asr9k-xbar-cfg";
  prefix asr9k-xbar-cfg;

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR asr9k-xbar package configuration.

     This module contains definitions
     for the following management objects:
       fabric-mgid-config: Configure Global Fabric Mgid Settings

     Copyright (c) 2013-2021 by Cisco Systems, Inc.
     All rights reserved.";

  revision 2021-01-07 {
    semver:module-version "1.0.0";
    description
      "IOS XR 7.3.1 revision.";
  }
  revision 2019-04-05 {
    description
      "Establish semantic version baseline.";
  }
  revision 2015-11-09 {
    description
      "IOS XR 6.0 revision.";
  }

  container fabric-mgid-config {
    description
      "Configure Global Fabric Mgid Settings";
    container mgid-mcast-scale {
      description
        "MGID mcast scale config";
      leaf enable {
        type boolean;
        description
          "enable MGID mcast scale";
      }
    }
  }
}
