submodule Cisco-IOS-XR-pppoe-ea-oper-sub1 {
  belongs-to Cisco-IOS-XR-pppoe-ea-oper {
    prefix Cisco-IOS-XR-pppoe-ea-oper;
  }

  import ietf-yang-types {
    prefix yang;
  }
  import Cisco-IOS-XR-types {
    prefix xr;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR pppoe-ea package operational data.

     Copyright (c) 2013-2023 by Cisco Systems, Inc.
     All rights reserved.";

  revision 2023-07-12 {
    semver:module-version "1.0.1";
    description
      "Added good description for model.";
  }
  revision 2019-04-05 {
    semver:module-version "1.0.1";
    description
      "Establish semantic version baseline.";
  }
  revision 2015-11-09 {
    description
      "IOS XR 6.0 revision.";
  }

  grouping PPPOE-EA-INTERFACE-INFO {
    description
      "PPPoE EA interface information";
    container peer-mac {
      description
        "Peer Mac-address";
      uses ETHER-MACADDR-TYPE;
    }
    container local-mac {
      description
        "Local Mac-address";
      uses ETHER-MACADDR-TYPE;
    }
    container srgv-mac {
      description
        "SRG VMac-address";
      uses ETHER-MACADDR-TYPE;
    }
    leaf interface {
      type xr:Interface-name;
      description
        "Subscriber interface";
    }
    leaf session-id {
      type uint16;
      description
        "Session ID";
    }
    leaf parent-interface {
      type xr:Interface-name;
      description
        "Parent interface";
    }
    leaf is-priority-set {
      type boolean;
      description
        "Is Priority Set";
    }
    leaf priority {
      type uint8;
      description
        "Interface priority status";
    }
    leaf is-in-sync {
      type boolean;
      description
        "Interface recreate status";
    }
    leaf is-platform-created {
      type boolean;
      description
        "platform parent interface create status";
    }
    leaf-list vlanid {
      type uint16;
      max-elements 2;
      description
        "VLAN Ids";
    }
  }

  grouping ETHER-MACADDR-TYPE {
    description
      "ETHER MACADDR TYPE";
    leaf macaddr {
      type yang:hex-string;
      description
        "macaddr";
    }
  }

  grouping PPPOE-EA-PARENT-INTERFACE-INFO {
    description
      "PPPoE EA parent interface information";
    container srgv-mac {
      description
        "SRG VMac-address";
      uses ETHER-MACADDR-TYPE;
    }
    leaf interface {
      type xr:Interface-name;
      description
        "Parent interface";
    }
    leaf is-in-sync {
      type boolean;
      description
        "Interface recreate status";
    }
  }
}
