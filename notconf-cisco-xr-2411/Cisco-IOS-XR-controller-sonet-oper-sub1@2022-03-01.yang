submodule Cisco-IOS-XR-controller-sonet-oper-sub1 {
  belongs-to Cisco-IOS-XR-controller-sonet-oper {
    prefix Cisco-IOS-XR-controller-sonet-oper;
  }

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR controller-sonet package operational data.

     Copyright (c) 2013-2022 by Cisco Systems, Inc.
     All rights reserved.";

  revision 2022-03-01 {
    semver:module-version "1.0.0";
    description
      "Added LED state field to port common info";
  }
  revision 2022-02-15 {
    description
      "64 byte trace mode added to j0_info";
  }
  revision 2019-04-05 {
    description
      "Establish semantic version baseline.";
  }
  revision 2015-11-09 {
    description
      "IOS XR 6.0 revision.";
  }

  typedef Sonet-prbs-err-inject {
    type enumeration {
      enum "none" {
        description
          "None";
      }
      enum "single" {
        description
          "Single";
      }
      enum "continuous" {
        description
          "Continuous";
      }
    }
    description
      "Sonet prbs err inject";
  }

  typedef Sonet-prbs-dir {
    type enumeration {
      enum "none" {
        description
          "None";
      }
      enum "line" {
        description
          "Line";
      }
      enum "system" {
        description
          "System";
      }
    }
    description
      "Sonet prbs dir";
  }

  typedef Sonet-prbs-framing {
    type enumeration {
      enum "none" {
        description
          "None";
      }
      enum "framed" {
        description
          "Framed";
      }
      enum "unframed" {
        description
          "Unframed";
      }
    }
    description
      "Sonet prbs framing";
  }

  typedef Sonet-prbs-status {
    type enumeration {
      enum "prbs-not-running" {
        value 0;
        description
          "Not Running";
      }
      enum "prbs-locked" {
        value 1;
        description
          "Locked";
      }
      enum "prbs-unlocked" {
        value 2;
        description
          "Unlocked";
      }
      enum "prbs-not-available" {
        value 3;
        description
          "Not Applicable";
      }
    }
    description
      "Sonet prbs status";
  }

  typedef Sonet-prbs-pattern {
    type enumeration {
      enum "none" {
        value 0;
        description
          "None";
      }
      enum "pn31" {
        value 1;
        description
          "PN31";
      }
      enum "pn23" {
        value 2;
        description
          "PN23";
      }
      enum "pn15" {
        value 3;
        description
          "PN15";
      }
      enum "pn11" {
        value 4;
        description
          "PN11";
      }
      enum "pn9" {
        value 5;
        description
          "PN9";
      }
      enum "pn7" {
        value 6;
        description
          "PN7";
      }
      enum "user-defined" {
        value 7;
        description
          "User Defined Pattern";
      }
    }
    description
      "Sonet prbs pattern";
  }

  typedef Sonet-prbs-mode {
    type enumeration {
      enum "none" {
        value 0;
        description
          "None";
      }
      enum "source" {
        value 1;
        description
          "Source";
      }
      enum "sink" {
        value 2;
        description
          "Sink";
      }
      enum "source-sink" {
        value 3;
        description
          "Source Sink";
      }
    }
    description
      "Sonet prbs mode";
  }

  typedef Ains-state-et {
    type enumeration {
      enum "none" {
        value 0;
        description
          "None";
      }
      enum "active-running" {
        value 1;
        description
          "Running";
      }
      enum "active-pending" {
        value 2;
        description
          "Pending";
      }
    }
    description
      "Ains state et";
  }

  typedef Tx-clock-info {
    type enumeration {
      enum "clock-src-internal" {
        description
          "clock src internal";
      }
      enum "clock-src-line" {
        description
          "clock src line";
      }
      enum "clock-recovered-dcr" {
        description
          "Differential Clock Recovery (DCR)";
      }
      enum "clock-none" {
        description
          "clock none";
      }
    }
    description
      "Tx clock info";
  }

  typedef Framing-info {
    type enumeration {
      enum "framing-sonet-ma" {
        description
          "framing sonet ma";
      }
      enum "framing-sdh-ma" {
        description
          "framing sdh ma";
      }
    }
    description
      "Framing info";
  }

  typedef Loopback-info {
    type enumeration {
      enum "none" {
        description
          "No loopback";
      }
      enum "internal" {
        description
          "Internal loopback";
      }
      enum "external" {
        description
          "External loopback";
      }
      enum "invalid" {
        description
          "Invalid loopback";
      }
    }
    description
      "loopback info";
  }

  typedef Trace-mode-enum {
    type enumeration {
      enum "trace-invalid" {
        value 0;
        description
          "Trace mode invalid";
      }
      enum "trace-byte" {
        value 1;
        description
          "Trace mode 1 byte";
      }
      enum "trace-16" {
        value 2;
        description
          "Trace mode is 16";
      }
      enum "trace-64" {
        value 3;
        description
          "Trace mode is 64";
      }
    }
    description
      "Trace mode Enum";
  }

  typedef Sonet-led-state {
    type enumeration {
      enum "off" {
        value 0;
        description
          "Off";
      }
      enum "green-on" {
        value 1;
        description
          "Green On";
      }
      enum "green-flashing" {
        value 2;
        description
          "Green Flashing";
      }
      enum "yellow-on" {
        value 3;
        description
          "Yellow On";
      }
      enum "yellow-flashing" {
        value 4;
        description
          "Yellow Flashing";
      }
      enum "red-on" {
        value 5;
        description
          "Red On";
      }
      enum "red-flashing" {
        value 6;
        description
          "Red Flashing";
      }
      enum "not-applicable" {
        value 7;
        description
          "Not Applicable";
      }
    }
    description
      "Sonet led state";
  }

  typedef Sonet-sec-state {
    type enumeration {
      enum "normal" {
        value 0;
        description
          "Normal";
      }
      enum "maintenance" {
        value 1;
        description
          "Maintenance";
      }
      enum "ains" {
        value 2;
        description
          "Automatic In Service";
      }
    }
    description
      "Sonet sec state";
  }

  typedef Sonet-ma-derived-admin-state {
    type enumeration {
      enum "in-service" {
        description
          "In Service";
      }
      enum "out-of-service" {
        description
          "Out of Service";
      }
      enum "maintenance" {
        description
          "Maintenance";
      }
      enum "ains" {
        description
          "Automatic In Service";
      }
    }
    description
      "Sonet ma derived admin state";
  }

  typedef Sonet-state-et {
    type enumeration {
      enum "not-ready" {
        value 0;
        description
          "Not Ready";
      }
      enum "admin-down" {
        value 1;
        description
          "Admin Down";
      }
      enum "down" {
        value 2;
        description
          "Down";
      }
      enum "up" {
        value 3;
        description
          "Up";
      }
      enum "shutdown" {
        value 4;
        description
          "Shutdown";
      }
      enum "error-disable" {
        value 5;
        description
          "Error Disable";
      }
      enum "down-immediate" {
        value 6;
        description
          "Down Immediate";
      }
      enum "down-immediate-admin" {
        value 7;
        description
          "Down Immediate Admin";
      }
      enum "down-graceful" {
        value 8;
        description
          "Down Graceful";
      }
      enum "begin-shutdown" {
        value 9;
        description
          "Begin Shutdown";
      }
      enum "end-shutdown" {
        value 10;
        description
          "End Shutdown";
      }
      enum "begin-error-disable" {
        value 11;
        description
          "Begin Error Disable";
      }
      enum "end-error-disable" {
        value 12;
        description
          "End Error Disable";
      }
      enum "begin-down-graceful" {
        value 13;
        description
          "Begin Down Graceful";
      }
      enum "reset" {
        value 14;
        description
          "Reset";
      }
      enum "operational" {
        value 15;
        description
          "Operational";
      }
      enum "not-operational" {
        value 16;
        description
          "Not Operational";
      }
      enum "unknown" {
        value 17;
        description
          "Unknown";
      }
      enum "last" {
        value 18;
        description
          "Last";
      }
    }
    description
      "Sonet state et";
  }

  grouping SONET-MA-PORT-INFO {
    description
      "SONET MA port operational info";
    container common-info {
      description
        "Port's common info";
      uses PORT-COMMON-INFO;
    }
    container section {
      description
        "Section info";
      uses SECTION-INFO;
    }
    container line {
      description
        "Line info";
      uses LINE-INFO;
    }
    container ains-info {
      description
        "AINS information";
      uses AINS-HW-INFO;
    }
    container prbs-info {
      description
        "PRBS information";
      uses SONET-PRBS-INFO;
    }
  }

  grouping SONET-PRBS-INFO {
    description
      "PRBS";
    leaf mode {
      type Sonet-prbs-mode;
      description
        "PRBS mode";
    }
    leaf pattern {
      type Sonet-prbs-pattern;
      description
        "PRBS pattern";
    }
    leaf status {
      type Sonet-prbs-status;
      description
        "PRBS status";
    }
    leaf framing {
      type Sonet-prbs-framing;
      description
        "PRBS framing";
    }
    leaf direction {
      type Sonet-prbs-dir;
      description
        "PRBS direction";
    }
    leaf err-inject {
      type Sonet-prbs-err-inject;
      description
        "PRBS error injection";
    }
    leaf user-pattern {
      type uint64;
      description
        "PRBS user pattern configured";
    }
  }

  grouping AINS-HW-INFO {
    description
      "AINS information";
    leaf ains-state {
      type Ains-state-et;
      description
        "AINS State";
    }
    leaf ains-timer-minutes {
      type uint32;
      units "minute";
      description
        "AINS TImer in Minutes";
    }
    leaf ains-remaining-secs {
      type uint32;
      units "second";
      description
        "AINS Remaining Seconds";
    }
  }

  grouping LINE-INFO {
    description
      "SONET Line operational info";
    container ais {
      description
        "AIS info";
      uses ALARM-INFO;
    }
    container rdi {
      description
        "RDI info";
      uses ALARM-INFO;
    }
    container bip {
      description
        "BIP (B2) BER info";
      uses BER-INFO;
    }
    container febe {
      description
        "FEBE info";
      uses BER-INFO;
    }
    container signal-degraded {
      description
        "BIP (B2) Signal Degraded info";
      uses BER-INFO;
    }
    container signal-failed {
      description
        "BIP (B2) Signal Failed info";
      uses BER-INFO;
    }
  }

  grouping EXTENDED-LOOPBACK-TYPE {
    description
      "EXTENDED LOOPBACK TYPE";
    leaf level {
      type uint32;
      description
        "Level";
    }
    leaf loopback {
      type Loopback-info;
      description
        "Port operational loopback";
    }
  }

  grouping J0-INFO {
    description
      "J0 overhead byte info";
    leaf mode {
      type Trace-mode-enum;
      description
        "Overhead Mode";
    }
    leaf trace-buffer {
      type string {
        length "0..64";
      }
      description
        "Trace info";
    }
  }

  grouping BER-INFO {
    description
      "error block info";
    leaf is-masked {
      type boolean;
      description
        "Are errors masked?";
    }
    leaf is-asserted {
      type boolean;
      description
        "Is threshold crossed?";
    }
    leaf threshold {
      type uint8;
      description
        "Error threshold power";
    }
    leaf count {
      type uint64;
      description
        "Error counter";
    }
  }

  grouping ALARM-INFO {
    description
      "defect/alarm info";
    leaf is-masked {
      type boolean;
      description
        "Is defect masked?";
    }
    leaf is-detected {
      type boolean;
      description
        "Is defect detected?";
    }
    leaf count {
      type uint64;
      description
        "Alarm counter";
    }
  }

  grouping SECTION-INFO {
    description
      "SONET Section operational info";
    container los {
      description
        "LOS info";
      uses ALARM-INFO;
    }
    container lof {
      description
        "LOF info";
      uses ALARM-INFO;
    }
    container tim {
      description
        "TIM info";
      uses ALARM-INFO;
    }
    container bip {
      description
        "BIP (B1) BER info";
      uses BER-INFO;
    }
    container j0-transmit {
      description
        "J0 Transmit";
      uses J0-INFO;
    }
    container j0-receive {
      description
        "J0 Receive";
      uses J0-INFO;
    }
    container j0-expected {
      description
        "J0 Expected";
      uses J0-INFO;
    }
    leaf loopback {
      type Loopback-info;
      description
        "Loopback info";
    }
    leaf framing {
      type Framing-info;
      description
        "Framing type";
    }
    leaf clock-source {
      type Tx-clock-info;
      description
        "Actual Transmit clock source";
    }
    leaf clock-source-cfg {
      type Tx-clock-info;
      description
        "Configured Transmit clock source";
    }
    list extended-loopback {
      description
        "Extended Loopback info";
      uses EXTENDED-LOOPBACK-TYPE;
    }
  }

  grouping PORT-COMMON-INFO {
    description
      "SONET port common info";
    leaf operational-state {
      type Sonet-state-et;
      description
        "Port's IM state";
    }
    leaf derived-state {
      type Sonet-ma-derived-admin-state;
      description
        "Derived State";
    }
    leaf config-sec-state {
      type Sonet-sec-state;
      description
        "Configured Sec Admin State";
    }
    leaf inherited-sec-state {
      type Sonet-sec-state;
      description
        "Inherited Sec Admin State";
    }
    leaf data-rate {
      type uint32;
      description
        "Data rate";
    }
    leaf last-clear-time {
      type uint32;
      description
        "Time Duration Since Last Clear";
    }
    leaf pm {
      type boolean;
      description
        "PM enable/Disable";
    }
    leaf led-state {
      type Sonet-led-state;
      description
        "Current State of LED of Controller";
    }
  }

  grouping SDH-PORT-INFO {
    description
      "SDH port operational info";
    container common-info {
      description
        "Port's common info";
      uses PORT-COMMON-INFO;
    }
    container regenerator-section {
      description
        "Regenerator Section info";
      uses SECTION-INFO;
    }
    container multiplex-section {
      description
        "Multiplex Section info";
      uses LINE-INFO;
    }
    container ains-info {
      description
        "AINS information";
      uses AINS-HW-INFO;
    }
    container prbs-info {
      description
        "PRBS information";
      uses SONET-PRBS-INFO;
    }
  }
}
