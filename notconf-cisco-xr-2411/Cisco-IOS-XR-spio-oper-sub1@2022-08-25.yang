submodule Cisco-IOS-XR-spio-oper-sub1 {
  belongs-to Cisco-IOS-XR-spio-oper {
    prefix Cisco-IOS-XR-spio-oper;
  }

  import Cisco-IOS-XR-types {
    prefix xr;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR spio package operational data.

     Copyright (c) 2013-2022 by Cisco Systems, Inc.
     All rights reserved.";

  revision 2022-08-25 {
    semver:module-version "1.0.0";
    description
      "Introduced yang support for spio";
  }
  revision 2019-04-05 {
    description
      "Establish semantic version baseline.";
  }
  revision 2015-11-09 {
    description
      "IOS XR 6.0 revision.";
  }

  typedef Spio-offload-platform {
    type enumeration {
      enum "software" {
        description
          "Software offload process";
      }
      enum "hardware" {
        description
          "Hardware offload";
      }
    }
    description
      "SPIO Offload Platform";
  }

  typedef Spio-direction {
    type enumeration {
      enum "detached" {
        description
          "None";
      }
      enum "receive" {
        description
          "Receive";
      }
      enum "transmit" {
        description
          "Transmit";
      }
      enum "both" {
        description
          "Receive and Transmit";
      }
    }
    description
      "SPIO Attach direction";
  }

  typedef Spio-protocol-id1 {
    type enumeration {
      enum "none" {
        description
          "No protocol";
      }
      enum "cfm" {
        description
          "CFM";
      }
      enum "stp" {
        description
          "STP";
      }
      enum "stp-pb" {
        description
          "STP (Provider Bridge)";
      }
      enum "ppp" {
        description
          "PPP";
      }
      enum "pppoe" {
        description
          "PPPoE";
      }
      enum "debug-trace" {
        description
          "ucode Debug/Trace";
      }
      enum "stats" {
        description
          "Statistics";
      }
      enum "afmon-upd" {
        description
          "AFMON Update";
      }
      enum "afmon-add" {
        description
          "AFMON Add";
      }
      enum "mofrr" {
        description
          "MOFRR";
      }
      enum "ip-sub" {
        description
          "IP Subscriber";
      }
      enum "ether-oam" {
        description
          "Ethernet Link OAM";
      }
      enum "lacp" {
        description
          "LACP";
      }
      enum "sync-e" {
        description
          "Synchronous Ethernet";
      }
      enum "chdlc" {
        description
          "Cisco HDLC";
      }
      enum "spa-ipc" {
        description
          "SPA IPC Messaging";
      }
      enum "net-flow" {
        description
          "Netflow";
      }
      enum "mvrp" {
        description
          "Multiple VLAN Registration";
      }
      enum "mvrp-pb" {
        description
          "MVRP (Provider Bridge)";
      }
      enum "ptp-eth" {
        description
          "Precision Time Protocol (Ethernet)";
      }
      enum "ptpipv4" {
        description
          "Precision Time Protocol (IPv4)";
      }
      enum "ptpipv6" {
        description
          "Precision Time Protocol (IPv6)";
      }
      enum "efpsec-notify" {
        description
          "EFP Security Notify";
      }
      enum "cluster-lmp" {
        description
          "Cluster Data Link Protocol";
      }
      enum "cluster-tst" {
        description
          "Cluster Data Link Test Client";
      }
      enum "cluster-dsc" {
        description
          "Cluster DSC Data Link Client";
      }
      enum "efpsec-notify-shut" {
        description
          "EFP Security Notify Shut";
      }
      enum "arp" {
        description
          "ARP";
      }
      enum "l2tpv2" {
        description
          "L2TPv2";
      }
      enum "lldp" {
        description
          "Link Layer Discovery";
      }
      enum "oam" {
        description
          "ATM OAM";
      }
      enum "pvst" {
        description
          "PVST";
      }
      enum "httpr" {
        description
          "HTTPR";
      }
      enum "sdac-discovery" {
        description
          "SDAC Discovery";
      }
      enum "erp" {
        description
          "Ethernet Ring Protection";
      }
      enum "udld" {
        description
          "UDLD";
      }
      enum "fhrp" {
        description
          "FHRP";
      }
      enum "unclassified" {
        description
          "Unclassified";
      }
      enum "httpripv6" {
        description
          "HTTPR IPV6";
      }
      enum "mac-cache-msg" {
        description
          "MAC Cache Msg";
      }
      enum "mirp-lite" {
        description
          "Multiple I-SID Registration Lite";
      }
      enum "pagent1" {
        description
          "PAGENT1";
      }
      enum "pagent2" {
        description
          "PAGENT2";
      }
      enum "mvrp-lite" {
        description
          "Multiple VLAN Registration Lite";
      }
      enum "cdp" {
        description
          "Cisco Discovery Protocol";
      }
      enum "dpss" {
        description
          "DPSS";
      }
      enum "mmrp" {
        description
          "Multiple MAC Registration";
      }
      enum "mka" {
        description
          "EAPoL Macsec MKA Control Pkt";
      }
      enum "an" {
        description
          "Autonomous Networks";
      }
      enum "exr" {
        description
          "Third Party Application";
      }
      enum "elmi" {
        description
          "Ethernet Local Management Interface";
      }
      enum "dot1x" {
        description
          "EAPoL Dot1x Control Pkt";
      }
      enum "pmdm" {
        description
          "Performance Measurement Protocol";
      }
      enum "pp-health" {
        description
          "Packet Path Health Monitoring Protocol";
      }
      enum "smart-sfp" {
        description
          "SMART SFP";
      }
      enum "ipv6-nd" {
        description
          "IPV6 ND";
      }
      enum "dot1x-mab" {
        description
          "EAPoL Dot1x MAB";
      }
      enum "pmdmoff" {
        description
          "Performance Measurement Protocol";
      }
      enum "p4rt" {
        description
          "P4RT";
      }
      enum "ztp" {
        description
          "ZTP Application";
      }
      enum "proto-max-count" {
        description
          "Max proto count";
      }
    }
    description
      "SPIO Protocol ID";
  }

  grouping SPIO-VI-INFO {
    description
      "SPIO VI information";
    leaf interface-name-xr {
      type xr:Interface-name;
      description
        "Interface name";
    }
    leaf vi-type {
      type uint32;
      description
        "VI type";
    }
    leaf intf-count {
      type uint32;
      description
        "Interface count";
    }
    leaf session-count {
      type uint32;
      description
        "Session count";
    }
    leaf primary-interface-name {
      type xr:Interface-name;
      description
        "Primary interface";
    }
    leaf backup-interface-name {
      type xr:Interface-name;
      description
        "Backup interface";
    }
    leaf flags {
      type uint32;
      description
        "Flags";
    }
    leaf primary-node-name {
      type xr:Node-id;
      description
        "Primary Node ID";
    }
    leaf backup-node-name {
      type xr:Node-id;
      description
        "Backup Node ID";
    }
  }

  grouping SPIO-SESSION-INFO {
    description
      "SPIO session information";
    leaf protocol-id {
      type Spio-protocol-id1;
      description
        "Protocol ID";
    }
    leaf node-name {
      type xr:Node-id;
      description
        "Node ID";
    }
    leaf interface-name {
      type xr:Interface-name;
      description
        "Interface name";
    }
    leaf platform {
      type Spio-offload-platform;
      description
        "Offload platform";
    }
    leaf key-xr {
      type string;
      description
        "Session key";
    }
    leaf data {
      type string;
      description
        "Opaque session data";
    }
    leaf last-update-id {
      type uint32;
      description
        "Last update ID";
    }
    leaf is-marked {
      type boolean;
      description
        "Mark/Sweep mark";
    }
    leaf present-in-interface-manager {
      type boolean;
      description
        "Whether session has been installed in Interface
         Manager";
    }
  }

  grouping SPIO-CLIENT-INFO {
    description
      "SPIO client information";
    leaf protocol-id-xr {
      type Spio-protocol-id1;
      description
        "Protocol ID";
    }
    leaf node-name-xr {
      type xr:Node-id;
      description
        "Node ID";
    }
    leaf interface-count {
      type uint32;
      description
        "Interface count";
    }
    leaf is-marked {
      type boolean;
      description
        "Mark/Sweep mark";
    }
  }

  grouping SPIO-INTERFACE-INFO {
    description
      "SPIO interface information";
    leaf protocol-id-xr {
      type Spio-protocol-id1;
      description
        "Protocol ID";
    }
    leaf node-name-xr {
      type xr:Node-id;
      description
        "Node ID";
    }
    leaf interface-name-xr {
      type xr:Interface-name;
      description
        "Interface name";
    }
    leaf attach-direction {
      type Spio-direction;
      description
        "Attach location";
    }
    leaf hardware-sessions {
      type uint32;
      description
        "Number of offload sessions running in hardware";
    }
    leaf software-sessions {
      type uint32;
      description
        "Number of offload sessions running in software";
    }
    leaf last-update-id {
      type uint32;
      description
        "Last update ID";
    }
    leaf is-marked {
      type boolean;
      description
        "Mark/Sweep mark";
    }
    leaf vi-handle {
      type xr:Interface-name;
      description
        "VI handle";
    }
  }
}
