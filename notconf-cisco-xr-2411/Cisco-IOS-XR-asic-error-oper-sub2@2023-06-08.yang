submodule Cisco-IOS-XR-asic-error-oper-sub2 {
  belongs-to Cisco-IOS-XR-asic-error-oper {
    prefix Cisco-IOS-XR-asic-error-oper;
  }

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR asic-error package operational data.

     Copyright (c) 2013-2023 by Cisco Systems, Inc.
     All rights reserved.";

  revision 2023-06-08 {
    semver:module-version "1.1.0";
    description
      "Datatype change from hex to string for Asic Information.";
  }
  revision 2021-02-10 {
    semver:module-version "1.1.0";
    description
      "Introduced working oper model for asic-errors.";
  }
  revision 2019-09-27 {
    semver:module-version "1.0.0";
    description
      "Introduced working oper model for asic-errors.";
  }
  revision 2019-09-24 {
    semver:module-version "1.0.0";
    description
      "Introduced working oper model for asic-errors.";
  }
  revision 2019-04-05 {
    description
      "Establish semantic version baseline.";
  }
  revision 2015-11-09 {
    description
      "IOS XR 6.0 revision.";
  }

  grouping GENERIC-ERROR-DATA-BG {
    description
      "GENERIC ERROR DATA BG";
    leaf at-time {
      type uint64;
      description
        "at time";
    }
    leaf at-time-nsec {
      type uint64;
      description
        "at time nsec";
    }
    leaf counter-val {
      type uint32;
      description
        "counter val";
    }
    leaf error-data {
      type string;
      description
        "error data";
    }
    leaf top-ec {
      type uint32;
      description
        "top ec";
    }
    leaf block-ec {
      type uint32;
      description
        "block ec";
    }
  }

  grouping GENERIC-NODE-BG {
    description
      "GENERIC NODE BG";
    leaf name {
      type string;
      description
        "Name assigned to mem";
    }
    leaf node-key {
      type uint32;
      description
        "32 bit key";
    }
    leaf alarm-on {
      type boolean;
      description
        "high threshold crossed";
    }
    leaf thresh-hi {
      type uint32;
      description
        "high threshold value";
    }
    leaf period-hi {
      type uint32;
      description
        "high period value";
    }
    leaf count {
      type uint32;
      description
        "Accumulated count";
    }
    leaf last-cleared {
      type uint64;
      description
        "Time  cleared";
    }
    list last-err {
      description
        " last Printable error information";
      uses GENERIC-ERROR-DATA-BG;
    }
  }

  grouping GENERIC-NODES-BG {
    description
      "GENERIC NODES BG";
    list error {
      description
        "Collection of errors";
      uses GENERIC-NODE-BG;
    }
  }

  grouping PARITY-DATA-BG {
    description
      "parity bit error";
    leaf at-time {
      type uint64;
      description
        "at time";
    }
    leaf at-time-nsec {
      type uint64;
      description
        "at time nsec";
    }
    leaf addr {
      type uint16;
      description
        "Offset from base addr of the PARITY";
    }
    leaf parity {
      type uint16;
      description
        "parity";
    }
    leaf top-ec {
      type uint32;
      description
        "top ec";
    }
    leaf block-ec {
      type uint32;
      description
        "block ec";
    }
    leaf-list value {
      type uint8;
      description
        "value";
    }
  }

  grouping PARITY-NODE-BG {
    description
      "PARITY NODE BG";
    leaf mem-name {
      type string;
      description
        "Name assigned to mem";
    }
    leaf node-key {
      type uint32;
      description
        "32 bit key";
    }
    leaf alarm-on {
      type boolean;
      description
        "high threshold crossed";
    }
    leaf thresh-hi {
      type uint32;
      description
        "high threshold value";
    }
    leaf period-hi {
      type uint32;
      description
        "high period value";
    }
    leaf count {
      type uint32;
      description
        "Accumulated count";
    }
    leaf last-cleared {
      type uint64;
      description
        "Time  cleared";
    }
    leaf base-address {
      type uint64;
      description
        "Base addr of ASIC mem/reg";
    }
    list last-err {
      description
        "Collection of last errs";
      uses PARITY-DATA-BG;
    }
  }

  grouping PARITY-NODES-BG {
    description
      "PARITY NODES BG";
    list error {
      description
        "Collection of errors";
      uses PARITY-NODE-BG;
    }
  }

  grouping CRC-DATA-BG {
    description
      "CRC DATA BG";
    leaf at-time {
      type uint64;
      description
        "at time";
    }
    leaf at-time-nsec {
      type uint64;
      description
        "at time nsec";
    }
    leaf counter-val {
      type uint32;
      description
        "counter val";
    }
    leaf top-ec {
      type uint32;
      description
        "top ec";
    }
    leaf block-ec {
      type uint32;
      description
        "block ec";
    }
  }

  grouping CRC-NODE-BG {
    description
      "CRC NODE BG";
    leaf name {
      type string;
      description
        "name";
    }
    leaf node-key {
      type uint32;
      description
        "32 bit key";
    }
    leaf alarm-on {
      type boolean;
      description
        "high threshold crossed";
    }
    leaf thresh-hi {
      type uint32;
      description
        "high threshold value";
    }
    leaf period-hi {
      type uint32;
      description
        "high period value";
    }
    leaf count {
      type uint32;
      description
        "Accumulated count";
    }
    leaf last-cleared {
      type uint64;
      description
        "Time  cleared";
    }
    list last-err {
      description
        "Collection of last errs";
      uses CRC-DATA-BG;
    }
  }

  grouping CRC-NODES-BG {
    description
      "CRC NODES BG";
    list error {
      description
        "Collection of errors";
      uses CRC-NODE-BG;
    }
  }

  grouping MBE-DATA-BG {
    description
      "Hfr multi bit error";
    leaf at-time {
      type uint64;
      description
        "at time";
    }
    leaf at-time-nsec {
      type uint64;
      description
        "at time nsec";
    }
    leaf addr {
      type uint32;
      description
        "Offset from base addr of the MBE";
    }
    leaf synd {
      type uint32;
      description
        "The error syndrome ";
    }
    leaf top-ec {
      type uint32;
      description
        "top ec";
    }
    leaf block-ec {
      type uint32;
      description
        "block ec";
    }
    leaf-list value {
      type uint32;
      description
        "Data value";
    }
  }

  grouping MBE-NODE-BG {
    description
      "MBE NODE BG";
    leaf mem-name {
      type string;
      description
        "Name assigned to mem";
    }
    leaf node-key {
      type uint32;
      description
        "32 bit key";
    }
    leaf alarm-on {
      type boolean;
      description
        "high threshold crossed";
    }
    leaf thresh-hi {
      type uint32;
      description
        "high threshold value";
    }
    leaf period-hi {
      type uint32;
      description
        "high period value";
    }
    leaf errored-data-width {
      type uint8;
      description
        "Width of the errored data in memory/reg";
    }
    leaf count {
      type uint32;
      description
        "Accumulated count";
    }
    leaf last-cleared {
      type uint64;
      description
        "Time  cleared";
    }
    leaf base-address {
      type uint64;
      description
        "Base addr of ASIC mem/reg";
    }
    list last-err {
      description
        "Collection of last errs";
      uses MBE-DATA-BG;
    }
  }

  grouping MBE-NODES-BG {
    description
      "MBE NODES BG";
    list error {
      description
        "Collection of errors";
      uses MBE-NODE-BG;
    }
  }

  grouping RESET-DATA-BG {
    description
      "RESET DATA BG";
    leaf at-time {
      type uint64;
      description
        "at time";
    }
    leaf at-time-nsec {
      type uint64;
      description
        "at time nsec";
    }
    leaf top-intr-status {
      type uint32;
      description
        "top intr status";
    }
    leaf top-halt-status {
      type uint32;
      description
        "top halt status";
    }
    leaf first-error-key {
      type uint32;
      description
        "first error key";
    }
    leaf reset-desc {
      type string;
      description
        "reset desc";
    }
    leaf top-ec {
      type uint32;
      description
        "top ec";
    }
    leaf block-ec {
      type uint32;
      description
        "block ec";
    }
  }

  grouping RESET-NODE-BG {
    description
      "RESET NODE BG";
    leaf name {
      type string;
      description
        "Name assigned to node";
    }
    leaf node-key {
      type uint32;
      description
        "32 bit key";
    }
    leaf alarm-on {
      type boolean;
      description
        "high threshold crossed";
    }
    leaf thresh-hi {
      type uint32;
      description
        "high threshold value";
    }
    leaf period-hi {
      type uint32;
      description
        "high period value";
    }
    leaf count {
      type uint32;
      description
        "Accumulated count";
    }
    leaf last-cleared {
      type uint64;
      description
        "Time  cleared";
    }
    list last-err {
      description
        "Collection of last errs";
      uses RESET-DATA-BG;
    }
  }

  grouping RESET-NODES-BG {
    description
      "RESET NODES BG";
    list error {
      description
        "Collection of errors";
      uses RESET-NODE-BG;
    }
  }

  grouping SBE-DATA-BG {
    description
      "Hfr single bit error";
    leaf at-time {
      type uint64;
      description
        "at time";
    }
    leaf at-time-nsec {
      type uint64;
      description
        "at time nsec";
    }
    leaf addr {
      type uint32;
      description
        "Offset from base addr of the SBE";
    }
    leaf synd {
      type uint32;
      description
        "The error syndrome ";
    }
    leaf bit-pos {
      type uint32;
      description
        "The bit pos at which the error";
    }
    leaf top-ec {
      type uint32;
      description
        "top ec";
    }
    leaf block-ec {
      type uint32;
      description
        "block ec";
    }
    leaf-list value {
      type uint32;
      description
        "Data value";
    }
  }

  grouping SBE-NODE-BG {
    description
      "SBE NODE BG";
    leaf mem-name {
      type string;
      description
        "Name assigned to mem";
    }
    leaf node-key {
      type uint32;
      description
        "32 bit key";
    }
    leaf alarm-on {
      type boolean;
      description
        "high threshold crossed";
    }
    leaf thresh-hi {
      type uint32;
      description
        "high threshold value";
    }
    leaf period-hi {
      type uint32;
      description
        "high period value";
    }
    leaf errored-data-width {
      type uint8;
      description
        "Width of the err data in memory/reg";
    }
    leaf count {
      type uint32;
      description
        "Accumulated count";
    }
    leaf last-cleared {
      type uint64;
      description
        "Time  cleared";
    }
    leaf base-address {
      type uint64;
      description
        "Base addr of ASIC mem/reg";
    }
    list last-err {
      description
        "Collection of last errs";
      uses SBE-DATA-BG;
    }
  }

  grouping SBE-NODES-BG {
    description
      "SBE NODES BG";
    list error {
      description
        "Collection of errors";
      uses SBE-NODE-BG;
    }
  }

  grouping PCIE-TLP-HEADER-DATA-BG {
    description
      "PCIE TLP HEADER DATA BG";
    leaf fmt-type {
      type uint32;
      description
        "fmt type";
    }
    leaf traffic-class {
      type uint32;
      description
        "traffic class";
    }
    leaf tlp-digest-field-present {
      type boolean;
      description
        "tlp digest field present";
    }
    leaf poisoned-data {
      type boolean;
      description
        "poisoned data";
    }
    leaf relaxed-ordering {
      type boolean;
      description
        "relaxed ordering";
    }
    leaf no-snoop {
      type boolean;
      description
        "no snoop";
    }
    leaf length {
      type uint16;
      description
        "length";
    }
    leaf first-dw-byte-enables {
      type uint8;
      description
        "first dw byte enables";
    }
    leaf last-dw-byte-enables {
      type uint8;
      description
        "last dw byte enables";
    }
    leaf-list transaction-descriptor {
      type uint8;
      description
        "transaction descriptor";
    }
  }

  grouping PCIE-ASIC-ERRORS-DATA-BG {
    description
      "PCIE ASIC ERRORS DATA BG";
    container tlp-header-data {
      description
        "tlp header data";
      uses PCIE-TLP-HEADER-DATA-BG;
    }
    leaf err-type {
      type uint32;
      description
        "err type";
    }
    leaf severity {
      type uint32;
      description
        "severity";
    }
    leaf err-attribute {
      type uint32;
      description
        "err attribute";
    }
    leaf is-tlp-header-present {
      type boolean;
      description
        "is tlp header present";
    }
    leaf-list raw-tlp-header {
      type uint32;
      description
        "raw tlp header";
    }
  }

  grouping PCIE-DATA-BG {
    description
      "PCIE DATA BG";
    container error-data {
      description
        "error data";
      uses PCIE-ASIC-ERRORS-DATA-BG;
    }
    leaf at-time {
      type uint64;
      description
        "at time";
    }
    leaf at-time-nsec {
      type uint64;
      description
        "at time nsec";
    }
    leaf counter-val {
      type uint32;
      description
        "counter val";
    }
    leaf top-ec {
      type uint32;
      description
        "top ec";
    }
    leaf block-ec {
      type uint32;
      description
        "block ec";
    }
  }

  grouping PCIE-NODE-BG {
    description
      "PCIE NODE BG";
    leaf name {
      type string;
      description
        "Name assigned to mem";
    }
    leaf node-key {
      type uint32;
      description
        "32 bit key";
    }
    leaf alarm-on {
      type boolean;
      description
        "High threshold crossed";
    }
    leaf thresh-hi {
      type uint32;
      description
        "High threshold value";
    }
    leaf period-hi {
      type uint32;
      description
        "High period value";
    }
    leaf count {
      type uint32;
      description
        "Accumulated count";
    }
    leaf last-cleared {
      type uint64;
      description
        "Time  cleared";
    }
    list last-err {
      description
        "Collection of last errs";
      uses PCIE-DATA-BG;
    }
  }

  grouping PCIE-NODES-BG {
    description
      "PCIE NODES BG";
    list error {
      description
        "Collection of errors";
      uses PCIE-NODE-BG;
    }
  }

  grouping CIHERR-ERROR-DATA-BG {
    description
      "CIHERR ERROR DATA BG";
    leaf at-time {
      type uint64;
      description
        "Asic error time";
    }
    leaf at-time-nsec {
      type uint64;
      description
        "Asic error nsec";
    }
    leaf counter-val {
      type uint32;
      description
        "Number of occurrence";
    }
    leaf error-desc {
      type string;
      description
        "Error description";
    }
    list error-regval {
      description
        "Error register value";
      leaf entry {
        type uint8;
        description
          "Error register value";
      }
    }
  }

  grouping CSRS-INFO-BG {
    description
      "CSRS INFO BG";
    leaf name {
      type string;
      description
        "Name of csrs register";
    }
    leaf address {
      type uint64;
      description
        "Address of csrs register";
    }
    leaf width {
      type uint32;
      description
        "Width of csrs register";
    }
  }

  grouping CIHERR-NODE-BG {
    description
      "CIHERR NODE BG";
    leaf name {
      type string;
      description
        "Name assigned to mem";
    }
    leaf asic-info {
      type string;
      description
        "Name of rack/board/asic";
    }
    leaf node-key {
      type uint32;
      description
        "32 bit key";
    }
    leaf alarm-on {
      type boolean;
      description
        "High threshold crossed";
    }
    leaf thresh-hi {
      type uint32;
      description
        "High threshold value";
    }
    leaf period-hi {
      type uint32;
      description
        "High period value";
    }
    leaf thresh-lo {
      type uint32;
      description
        "High threshold value";
    }
    leaf period-lo {
      type uint32;
      description
        "High period value";
    }
    leaf count {
      type uint32;
      description
        "Accumulated count";
    }
    leaf intr-type {
      type uint32;
      description
        "Type of error";
    }
    leaf leaf-id {
      type uint32;
      description
        "Leaf ID defined in user data";
    }
    leaf last-cleared {
      type uint64;
      description
        "Time  cleared";
    }
    list csrs-info {
      description
        "List of csrs_info";
      uses CSRS-INFO-BG;
    }
    list last-err {
      description
        "Last Printable error information";
      uses CIHERR-ERROR-DATA-BG;
    }
  }

  grouping CIHERR-NODES-BG {
    description
      "CIHERR NODES BG";
    list error {
      description
        "Collection of errors";
      uses CIHERR-NODE-BG;
    }
  }

  grouping PACERR-ERROR-DATA-BG {
    description
      "PACERR ERROR DATA BG";
    leaf at-time {
      type uint64;
      description
        "at time";
    }
    leaf at-time-nsec {
      type uint64;
      description
        "at time nsec";
    }
    leaf counter-val {
      type uint32;
      description
        "counter val";
    }
    leaf error-desc {
      type string;
      description
        "error desc";
    }
  }

  grouping PACERR-NODE-BG {
    description
      "PACERR NODE BG";
    leaf name {
      type string;
      description
        "Name assigned to mem";
    }
    leaf asic-info {
      type string;
      description
        "Name of rack/board/asic";
    }
    leaf node-key {
      type uint32;
      description
        "32 bit key";
    }
    leaf alarm-on {
      type boolean;
      description
        "High threshold crossed";
    }
    leaf thresh-hi {
      type uint32;
      description
        "High threshold value";
    }
    leaf period-hi {
      type uint32;
      description
        "High period value";
    }
    leaf thresh-lo {
      type uint32;
      description
        "Low threshold value";
    }
    leaf period-lo {
      type uint32;
      description
        "Low period value";
    }
    leaf count {
      type uint32;
      description
        "Accumulated count";
    }
    leaf block-id {
      type uint32;
      description
        "block where error occurred";
    }
    leaf addr {
      type uint32;
      description
        "addr of the error interrupt inside node";
    }
    leaf leaf-id {
      type uint32;
      description
        "leaf_id of the error occurred";
    }
    leaf intr-type {
      type uint32;
      description
        "Type of error";
    }
    leaf last-cleared {
      type uint64;
      description
        "Time  cleared";
    }
    list last-err {
      description
        "Last Printable error information";
      uses PACERR-ERROR-DATA-BG;
    }
  }

  grouping PACERR-NODES-BG {
    description
      "PACERR NODES BG";
    list error {
      description
        "Collection of errors";
      uses PACERR-NODE-BG;
    }
  }

  grouping SCHEMA-DATA-BG {
    description
      "SCHEMA DATA BG";
    container pacerr-nodes {
      description
        "pacerr nodes";
      uses PACERR-NODES-BG;
    }
    container ciherr-nodes {
      description
        "ciherr nodes";
      uses CIHERR-NODES-BG;
    }
    container pcie-nodes {
      description
        "pcie nodes";
      uses PCIE-NODES-BG;
    }
    container sbe-nodes {
      description
        "sbe nodes";
      uses SBE-NODES-BG;
    }
    container reset-nodes {
      description
        "reset nodes";
      uses RESET-NODES-BG;
    }
    container mbe-nodes {
      description
        "mbe nodes";
      uses MBE-NODES-BG;
    }
    container crc-nodes {
      description
        "crc nodes";
      uses CRC-NODES-BG;
    }
    container parity-nodes {
      description
        "parity nodes";
      uses PARITY-NODES-BG;
    }
    container generic-nodes {
      description
        "generic nodes";
      uses GENERIC-NODES-BG;
    }
  }

  grouping ASIC-ERROR-INST-BG {
    description
      "ASIC ERROR INST BG";
    leaf err-class-name {
      type string;
      description
        "err class name";
    }
    leaf count {
      type uint32;
      description
        "count";
    }
  }
}
