module Cisco-IOS-XR-ipv4-dhcpd-oper {
  namespace "http://cisco.com/ns/yang/Cisco-IOS-XR-ipv4-dhcpd-oper";
  prefix ipv4-dhcpd-oper;

  import Cisco-IOS-XR-types {
    prefix xr;
  }
  import cisco-semver {
    prefix semver;
  }

  include Cisco-IOS-XR-ipv4-dhcpd-oper-sub2 {
    revision-date 2022-12-13;
  }
  include Cisco-IOS-XR-ipv4-dhcpd-oper-sub1 {
    revision-date 2022-12-13;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ipv4-dhcpd package operational data.

     This module contains definitions
     for the following management objects:
       dhcp-client: DHCP client operational data
       ipv4-dhcpd: IPV4 DHCPD operational data

     Copyright (c) 2013-2022 by Cisco Systems, Inc.
     All rights reserved.";

  revision 2022-12-13 {
    semver:module-version "3.0.0";
    description
      "Removed SnoopBindingCHADDR,SnoopBindingCHADDRLen and added MacAddress,SnoopBindingRemainingLeaseTime for dhcp Snoop Binding.
       2022-11-08
         Migrated LEAF-LIST with duplicate value to LIST type.
       2022-09-08
         Fixed oper for dhcp statistics and binding.
       2022-02-11
         Enhanced interface length based on IM changes.
       2021-10-07
         Added session_in_bound_client_id_changed counter in debug stats.
       2021-10-05
         Migrated LEAF-LIST with duplicate value to LIST type.";
  }
  revision 2021-09-14 {
    semver:module-version "2.0.0";
    description
      "Fixed GET-OPER to display interface name in standard format.
       2021-09-08
          Fixed GET-OPER rpc response which returns false value.
       2021-08-23
          Migrated LEAF-LIST with duplicate value to LIST type.
       2021-06-21
          Added l2-interface information for show command
       2021-04-09
          NodeID keyword changed from nodeid to NodeName as per standard";
  }
  revision 2020-11-20 {
    semver:module-version "1.1.0";
    description
      "Added Yang Support for ADT,to retrive statistcs with help of vrf/interface.
       2020-09-30
           Modified to accommodate cdm changes";
  }
  revision 2019-06-25 {
    semver:module-version "1.0.1";
    description
      "Introduced an option to show dhcp rate limit hit counters.";
  }
  revision 2019-04-05 {
    description
      "Establish semantic version baseline.";
  }
  revision 2018-09-20 {
    description
      "Fixing yang gaps.";
  }
  revision 2015-11-09 {
    description
      "IOS XR 6.0 revision.";
  }

  container dhcp-client {
    config false;
    description
      "DHCP client operational data";
    container nodes {
      description
        "DHCP client list of nodes";
      list node {
        key "node-name";
        description
          "DHCP client particular node name";
        container client-stats {
          description
            "IPv4 DHCP client statistics table";
          list client-stat {
            key "client-ifhandle";
            description
              "DHCP client binding statistics";
            leaf client-ifhandle {
              type xr:Cisco-ios-xr-string;
              description
                "Client Ifhandle";
            }
            uses DHCPC-EDM-CLIENT-IPV4-STATS-BAG;
          }
        }
        container clients {
          description
            "IPv4 DHCP client table";
          list client {
            key "client-ifhandle";
            description
              "Single DHCP client binding";
            leaf client-ifhandle {
              type xr:Cisco-ios-xr-string;
              description
                "Client Ifhandle";
            }
            uses DHCPC-EDM-CLIENT-IPV4-BAG;
          }
        }
        leaf node-name {
          type xr:Node-id;
          description
            "Node name";
        }
      }
    }
  }
  container ipv4-dhcpd {
    config false;
    description
      "IPV4 DHCPD operational data";
    container snoop {
      description
        "DHCP Snoop operational data";
      container bindings {
        description
          "DHCP Snoop Bindings";
        list binding {
          key "client-uid";
          description
            "DHCP Snoop binding";
          leaf client-uid {
            type xr:Cisco-ios-xr-string;
            description
              "Client opaque handle";
          }
          uses IPV4-DHCPD-SNOOP-BINDING;
        }
      }
      container binding-statistics {
        description
          "DHCP snoop binding statistics";
        uses IPV4-DHCPD-SNOOP-BINDING-STATISTICS;
      }
      container statistics-info {
        description
          "DHCP snoop statistics info";
        uses IPV4-DHCPD-SNOOP-STATS-INFO;
      }
      container profiles {
        description
          "DHCP Snoop Profile";
        list profile {
          key "profile-name";
          description
            "DHCP Snoop profile";
          leaf profile-name {
            type xr:Cisco-ios-xr-string;
            description
              "Profile name";
          }
          uses IPV4-DHCPD-SNOOP-PROFILE;
        }
      }
      container statistics {
        description
          "DHCP Snoop Statistics";
        list statistic {
          key "bridge-name";
          description
            "DHCP Snoop bridge domain statistics";
          leaf bridge-name {
            type xr:Cisco-ios-xr-string;
            description
              "Bridge domain name";
          }
          uses IPV4-DHCPD-SNOOP-STATS;
        }
      }
    }
    container nodes {
      description
        "IPv4 DHCPD operational data for a particular
         location";
      list node {
        key "node-name";
        description
          "Location. For eg., 0/1/CPU0";
        container proxy {
          description
            "IPv4 DHCP proxy operational data";
          container statistics-info {
            description
              "DHCP proxy stats info";
            uses IPV4-DHCPD-PROXY-STATS-INFO;
          }
          container vrfs {
            description
              "DHCP proxy list of VRF names";
            list vrf {
              key "vrf-name";
              description
                "IPv4 DHCP proxy VRF name";
              container statistics {
                description
                  "IPv4 DHCP proxy statistics";
                uses IPV4-DHCPD-PROXY-TYPE;
              }
              leaf vrf-name {
                type xr:Cisco-ios-xr-string;
                description
                  "VRF name";
              }
            }
          }
          container profiles {
            description
              "IPv4 DHCP proxy profile";
            list profile {
              key "profile-name";
              description
                "IPv4 DHCP proxy profile";
              leaf profile-name {
                type xr:Cisco-ios-xr-string;
                description
                  "Profile name";
              }
              uses IPV4-DHCPD-PROXY-PROFILE;
            }
          }
          container stats {
            description
              "IPv4 DHCP proxy stats";
            list stat {
              description
                "Proxy statistics for vrf/interface";
              leaf vrf-name {
                type xr:Cisco-ios-xr-string;
                description
                  "L3 VRF Name";
              }
              leaf interface-name {
                type xr:Interface-name;
                description
                  "L3 Interface Name";
              }
              uses IPV4-DHCPD-VRF-INTF-STATS;
            }
          }
          container disconnect-histories {
            description
              "DHCP proxy disconnect history";
            list disconnect-history {
              key "index";
              description
                "Single DHCP proxy disconnect history";
              leaf index {
                type xr:Cisco-ios-xr-string;
                description
                  "Index";
              }
              uses IPV4-DHCPD-DISC-HISTORY;
            }
          }
          container binding {
            description
              "DHCP proxy bindings";
            container clients {
              description
                "DHCP proxy client bindings";
              list client {
                key "client-id";
                description
                  "Single DHCP proxy binding";
                leaf client-id {
                  type xr:Cisco-ios-xr-string;
                  description
                    "Client ID";
                }
                uses IPV4-DHCPD-PROXY-BINDING;
              }
            }
            container summary {
              description
                "DHCP proxy binding summary";
              uses IPV4-DHCPD-PROXY-BINDINGS-SUMMARY;
            }
          }
          container statistics {
            description
              "DHCP proxy statistics";
            container summary {
              description
                "DHCP Proxy binding statistics";
              uses IPV4-DHCPD-PROXY-STATS;
            }
          }
        }
        container interfaces {
          description
            "IPv4 DHCP proxy/server Interface";
          list interface {
            key "interface-name";
            description
              "IPv4 DHCP proxy/server interface info";
            leaf interface-name {
              type xr:Interface-name;
              description
                "Interface Name";
            }
            uses IPV4-DHCPD-PROXY-INTERFACE;
          }
        }
        container base {
          description
            "IPv4 DHCP base operational data";
          container statistics {
            description
              "DHCP base statistics";
            uses IPV4-DHCPD-PROXY-STATS;
          }
          container drops {
            description
              "DHCP base drop statistics";
            uses IPV4-DHCPD-BASE-DROP-STATS;
          }
          container issu-status {
            description
              "IPv4 DHCP ISSU status";
            uses DHCPD-ISSU-STATUS-INFO;
          }
          container vrfs {
            description
              "DHCP base list of VRF names";
            list vrf {
              key "vrf-name";
              description
                "IPv4 DHCP base VRF name";
              container statistics {
                description
                  "IPv4 DHCP base statistics";
                uses IPV4-DHCPD-PROXY-TYPE;
              }
              leaf vrf-name {
                type xr:Cisco-ios-xr-string;
                description
                  "VRF name";
              }
            }
          }
          container profiles {
            description
              "IPv4 DHCP Base profile";
            list profile {
              key "profile-name";
              description
                "IPv4 DHCP base profile";
              leaf profile-name {
                type xr:Cisco-ios-xr-string;
                description
                  "Profile name";
              }
              uses IPV4-DHCPD-BASE-PROFILE;
            }
          }
          container database {
            description
              "IPv4 DHCP database";
            uses IPV4-DHCPD-DATABASE;
          }
          container stats {
            description
              "IPv4 DHCP base stats";
            list stat {
              description
                "Base statistics for vrf/interface";
              leaf vrf-name {
                type xr:Cisco-ios-xr-string;
                description
                  "L3 VRF Name";
              }
              leaf interface-name {
                type xr:Interface-name;
                description
                  "L3 Interface Name";
              }
              uses IPV4-DHCPD-VRF-INTF-STATS;
            }
          }
        }
        container server {
          description
            "IPv4 DHCP Server operational data";
          container statistics {
            description
              "DHCP Server statistics";
            container summary {
              description
                "DHCP server statistics";
              uses IPV4-DHCPD-PROXY-STATS;
            }
          }
          container profiles {
            description
              "IPv4 DHCP Server profile";
            list profile {
              key "server-profile-name";
              description
                "IPv4 DHCP server profile";
              leaf server-profile-name {
                type xr:Cisco-ios-xr-string;
                description
                  "Profile name";
              }
              uses IPV4-DHCPD-SERVER-PROFILE;
            }
          }
          container stats {
            description
              "IPv4 DHCP server stats";
            list stat {
              description
                "Server statistics for vrf/interface";
              leaf vrf-name {
                type xr:Cisco-ios-xr-string;
                description
                  "L3 VRF Name";
              }
              leaf interface-name {
                type xr:Interface-name;
                description
                  "L3 Interface Name";
              }
              uses IPV4-DHCPD-VRF-INTF-STATS;
            }
          }
          container binding {
            description
              "DHCP server bindings";
            container summary {
              description
                "DHCP server binding summary";
              uses IPV4-DHCPD-PROXY-BINDINGS-SUMMARY;
            }
            container clients {
              description
                "DHCP server client bindings";
              list client {
                key "client-id";
                description
                  "Single DHCP Server binding";
                leaf client-id {
                  type xr:Cisco-ios-xr-string;
                  description
                    "Client ID";
                }
                uses IPV4-DHCPD-PROXY-BINDING;
              }
            }
          }
          container disconnect-histories {
            description
              "DHCP server disconnect history";
            list disconnect-history {
              key "index";
              description
                "Single DHCP server disconnect history";
              leaf index {
                type xr:Cisco-ios-xr-string;
                description
                  "Index";
              }
              uses IPV4-DHCPD-DISC-HISTORY;
            }
          }
          container statistics-info {
            description
              "DHCP proxy stats info";
            uses IPV4-DHCPD-PROXY-STATS-INFO;
          }
          container vrfs {
            description
              "DHCP Server list of VRF names";
            list vrf {
              key "vrf-name";
              description
                "IPv4 DHCP server VRF name";
              container statistics {
                description
                  "IPv4 DHCP server statistics";
                uses IPV4-DHCPD-PROXY-TYPE;
              }
              leaf vrf-name {
                type xr:Cisco-ios-xr-string;
                description
                  "VRF name";
              }
            }
          }
        }
        container relay {
          description
            "IPv4 DHCPD Relay operational data";
          container profiles {
            description
              "DHCP Relay Profiles";
            list profile {
              key "profile-name";
              description
                "DHCP Relay profile";
              leaf profile-name {
                type xr:Cisco-ios-xr-string;
                description
                  "Profile name";
              }
              uses IPV4-DHCPD-RELAY-PROFILE;
            }
          }
          container statistics-info {
            description
              "DHCP relay statistics info";
            uses IPV4-DHCPD-RELAY-STATS-INFO;
          }
          container statistics {
            description
              "DHCP Relay VRF statistics";
            container summary {
              description
                "DHCP Relay VRF statistics";
              uses IPV4-DHCPD-RELAY-STATS;
            }
          }
          container vrfs {
            description
              "DHCP relay list of VRF names";
            list vrf {
              key "vrf-name";
              description
                "IPv4 DHCP relay VRF name";
              container vrf-statistics {
                description
                  "IPv4 DHCP relay statistics";
                uses IPV4-DHCPD-PROXY-TYPE;
              }
              leaf vrf-name {
                type xr:Cisco-ios-xr-string;
                description
                  "VRF name";
              }
            }
          }
        }
        leaf node-name {
          type xr:Node-id;
          description
            "Node name";
        }
      }
    }
  }
}
