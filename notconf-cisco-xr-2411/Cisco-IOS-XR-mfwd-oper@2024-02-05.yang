module Cisco-IOS-XR-mfwd-oper {
  namespace "http://cisco.com/ns/yang/Cisco-IOS-XR-mfwd-oper";
  prefix mfwd-oper;

  import ietf-inet-types {
    prefix inet;
  }
  import Cisco-IOS-XR-types {
    prefix xr;
  }
  import cisco-semver {
    prefix semver;
  }

  include Cisco-IOS-XR-mfwd-oper-sub2 {
    revision-date 2024-02-05;
  }
  include Cisco-IOS-XR-mfwd-oper-sub1 {
    revision-date 2024-02-05;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR mfwd package operational data.

     This module contains definitions
     for the following management objects:
       mfwd: MFWD operational data
       ipv6-mfwd: IPV6 MFWD operational data

     Copyright (c) 2013-2024 by Cisco Systems, Inc.
     All rights reserved.";

  revision 2024-02-05 {
    semver:module-version "1.2.0";
    description
      "Changed pathname of RouteStatisticsTable to remove same-path conflict with RouteTable
       2023-02-09
         Adding a new field in mfwd_route_bag_event_history which is part of the ipv4_mfwd_route_bag
       2022-12-01
         Adding mfwd interface stats bag to display interface statistics
       2022-09-22
         New entry added in the bag and schema files for OOR-mode information support, for newly added CLI operational command
       2022-04-29
         Backward compatible addition in mfwd_bvi_mroute_bag and new bag table_name
       2021-11-19
         Backward compatible addition in ipv4_mfwd_connection and new bag mfib_timespec";
  }
  revision 2020-10-11 {
    semver:module-version "1.1.0";
    description
      "Backward compatible addition in leaf ul-interface, customer-mdt-data-tree-sidacl-name, is-customer-mdt-data-tree-sidacl-present and ,is-all-customer-routes-for-tree-sid-data-mdt";
  }
  revision 2019-08-27 {
    semver:module-version "1.0.0";
    description
      "Initial IOS-XR MFWD native model";
  }
  revision 2019-04-05 {
    description
      "Establish semantic version baseline.";
  }
  revision 2015-11-09 {
    description
      "IOS XR 6.0 revision.";
  }

  typedef Encap {
    type enumeration {
      enum "any" {
        value 0;
        description
          "Encap Any";
      }
      enum "lsm" {
        value 1;
        description
          "Encap LSM";
      }
      enum "te" {
        value 2;
        description
          "Encap TE";
      }
      enum "gre" {
        value 3;
        description
          "Encap GRE";
      }
    }
    description
      "Encap";
  }

  grouping NODE-TABLE {
    description
      "Common node of mfwd, ipv6-mfwd";
    container nodes {
      description
        "All Nodes";
      list node {
        key "node-name";
        description
          "Multicast Forwarding operational data for this
           particular node";
        container process {
          description
            "MFWD NSF Databases";
          container nsf {
            description
              "MFWD NSF Information";
            uses IPV4-MFWD-NSF-BAG;
          }
          container vrfs {
            description
              "Traversal in VRF Name/ID DB";
            list vrf {
              key "vrf-name";
              description
                "VRF";
              leaf vrf-name {
                type xr:Cisco-ios-xr-string {
                  length "1..32";
                }
                description
                  "VRF Name";
              }
              uses IPV4-MFWD-TABLE-BAG;
            }
          }
          container table-ids {
            description
              "Traversal using Table ID DB";
            list table-id {
              key "table-id";
              description
                "Table ID";
              leaf table-id {
                type uint32;
                description
                  "Table ID";
              }
              uses IPV4-MFWD-TABLE-BAG;
            }
          }
          container bvi-routes {
            description
              "MFWD BVI route table";
            list bvi-route {
              key "interface-name source-address group-address prefix-length";
              description
                "MFWD BVI route entry";
              leaf interface-name {
                type xr:Interface-name;
                description
                  "Interface Name";
              }
              leaf source-address {
                type inet:ip-address-no-zone;
                description
                  "Source Address";
              }
              leaf group-address {
                type inet:ip-address-no-zone;
                description
                  "Group Address";
              }
              leaf prefix-length {
                type uint32;
                description
                  "Prefix Length";
              }
              uses MFWD-BVI-ROUTE-BAG;
            }
          }
          container oor-mode {
            description
              "MFWD OOR-MODE Information";
            uses MFWD-OOR-MODE-BAG;
          }
        }
        container databases {
          description
            "MFWD Databases";
          list database {
            key "database-name";
            description
              "Database Name";
            container encap-registrations {
              description
                "MFWD Encap Registration";
              list encap-registration {
                key "encap-type lsm-id if-handle source-address group-address";
                description
                  "MFWD Encap Registration";
                leaf encap-type {
                  type Encap;
                  description
                    "Encap Type";
                }
                leaf lsm-id {
                  type uint32;
                  description
                    "LSM ID";
                }
                leaf if-handle {
                  type uint32;
                  description
                    "IFHandle";
                }
                leaf source-address {
                  type inet:ip-address-no-zone;
                  description
                    "Source Address";
                }
                leaf group-address {
                  type inet:ip-address-no-zone;
                  description
                    "Group Address";
                }
                uses IPV4-MFWD-REGDB-BAG;
              }
            }
            container summary {
              description
                "MFWD RouteDB Summary Information";
              uses IPV4-MFWD-ROUTE-SUMM-BAG;
            }
            container encap-identifiers {
              description
                "MFWD Encap Table";
              list encap-identifier {
                key "encap-id";
                description
                  "MFWD Encap Identifier";
                leaf encap-id {
                  type uint32;
                  description
                    "Encap ID";
                }
                uses IPV4-MFWD-ENCAPID-BAG;
              }
            }
            container detail-interfaces {
              description
                "Detailed information about MFWD Interfaces";
              list detail-interface {
                key "interface-name";
                description
                  "Detailed MFWD Interface info";
                leaf interface-name {
                  type xr:Interface-name;
                  description
                    "Interface Name";
                }
                uses IPV4-MFWD-INTF-DETAIL-BAG;
              }
            }
            container interface-routes {
              description
                "Display MFIB interface specific information";
              list interface-route {
                key "interface-name";
                description
                  "Interface Table";
                container source-group-addresses {
                  description
                    "Source,Group Address Table";
                  list source-group-address {
                    key "source-address group-address prefix-length";
                    description
                      "List the routes associated with an
                       Interface";
                    leaf source-address {
                      type inet:ip-address-no-zone;
                      description
                        "Source Address";
                    }
                    leaf group-address {
                      type inet:ip-address-no-zone;
                      description
                        "Group Address";
                    }
                    leaf prefix-length {
                      type uint32 {
                        range "0..128";
                      }
                      description
                        "Prefix Length";
                    }
                    uses IPV4-MFWD-ROUTE-BAG;
                  }
                }
                leaf interface-name {
                  type xr:Interface-name;
                  description
                    "Interface Name";
                }
              }
            }
            container counters {
              description
                "MFWD RouteDB Counters Information";
              uses IPV4-MFWD-TABLE-COUNTERS-BAG;
            }
            container interfaces {
              description
                "Information about MFWD Interfaces";
              list interface {
                key "interface-name";
                description
                  "MFWD Interface information";
                leaf interface-name {
                  type xr:Interface-name;
                  description
                    "Interface Name";
                }
                uses IPV4-MFWD-INTF-BAG;
              }
            }
            container encapsulation-infos {
              description
                "Encapsulation InformationTable";
              list encapsulation-info {
                key "source source-address group group-address";
                description
                  "Encapsulation Information";
                leaf source {
                  type xr:Cisco-ios-xr-string {
                    length "1..9";
                  }
                  description
                    "prev source CTID type";
                }
                leaf source-address {
                  type inet:ip-address-no-zone;
                  description
                    "prev source CTID ID 1";
                }
                leaf group {
                  type xr:Cisco-ios-xr-string {
                    length "1..9";
                  }
                  description
                    "prev group CTID type";
                }
                leaf group-address {
                  type inet:ip-address-no-zone;
                  description
                    "prev group CTID ID 2";
                }
                uses IPV4-MFWD-ENCAP-BAG;
              }
            }
            container routes {
              description
                "The set of MRIB RouteDB operations";
              list route {
                key "source-address group-address prefix-length";
                description
                  "MFWD Route Entry Information";
                leaf source-address {
                  type inet:ip-address-no-zone;
                  description
                    "Source Address";
                }
                leaf group-address {
                  type inet:ip-address-no-zone;
                  description
                    "Group Address";
                }
                leaf prefix-length {
                  type uint32 {
                    range "0..128";
                  }
                  description
                    "Prefix Length";
                }
                uses IPV4-MFWD-ROUTE-BAG;
              }
            }
            container svd {
              description
                "SVD table information";
              uses IPV4-MFWD-SVD-BAG;
            }
            container connections {
              description
                "MFWD RouteDB connections information";
              uses IPV4-MFWD-CONNECTION-BAG;
            }
            container imdr {
              description
                "MFWD RouteDB IMDR status information";
              uses IPV4-MFWD-IMDR-BAG;
            }
            container bvi-interfaces {
              description
                "MFIB BVI interface mapping";
              list bvi-interface {
                key "interface-name";
                description
                  "BVI Interface Handle";
                leaf interface-name {
                  type xr:Interface-name;
                  description
                    "Interface Name";
                }
                uses MFWD-BVI-INTERFACE-BAG;
              }
            }
            container route-statistics {
              description
                "The set of MRIB RouteDB and route statistics
                 operations";
              list route-statistic {
                key "source-address group-address prefix-length";
                description
                  "MFWD Route Entry and route statistics
                   Information";
                leaf source-address {
                  type inet:ip-address-no-zone;
                  description
                    "Source Address";
                }
                leaf group-address {
                  type inet:ip-address-no-zone;
                  description
                    "Group Address";
                }
                leaf prefix-length {
                  type uint32 {
                    range "0..128";
                  }
                  description
                    "Prefix Length";
                }
                uses IPV4-MFWD-ROUTE-BAG;
              }
            }
            leaf database-name {
              type xr:Cisco-ios-xr-string {
                length "1..32";
              }
              description
                "Database Name";
            }
          }
        }
        leaf node-name {
          type xr:Node-id;
          description
            "Node name";
        }
      }
    }
  }

  container mfwd {
    config false;
    description
      "MFWD operational data";
    uses NODE-TABLE;
  }
  container ipv6-mfwd {
    config false;
    description
      "IPV6 MFWD operational data";
    uses NODE-TABLE;
  }
}
