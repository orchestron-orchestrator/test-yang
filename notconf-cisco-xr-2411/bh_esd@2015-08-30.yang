module bh_esd {
  namespace "http://cisco.com/calvados/bh_esd";
  prefix bh_esd;

  import Cisco-IOS-XR-sysadmin-show-trace {
    prefix show_trace;
  }

  organization
    "Cisco Systems, Inc.";
  contact
    "Cisco Systems, Inc.
     Customer Service

     Postal: 170 West Tasman Drive
     San Jose, CA 95134

     Tel: +1 800 553-NETS

     E-mail: cs-yang@cisco.com";
  description
    "This module contains definitions
     for the Calvados model objects.

     Copyright (c) 2012-2020 by Cisco Systems, Inc.
     All rights reserved.";

  revision 2015-08-30 {
    description
      "Initial version.";
  }

  container bh_esd {
    config false;
    uses show_trace:traceable;
  }
}
