module Cisco-IOS-XR-linux-os-heap-summary-oper {
  namespace "http://cisco.com/ns/yang/Cisco-IOS-XR-linux-os-heap-summary-oper";
  prefix linux-os-heap-summary-oper;

  import Cisco-IOS-XR-types {
    prefix xr;
  }
  import cisco-semver {
    prefix semver;
  }

  include Cisco-IOS-XR-linux-os-heap-summary-oper-sub1 {
    revision-date 2021-04-16;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR linux-os-heap-summary package operational data.

     This module contains definitions
     for the following management objects:
       heap-summary: Heap Summary

     Copyright (c) 2013-2021 by Cisco Systems, Inc.
     All rights reserved.";

  revision 2021-04-16 {
    semver:module-version "2.0.0";
    description
      "Structuring the yang response of show memory heap summary all.";
  }
  revision 2019-04-05 {
    semver:module-version "1.0.1";
    description
      "Establish semantic version baseline.";
  }
  revision 2015-11-09 {
    description
      "IOS XR 6.0 revision.";
  }

  grouping PROCESS {
    description
      "Common node of process-table, all";
    list process {
      key "process-name";
      description
        "Process Name";
      leaf process-name {
        type xr:Cisco-ios-xr-string;
        description
          "Process name";
      }
      uses SHOW-MEM-HEAP-SUM-YANG;
    }
  }

  container heap-summary {
    config false;
    description
      "Heap Summary";
    container location-descriptions {
      description
        "Location";
      list location-description {
        key "node";
        description
          "Location specified in location";
        container process-table {
          description
            "List of processes";
          uses PROCESS;
        }
        leaf node {
          type xr:Node-id;
          description
            "Node location";
        }
      }
    }
    container all {
      description
        "All processes";
      uses PROCESS;
    }
  }
}
