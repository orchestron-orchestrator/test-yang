submodule Cisco-IOS-XR-asr9k-xbar-oper-sub4 {
  belongs-to Cisco-IOS-XR-asr9k-xbar-oper {
    prefix Cisco-IOS-XR-asr9k-xbar-oper;
  }

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR asr9k-xbar package operational data.

     Copyright (c) 2013-2019 by Cisco Systems, Inc.
     All rights reserved.";

  revision 2019-07-29 {
    semver:module-version "1.0.0";
    description
      "Support for bandwidth-utils-stats CLI.";
  }
  revision 2019-04-05 {
    description
      "Establish semantic version baseline.";
  }
  revision 2015-11-09 {
    description
      "IOS XR 6.0 revision.";
  }

  grouping BANDWIDTH-UTILS {
    description
      "BANDWIDTH UTILS";
    leaf-list bandwidth-util {
      type uint64;
      max-elements 6;
      description
        "bandwidth util";
    }
  }

  grouping XBAR-EDM-BANDWIDTH-UTILS {
    description
      "XBAR EDM BANDWIDTH UTILS";
    list port {
      max-elements 20;
      description
        "port";
      uses BANDWIDTH-UTILS;
    }
  }
}
