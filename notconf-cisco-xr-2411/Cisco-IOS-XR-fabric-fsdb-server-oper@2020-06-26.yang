module Cisco-IOS-XR-fabric-fsdb-server-oper {
  namespace "http://cisco.com/ns/yang/Cisco-IOS-XR-fabric-fsdb-server-oper";
  prefix fabric-fsdb-server-oper;

  import Cisco-IOS-XR-types {
    prefix xr;
  }
  import cisco-semver {
    prefix semver;
  }

  include Cisco-IOS-XR-fabric-fsdb-server-oper-sub1 {
    revision-date 2020-06-26;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR fabric-fsdb-server package operational data.

     This module contains definitions
     for the following management objects:
       fabric-server: Fabric Data

     Copyright (c) 2013-2020 by Cisco Systems, Inc.
     All rights reserved.";

  revision 2020-06-26 {
    semver:module-version "1.0.0";
    description
      "task-name field added.";
  }
  revision 2019-07-17 {
    description
      "Yang Schema fixed for fabric link port Information.";
  }
  revision 2019-04-05 {
    description
      "Establish semantic version baseline.";
  }
  revision 2015-11-09 {
    description
      "IOS XR 6.0 revision.";
  }

  container fabric-server {
    config false;
    description
      "Fabric Data";
    list rack-number {
      key "rack-num";
      description
        "Fabric Fsdb Rack Number";
      container stages {
        description
          "Fsdb Server Link Port";
        list stage {
          key "stage";
          description
            "Fsdb Server Link-Port Stage FIA=1;S1=2;S2=3
             ;S3=4;";
          leaf stage {
            type uint32;
            description
              "Stage Option fia/s1/s2/s3";
          }
          list rx-tx {
            key "rx-tx";
            description
              "Link Direction rx/tx - RX=0;TX=1;";
            leaf rx-tx {
              type uint32;
              description
                "Direction rx/tx";
            }
            list filter-option {
              key "foption";
              description
                "FE Port state - UP=0;DOWN=1;MISMATCH=2;ALL=3
                 ;";
              leaf foption {
                type uint32;
                description
                  "Filter option";
              }
              list links-info {
                key "log-slot-no";
                description
                  "Links Information - logical slot";
                leaf log-slot-no {
                  type uint32;
                  description
                    "Logical Slot Num";
                }
                list asics {
                  key "asic-inst";
                  description
                    "Links Information - asic instances";
                  leaf asic-inst {
                    type uint32;
                    description
                      "Asic Instance";
                  }
                  list links {
                    key "link-num";
                    description
                      "Links Information - link number";
                    container link {
                      description
                        "Single Link Information R/S/A/L";
                      uses FSDB-SERVER-EDM-LPORT;
                    }
                    leaf link-num {
                      type uint32;
                      description
                        "Link Number";
                    }
                  }
                }
              }
            }
          }
        }
      }
      container fsdb-stages {
        description
          "Fabric Fsdb Pla Data";
        list fsdb-stage {
          key "option";
          description
            "Option : s1 , s2 , s3 , s123";
          leaf option {
            type xr:Cisco-ios-xr-string;
            description
              "Stage option";
          }
          list fabid {
            key "fabid";
            description
              "Destination fabid";
            container fabid-xr {
              description
                "PLA info for fabid";
              uses FSDB-SERVER-EDM-PLA-FAB;
            }
            leaf fabid {
              type uint32;
              description
                "fabid";
            }
          }
        }
      }
      leaf rack-num {
        type uint32;
        description
          "Rack Number";
      }
    }
  }
}
