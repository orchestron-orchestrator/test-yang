module Cisco-IOS-XR-8000-platforms-npu-evict-voq-buff-oper {
  namespace "http://cisco.com/ns/yang/Cisco-IOS-XR-8000-platforms-npu-evict-voq-buff-oper";
  prefix xr-8000-platforms-npu-evict-voq-buff-oper;

  import cisco-semver {
    prefix semver;
  }
  import Cisco-IOS-XR-platforms-ofa-oper {
    prefix a1;
  }

  include Cisco-IOS-XR-8000-platforms-npu-evict-voq-buff-oper-sub1 {
    revision-date 2019-04-05;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR 8000-platforms-npu-evict-voq-buff package operational data.

     This YANG module augments the
       Cisco-IOS-XR-platforms-ofa-oper
     module with state data.

     Copyright (c) 2013-2019 by Cisco Systems, Inc.
     All rights reserved.";

  revision 2019-04-05 {
    semver:module-version "1.0.0";
    description
      "Establish semantic version baseline.";
  }
  revision 2015-11-09 {
    description
      "IOS XR 6.0 revision.";
  }

  augment "/a1:ofa/a1:stats/a1:nodes/a1:node" {
    description
      "This augment extends the operational data of
       'Cisco-IOS-XR-platforms-ofa-oper'";
    container evic-voq-buff-instances {
      description
        "Evic Voq Buff usage";
      list evic-voq-buff-instance {
        key "npu-id";
        description
          "Instance ID";
        container latest {
          description
            "Latest";
          uses OFA-SYSDB-EVICT-VOQ-BUFF-USAGE-ARRAY-ST;
        }
        leaf npu-id {
          type uint32;
          description
            "EvicVoqBuffInstance";
        }
        uses OFA-SYSDB-EVICT-VOQ-BUFF-USAGE-ARRAY-ST;
      }
    }
  }
}
