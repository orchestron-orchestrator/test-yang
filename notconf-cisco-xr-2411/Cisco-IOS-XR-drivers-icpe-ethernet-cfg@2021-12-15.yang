module Cisco-IOS-XR-drivers-icpe-ethernet-cfg {
  namespace "http://cisco.com/ns/yang/Cisco-IOS-XR-drivers-icpe-ethernet-cfg";
  prefix drivers-icpe-ethernet-cfg;

  import Cisco-IOS-XR-types {
    prefix xr;
  }
  import cisco-semver {
    prefix semver;
  }
  import Cisco-IOS-XR-ifmgr-cfg {
    prefix a1;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR drivers-icpe-ethernet package configuration.

     This YANG module augments the
       Cisco-IOS-XR-ifmgr-cfg
     module with configuration data.

     Copyright (c) 2013-2021 by Cisco Systems, Inc.
     All rights reserved.";

  revision 2021-12-15 {
    semver:module-version "1.1.0";
    description
      "PRBS configuration added
       2021-10-07
         Insert Idle support added for ethernet controllers.";
  }
  revision 2019-04-05 {
    semver:module-version "1.0.0";
    description
      "Establish semantic version baseline.";
  }
  revision 2015-11-09 {
    description
      "IOS XR 6.0 revision.";
  }

  typedef Eth-ctrlr-prbs-mode {
    type enumeration {
      enum "source" {
        value 1;
        description
          "source mode";
      }
      enum "sink" {
        value 2;
        description
          "sink mode";
      }
      enum "source-sink" {
        value 3;
        description
          "source-sink mode";
      }
    }
    description
      "Eth ctrlr prbs mode";
  }

  typedef Eth-ctrlr-prbs-framing {
    type enumeration {
      enum "none" {
        value 0;
        description
          "No framing config";
      }
      enum "unframed" {
        value 1;
        description
          "unframed PRBS";
      }
      enum "framed" {
        value 2;
        description
          "framed PRBS";
      }
    }
    description
      "Eth ctrlr prbs framing";
  }

  typedef Eth-ctrlr-prbs-error {
    type enumeration {
      enum "none" {
        value 0;
        description
          "No error-inject config";
      }
      enum "single" {
        value 1;
        description
          "Inject error once";
      }
      enum "continuous" {
        value 2;
        description
          "Inject error continuously";
      }
    }
    description
      "Eth ctrlr prbs error";
  }

  typedef Extended-ethernet-loopback {
    type enumeration {
      enum "internal" {
        value 1;
        description
          "Internal loopback";
      }
      enum "line" {
        value 2;
        description
          "Line loopback";
      }
    }
    description
      "Extended ethernet loopback";
  }

  typedef Eth-ctrlr-prbs-direction {
    type enumeration {
      enum "none" {
        value 0;
        description
          "No direction config";
      }
      enum "line" {
        value 1;
        description
          "PRBS towards line side";
      }
      enum "system" {
        value 2;
        description
          "PRBS towards system side";
      }
    }
    description
      "Eth ctrlr prbs direction";
  }

  typedef Eth-ctrlr-prbs-pattern {
    type enumeration {
      enum "pn7" {
        value 1;
        description
          "pattern pn7";
      }
      enum "pn9" {
        value 2;
        description
          "pattern pn9";
      }
      enum "pn11" {
        value 3;
        description
          "pattern pn11";
      }
      enum "pn15" {
        value 4;
        description
          "pattern pn15";
      }
      enum "pn23" {
        value 5;
        description
          "pattern pn23";
      }
      enum "pn31" {
        value 6;
        description
          "pattern pn31";
      }
      enum "user-defined" {
        value 7;
        description
          "user-defined pattern(64-bit hex value)";
      }
    }
    description
      "Eth ctrlr prbs pattern";
  }

  augment "/a1:interface-configurations/a1:interface-configuration" {
    description
      "This augment extends the configuration data of
       'Cisco-IOS-XR-ifmgr-cfg'";
    leaf laser-squelch {
      type empty;
      description
        "Configure Laser-Squelch";
    }
  }
  augment "/a1:interface-configurations/a1:interface-configuration" {
    description
      "This augment extends the configuration data of
       'Cisco-IOS-XR-ifmgr-cfg'";
    leaf holdoff-time {
      type uint32 {
        range "0..3000";
      }
      description
        "Configure Holdoff Time";
    }
  }
  augment "/a1:interface-configurations/a1:interface-configuration" {
    description
      "This augment extends the configuration data of
       'Cisco-IOS-XR-ifmgr-cfg'";
    leaf insert-idle-egress {
      type empty;
      description
        "Configure insert idle egress support";
    }
  }
  augment "/a1:interface-configurations/a1:interface-configuration" {
    description
      "This augment extends the configuration data of
       'Cisco-IOS-XR-ifmgr-cfg'";
    container loopbacks {
      description
        "Configure Extended loopback (diagnostics)";
      list loopback {
        key "level";
        description
          "Configure extended loopback mode";
        leaf level {
          type uint32 {
            range "1..3";
          }
          description
            "Level";
        }
        leaf loopback {
          type Extended-ethernet-loopback;
          mandatory true;
          description
            "Loopback";
        }
      }
    }
  }
  augment "/a1:interface-configurations/a1:interface-configuration" {
    description
      "This augment extends the configuration data of
       'Cisco-IOS-XR-ifmgr-cfg'";
    leaf insert-idle-ingress {
      type empty;
      description
        "Configure insert idle ingress support";
    }
  }
  augment "/a1:interface-configurations/a1:interface-configuration" {
    description
      "This augment extends the configuration data of
       'Cisco-IOS-XR-ifmgr-cfg'";
    leaf perf-mon-disable {
      type empty;
      description
        "Configure Performance Monitoring ";
    }
  }
  augment "/a1:interface-configurations/a1:interface-configuration" {
    description
      "This augment extends the configuration data of
       'Cisco-IOS-XR-ifmgr-cfg'";
    container prbs {
      presence "Indicates a prbs node is configured.";
      description
        "Configure Pseudo Random Binary Sequence Test";
      leaf mode {
        type Eth-ctrlr-prbs-mode;
        mandatory true;
        description
          "PRBS Mode";
      }
      leaf pattern {
        type Eth-ctrlr-prbs-pattern;
        mandatory true;
        description
          "PRBS pattern";
      }
      leaf direction {
        type Eth-ctrlr-prbs-direction;
        description
          "PRBS direction";
      }
      leaf error {
        type Eth-ctrlr-prbs-error;
        description
          "PRBS error inject type";
      }
      leaf framing {
        type Eth-ctrlr-prbs-framing;
        description
          "PRBS framing type";
      }
      leaf user-pattern {
        type xr:Hex-long-integer;
        description
          "PRBS user defined pattern(64-bit hex value)";
      }
    }
  }
}
