module Cisco-IOS-XR-sysadmin-ethsw-esdma-trace {
  namespace "http://www.cisco.com/ns/yang/Cisco-IOS-XR-sysadmin-ethsw-esdma-trace";
  prefix esdma_trace;

  import Cisco-IOS-XR-sysadmin-show-trace {
    prefix show_trace;
  }
  import cisco-semver {
    prefix semver;
  }

  organization
    "Cisco Systems Inc.";
  contact
    "Cisco Systems, Inc.
     Customer Service

     Postal: 170 West Tasman Drive
     San Jose, CA 95134

     Tel: +1 800 553-NETS

     E-mail: cs-yang@cisco.com";
  description
    "This module contains the YANG definitions
     for the Cisco IOS-XR SysAdmin
     'show controller switch trace' commands.

     Copyright (c) 2011-2020 by Cisco Systems, Inc.
     All rights reserved.";

  revision 2019-04-15 {
    semver:module-version "1.0.0";
    description
      "Establish semantic version baseline.";
  }
  revision 2017-05-01 {
    description
      "Namespace change to comply with Cisco guidelines on namespace";
  }
  revision 2016-07-06 {
    description
      "Initial revision with content extracted from esdma_cli.yang.";
  }

  grouping esd-ctrace {
    container esd {
      uses show_trace:traceable_process;
    }
  }

  grouping esd-ctrace-ncs5500 {
    container trace {
      list location {
        key "location_str";
        leaf location_str {
          type string;
        }
        container esd {
          uses show_trace:traceable_with_keypath_location;
        }
        container esd-EPC-SW {
          uses show_trace:traceable_with_keypath_location;
        }
        container esd-EOBC-SW {
          uses show_trace:traceable_with_keypath_location;
        }
      }
    }
  }

  grouping esdma-ctrace {
    container esdma {
      uses show_trace:traceable;
    }
  }
}
