module Cisco-IOS-XR-sysadmin-led-mgr-ui {
  namespace "http://www.cisco.com/ns/yang/Cisco-IOS-XR-sysadmin-led-mgr-ui";
  prefix led_mgr;

  import Cisco-IOS-XR-sysadmin-show-trace {
    prefix show_trace;
  }
  import cisco-semver {
    prefix semver;
  }

  organization
    "Cisco Systems Inc.";
  contact
    "Cisco Systems, Inc.
     Customer Service

     Postal: 170 West Tasman Drive
     San Jose, CA 95134

     Tel: +1 800 553-NETS

     E-mail: cs-yang@cisco.com";
  description
    "This module provides CLI for Status, ATTN, ALARM LED's.

     Copyright (c) 2012-2020 by Cisco Systems, Inc.
     All rights reserved.";

  revision 2021-02-05 {
    semver:module-version "2.0.0";
    description
      "Adding support for Bay3 attention LED configuration";
  }
  revision 2019-04-15 {
    semver:module-version "1.0.0";
    description
      "Establish semantic version baseline.";
  }
  revision 2017-05-01 {
    description
      "Namespace change to comply with Cisco guidelines on namespace";
  }
  revision 2012-03-25 {
    description
      "changed leds to location, and added all";
  }
  revision 2012-03-15 {
    description
      "Initial revision of led commands, march 25 changed leds to
         location";
  }

  grouping hw-module-config-group {
    uses hw-module-attention-led-config-group;
  }

  grouping hw-module-attention-led-config-group {
    container attention-led {
      list location {
        key "location";
        leaf location {
          type string {
            pattern "([0-255])|((0?[0-9]|1[0-5])/(FC(0?[0-5])))|((0?[0-9]|1[0-5])/(RP(0?[0-1])))|((0?[0-9]|1[0-5])/(0?[0-9]|1[0-5])(/[1-3])?)|((F[0-3])/(FC(0?[0-9]|1[0-1])))|((F[0-3])/(SC(0?[0-1])))|(0?[0-9]/(SC(0?[0-1])))|(0?[0-9]/(FT(0?[0-2])))|(0?[0-9]/(PM(0?[0-9])))";
          }
          mandatory true;
        }
      }
    }
  }

  container led {
    config false;
    description
      "Calvados Led Manager Status, Attn, Alarm inventory";
    list location {
      key "location";
      leaf location {
        type string;
      }
      list led_attributes {
        key "led_name";
        leaf location {
          type string;
        }
        leaf print_header {
          type boolean;
          default "false";
        }
        leaf loc_header {
          type boolean;
          default "false";
        }
        leaf led_name {
          type string;
        }
        leaf led_mode {
          type string;
        }
        leaf led_color {
          type string;
        }
      }
    }
    uses show_trace:traceable;
  }
}
