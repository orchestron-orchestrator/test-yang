module Cisco-IOS-XR-infra-correlator-oper {
  namespace "http://cisco.com/ns/yang/Cisco-IOS-XR-infra-correlator-oper";
  prefix infra-correlator-oper;

  import cisco-semver {
    prefix semver;
  }

  include Cisco-IOS-XR-infra-correlator-oper-sub1 {
    revision-date 2019-04-05;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR infra-correlator package operational data.

     This module contains definitions
     for the following management objects:
       suppression: Suppression operational data
       correlator: Correlator operational data

     Copyright (c) 2013-2019 by Cisco Systems, Inc.
     All rights reserved.";

  revision 2019-04-05 {
    semver:module-version "1.0.1";
    description
      "Establish semantic version baseline.";
  }
  revision 2017-09-07 {
    description
      "Fixed type translation error.";
  }
  revision 2017-05-01 {
    description
      "Fixing backward compatibility error in module.";
  }
  revision 2015-11-09 {
    description
      "IOS XR 6.0 revision.";
  }

  container suppression {
    config false;
    description
      "Suppression operational data";
    container rule-summaries {
      description
        "Table that contains the database of suppression
         rule summary";
      list rule-summary {
        key "rule-name";
        description
          "One of the suppression rules";
        leaf rule-name {
          type string {
            length "1..32";
          }
          description
            "Suppression Rule Name";
        }
        uses AC-SUPPR-RULE-SUMMARY-BAG;
      }
    }
    container rule-details {
      description
        "Table that contains the database of suppression
         rule details";
      list rule-detail {
        key "rule-name";
        description
          "Details of one of the suppression rules";
        leaf rule-name {
          type string {
            length "1..32";
          }
          description
            "Suppression Rule Name";
        }
        uses AC-SUPPR-RULE-DETAIL-BAG;
      }
    }
  }
  container correlator {
    config false;
    description
      "Correlator operational data";
    container rules {
      description
        "Table that contains the database of correlation
         rules";
      list rule {
        key "rule-name";
        description
          "One of the correlation rules";
        leaf rule-name {
          type string {
            length "1..32";
          }
          description
            "Correlation Rule Name";
        }
        uses AC-RULE-INFO-BAG;
      }
    }
    container buffer-status {
      description
        "Describes buffer utilization and parameters
         configured";
      uses AC-BUFFER-INFO-BAG;
    }
    container alarms {
      description
        "Correlated alarms Table";
      list alarm {
        key "alarm-id";
        description
          "One of the correlated alarms";
        leaf alarm-id {
          type uint32;
          description
            "Alarm ID";
        }
        uses AC-ALDEMS-ALARM-BAG;
      }
    }
    container rule-set-summaries {
      description
        "Table that contains the ruleset summary info";
      list rule-set-summary {
        key "rule-set-name";
        description
          "Summary of one of the correlation rulesets";
        leaf rule-set-name {
          type string {
            length "1..32";
          }
          description
            "Ruleset Name";
        }
        uses AC-RULESET-SUMMARY-BAG;
      }
    }
    container rule-set-details {
      description
        "Table that contains the ruleset detail info";
      list rule-set-detail {
        key "rule-set-name";
        description
          "Detail of one of the correlation rulesets";
        leaf rule-set-name {
          type string {
            length "1..32";
          }
          description
            "Ruleset Name";
        }
        uses AC-RULESET-DETAIL-BAG;
      }
    }
    container rule-details {
      description
        "Table that contains the database of correlation
         rule details";
      list rule-detail {
        key "rule-name";
        description
          "Details of one of the correlation rules";
        leaf rule-name {
          type string {
            length "1..32";
          }
          description
            "Correlation Rule Name";
        }
        uses AC-RULE-DETAIL-BAG;
      }
    }
    container rule-summaries {
      description
        "Table that contains the database of correlation
         rule summary";
      list rule-summary {
        key "rule-name";
        description
          "One of the correlation rules";
        leaf rule-name {
          type string {
            length "1..32";
          }
          description
            "Correlation Rule Name";
        }
        uses AC-RULE-SUMMARY-BAG;
      }
    }
  }
}
