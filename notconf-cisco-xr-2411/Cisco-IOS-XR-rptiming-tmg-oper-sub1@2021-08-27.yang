submodule Cisco-IOS-XR-rptiming-tmg-oper-sub1 {
  belongs-to Cisco-IOS-XR-rptiming-tmg-oper {
    prefix Cisco-IOS-XR-rptiming-tmg-oper;
  }

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR rptiming-tmg package operational data.

     Copyright (c) 2013-2021 by Cisco Systems, Inc.
     All rights reserved.";

  revision 2021-08-27 {
    semver:module-version "1.2.0";
    description
      "led and utc-offset values added for yang";
  }
  revision 2019-11-24 {
    semver:module-version "1.0.0";
    description
      "Added Yang support for LED Information.";
  }
  revision 2019-04-05 {
    description
      "Establish semantic version baseline.";
  }
  revision 2015-11-09 {
    description
      "IOS XR 6.0 revision.";
  }

  grouping TMG-TOD-INFO {
    description
      "Timing ToD status";
    leaf secs {
      type uint64;
      units "second";
      description
        "ToD Seconds";
    }
    leaf nanosecs {
      type uint32;
      units "nanosecond";
      description
        "ToD Nanoseconds";
    }
    leaf ut-coffset {
      type uint32;
      description
        "UTC offset from TAI";
    }
  }

  grouping TMG-LED-INFO {
    description
      "Timing LED status";
    leaf bits0-led {
      type uint32;
      description
        "BITS0 LED";
    }
    leaf bits1-led {
      type uint32;
      description
        "BITS1 LED";
    }
    leaf gps-led {
      type uint32;
      description
        "GPS LED";
    }
    leaf sync-led {
      type uint32;
      description
        "Sync LED";
    }
    leaf gnss-led {
      type uint32;
      description
        "GNSS LED";
    }
  }

  grouping TMG-PLL-DUMP {
    description
      "Timing PLL dump";
    leaf chip-id {
      type uint32;
      description
        "SETS Chip ID";
    }
    leaf chip-ver {
      type uint32;
      description
        "SETS Chip Version";
    }
    leaf dpll0-bandwidth {
      type string {
        length "0..50";
      }
      description
        "DPLL0 Bandwidth";
    }
    leaf dpll0-psl {
      type string {
        length "0..50";
      }
      description
        "DPLL0 PSL";
    }
    leaf dpll0-mode {
      type string {
        length "0..50";
      }
      description
        "DPLL0 Mode";
    }
    leaf dpll0-select {
      type string {
        length "0..50";
      }
      description
        "DPLL0 Input Selected";
    }
    leaf dpll0-holdover {
      type string {
        length "0..50";
      }
      description
        "DPLL0 Holdover Status";
    }
    leaf dpll0-lock {
      type string {
        length "0..50";
      }
      description
        "DPLL0 Lock Status";
    }
    leaf dpll1-bandwidth {
      type string {
        length "0..50";
      }
      description
        "DPLL1 Bandwidth";
    }
    leaf dpll1-psl {
      type string {
        length "0..50";
      }
      description
        "DPLL1 PSL";
    }
    leaf dpll1-mode {
      type string {
        length "0..50";
      }
      description
        "DPLL1 Mode";
    }
    leaf dpll1-select {
      type string {
        length "0..50";
      }
      description
        "DPLL1 Input Selected";
    }
    leaf dpll1-holdover {
      type string {
        length "0..50";
      }
      description
        "DPLL1 Holdover Status";
    }
    leaf dpll1-lock {
      type string {
        length "0..50";
      }
      description
        "DPLL1 Lock Status";
    }
    leaf dpll2-bandwidth {
      type string {
        length "0..50";
      }
      description
        "DPLL2 Bandwidth";
    }
    leaf dpll2-psl {
      type string {
        length "0..50";
      }
      description
        "DPLL2 PSL";
    }
    leaf dpll2-mode {
      type string {
        length "0..50";
      }
      description
        "DPLL2 Mode";
    }
    leaf dpll2-select {
      type string {
        length "0..50";
      }
      description
        "DPLL2 Input Selected";
    }
    leaf dpll2-holdover {
      type string {
        length "0..50";
      }
      description
        "DPLL2 Holdover Status";
    }
    leaf dpll2-lock {
      type string {
        length "0..50";
      }
      description
        "DPLL2 Lock Status";
    }
    leaf ref0-status {
      type string {
        length "0..50";
      }
      description
        "Ref0 Status";
    }
    leaf ref1-status {
      type string {
        length "0..50";
      }
      description
        "Ref1 Status";
    }
    leaf ref2-status {
      type string {
        length "0..50";
      }
      description
        "Ref2 Status";
    }
    leaf ref3-status {
      type string {
        length "0..50";
      }
      description
        "Ref3 Status";
    }
    leaf ref4-status {
      type string {
        length "0..50";
      }
      description
        "Ref4 Status";
    }
    leaf ref5-status {
      type string {
        length "0..50";
      }
      description
        "Ref5 Status";
    }
    leaf ref6-status {
      type string {
        length "0..50";
      }
      description
        "Ref6 Status";
    }
    leaf ref7-status {
      type string {
        length "0..50";
      }
      description
        "Ref7 Status";
    }
    leaf ref8-status {
      type string {
        length "0..50";
      }
      description
        "Ref8 Status";
    }
    leaf ref9-status {
      type string {
        length "0..50";
      }
      description
        "Ref9 Status";
    }
    leaf ref10-status {
      type string {
        length "0..50";
      }
      description
        "Ref10 Status";
    }
    leaf ref0-freq {
      type string {
        length "0..50";
      }
      description
        "Ref0 Frequency";
    }
    leaf ref1-freq {
      type string {
        length "0..50";
      }
      description
        "Ref1 Frequency";
    }
    leaf ref2-freq {
      type string {
        length "0..50";
      }
      description
        "Ref2 Frequency";
    }
    leaf ref3-freq {
      type string {
        length "0..50";
      }
      description
        "Ref3 Frequency";
    }
    leaf ref4-freq {
      type string {
        length "0..50";
      }
      description
        "Ref4 Frequency";
    }
    leaf ref5-freq {
      type string {
        length "0..50";
      }
      description
        "Ref5 Frequency";
    }
    leaf ref6-freq {
      type string {
        length "0..50";
      }
      description
        "Ref6 Frequency";
    }
    leaf ref7-freq {
      type string {
        length "0..50";
      }
      description
        "Ref7 Frequency";
    }
    leaf ref8-freq {
      type string {
        length "0..50";
      }
      description
        "Ref8 Frequency";
    }
    leaf ref9-freq {
      type string {
        length "0..50";
      }
      description
        "Ref9 Frequency";
    }
    leaf ref10-freq {
      type string {
        length "0..50";
      }
      description
        "Ref10 Frequency";
    }
    list set-dump {
      max-elements 2048;
      description
        "Sets dumps";
      leaf entry {
        type uint32;
        description
          "Sets dumps";
      }
    }
    list dpll0-prio {
      max-elements 11;
      description
        "Dpll0 ref inputs";
      leaf entry {
        type uint32;
        description
          "Dpll0 ref inputs";
      }
    }
    list dpll1-prio {
      max-elements 11;
      description
        "Dpll1 ref inputs";
      leaf entry {
        type uint32;
        description
          "Dpll1 ref inputs";
      }
    }
    list dpll2-prio {
      max-elements 11;
      description
        "Dpll2 ref inputs";
      leaf entry {
        type uint32;
        description
          "Dpll2 ref inputs";
      }
    }
  }

  grouping TMG-CLKIN-INFO {
    description
      "Timing input clock status";
    leaf ic1-valid {
      type boolean;
      description
        "IC Valid 1";
    }
    leaf ic2-valid {
      type boolean;
      description
        "IC Valid 2";
    }
    leaf ic3-valid {
      type boolean;
      description
        "IC Valid 3";
    }
    leaf ic4-valid {
      type boolean;
      description
        "IC Valid 4";
    }
    leaf ic5-valid {
      type boolean;
      description
        "IC Valid 5";
    }
    leaf ic6-valid {
      type boolean;
      description
        "IC Valid 6";
    }
    leaf ic7-valid {
      type boolean;
      description
        "IC Valid 7";
    }
    leaf ic8-valid {
      type boolean;
      description
        "IC Valid 8";
    }
    leaf ic9-valid {
      type boolean;
      description
        "IC Valid 9";
    }
    leaf ic10-valid {
      type boolean;
      description
        "IC Valid 10";
    }
    leaf ic11-valid {
      type boolean;
      description
        "IC Valid 11";
    }
    leaf ic1-slot {
      type string {
        length "0..50";
      }
      description
        "IC Slot 1";
    }
    leaf ic2-slot {
      type string {
        length "0..50";
      }
      description
        "IC Slot 2";
    }
    leaf ic3-slot {
      type string {
        length "0..50";
      }
      description
        "IC Slot 3";
    }
    leaf ic4-slot {
      type string {
        length "0..50";
      }
      description
        "IC Slot 4";
    }
    leaf ic5-slot {
      type string {
        length "0..50";
      }
      description
        "IC Slot 5";
    }
    leaf ic6-slot {
      type string {
        length "0..50";
      }
      description
        "IC Slot 6";
    }
    leaf ic7-slot {
      type string {
        length "0..50";
      }
      description
        "IC Slot 7";
    }
    leaf ic8-slot {
      type string {
        length "0..50";
      }
      description
        "IC Slot 8";
    }
    leaf ic9-slot {
      type string {
        length "0..50";
      }
      description
        "IC Slot 9";
    }
    leaf ic10-slot {
      type string {
        length "0..50";
      }
      description
        "IC Slot 10";
    }
    leaf ic11-slot {
      type string {
        length "0..50";
      }
      description
        "IC Slot 11";
    }
    leaf ic1-split-xom {
      type string {
        length "0..50";
      }
      description
        "IC1 Split XO Mode Status";
    }
    leaf ic2-split-xom {
      type string {
        length "0..50";
      }
      description
        "IC2 Split XO Mode Status";
    }
    leaf ic3-split-xom {
      type string {
        length "0..50";
      }
      description
        "IC3 Split XO Mode Status";
    }
    leaf ic4-split-xom {
      type string {
        length "0..50";
      }
      description
        "IC4 Split XO Mode Status";
    }
    leaf ic5-split-xom {
      type string {
        length "0..50";
      }
      description
        "IC5 Split XO Mode Status";
    }
    leaf ic6-split-xom {
      type string {
        length "0..50";
      }
      description
        "IC6 Split XO Mode Status";
    }
    leaf ic7-split-xom {
      type string {
        length "0..50";
      }
      description
        "IC7 Split XO Mode Status";
    }
    leaf ic8-split-xom {
      type string {
        length "0..50";
      }
      description
        "IC8 Split XO Mode Status";
    }
    leaf ic9-split-xom {
      type string {
        length "0..50";
      }
      description
        "IC9 Split XO Mode Status";
    }
    leaf ic10-split-xom {
      type string {
        length "0..50";
      }
      description
        "IC10 Split XO Mode Status";
    }
    leaf ic11-split-xom {
      type string {
        length "0..50";
      }
      description
        "IC11 Split XO Mode Status";
    }
    leaf ic1-eppsm {
      type string {
        length "0..50";
      }
      description
        "IC1 ePPSM Status";
    }
    leaf ic2-eppsm {
      type string {
        length "0..50";
      }
      description
        "IC2 ePPSM Status";
    }
    leaf ic3-eppsm {
      type string {
        length "0..50";
      }
      description
        "IC3 ePPSM Status";
    }
    leaf ic4-eppsm {
      type string {
        length "0..50";
      }
      description
        "IC4 ePPSM Status";
    }
    leaf ic5-eppsm {
      type string {
        length "0..50";
      }
      description
        "IC5 ePPSM Status";
    }
    leaf ic6-eppsm {
      type string {
        length "0..50";
      }
      description
        "IC6 ePPSM Status";
    }
    leaf ic7-eppsm {
      type string {
        length "0..50";
      }
      description
        "IC7 ePPSM Status";
    }
    leaf ic8-eppsm {
      type string {
        length "0..50";
      }
      description
        "IC8 ePPSM Status";
    }
    leaf ic9-eppsm {
      type string {
        length "0..50";
      }
      description
        "IC9 ePPSM Status";
    }
    leaf ic10-eppsm {
      type string {
        length "0..50";
      }
      description
        "IC10 ePPSM Status";
    }
    leaf ic11-eppsm {
      type string {
        length "0..50";
      }
      description
        "IC11 ePPSM Status";
    }
    leaf ic1-pfm {
      type string {
        length "0..50";
      }
      description
        "IC1 PFM Status";
    }
    leaf ic2-pfm {
      type string {
        length "0..50";
      }
      description
        "IC2 PFM Status";
    }
    leaf ic3-pfm {
      type string {
        length "0..50";
      }
      description
        "IC3 PFM Status";
    }
    leaf ic4-pfm {
      type string {
        length "0..50";
      }
      description
        "IC4 PFM Status";
    }
    leaf ic5-pfm {
      type string {
        length "0..50";
      }
      description
        "IC5 PFM Status";
    }
    leaf ic6-pfm {
      type string {
        length "0..50";
      }
      description
        "IC6 PFM Status";
    }
    leaf ic7-pfm {
      type string {
        length "0..50";
      }
      description
        "IC7 PFM Status";
    }
    leaf ic8-pfm {
      type string {
        length "0..50";
      }
      description
        "IC8 PFM Status";
    }
    leaf ic9-pfm {
      type string {
        length "0..50";
      }
      description
        "IC9 PFM Status";
    }
    leaf ic10-pfm {
      type string {
        length "0..50";
      }
      description
        "IC10 PFM Status";
    }
    leaf ic11-pfm {
      type string {
        length "0..50";
      }
      description
        "IC11 PFM Status";
    }
    leaf ic1-gst {
      type string {
        length "0..50";
      }
      description
        "IC1 GST Status";
    }
    leaf ic2-gst {
      type string {
        length "0..50";
      }
      description
        "IC2 GST Status";
    }
    leaf ic3-gst {
      type string {
        length "0..50";
      }
      description
        "IC3 GST Status";
    }
    leaf ic4-gst {
      type string {
        length "0..50";
      }
      description
        "IC4 GST Status";
    }
    leaf ic5-gst {
      type string {
        length "0..50";
      }
      description
        "IC5 GST Status";
    }
    leaf ic6-gst {
      type string {
        length "0..50";
      }
      description
        "IC6 GST Status";
    }
    leaf ic7-gst {
      type string {
        length "0..50";
      }
      description
        "IC7 GST Status";
    }
    leaf ic8-gst {
      type string {
        length "0..50";
      }
      description
        "IC8 GST Status";
    }
    leaf ic9-gst {
      type string {
        length "0..50";
      }
      description
        "IC9 GST Status";
    }
    leaf ic10-gst {
      type string {
        length "0..50";
      }
      description
        "IC10 GST Status";
    }
    leaf ic11-gst {
      type string {
        length "0..50";
      }
      description
        "IC11 GST Status";
    }
    leaf ic1-cfm {
      type string {
        length "0..50";
      }
      description
        "IC1 CFM Status";
    }
    leaf ic2-cfm {
      type string {
        length "0..50";
      }
      description
        "IC2 CFM Status";
    }
    leaf ic3-cfm {
      type string {
        length "0..50";
      }
      description
        "IC3 CFM Status";
    }
    leaf ic4-cfm {
      type string {
        length "0..50";
      }
      description
        "IC4 CFM Status";
    }
    leaf ic5-cfm {
      type string {
        length "0..50";
      }
      description
        "IC5 CFM Status";
    }
    leaf ic6-cfm {
      type string {
        length "0..50";
      }
      description
        "IC6 CFM Status";
    }
    leaf ic7-cfm {
      type string {
        length "0..50";
      }
      description
        "IC7 CFM Status";
    }
    leaf ic8-cfm {
      type string {
        length "0..50";
      }
      description
        "IC8 CFM Status";
    }
    leaf ic9-cfm {
      type string {
        length "0..50";
      }
      description
        "IC9 CFM Status";
    }
    leaf ic10-cfm {
      type string {
        length "0..50";
      }
      description
        "IC10 CFM Status";
    }
    leaf ic11-cfm {
      type string {
        length "0..50";
      }
      description
        "IC11 CFM Status";
    }
    leaf ic1-scm {
      type string {
        length "0..50";
      }
      description
        "IC1 SCM Status";
    }
    leaf ic2-scm {
      type string {
        length "0..50";
      }
      description
        "IC2 SCM Status";
    }
    leaf ic3-scm {
      type string {
        length "0..50";
      }
      description
        "IC3 SCM Status";
    }
    leaf ic4-scm {
      type string {
        length "0..50";
      }
      description
        "IC4 SCM Status";
    }
    leaf ic5-scm {
      type string {
        length "0..50";
      }
      description
        "IC5 SCM Status";
    }
    leaf ic6-scm {
      type string {
        length "0..50";
      }
      description
        "IC6 SCM Status";
    }
    leaf ic7-scm {
      type string {
        length "0..50";
      }
      description
        "IC7 SCM Status";
    }
    leaf ic8-scm {
      type string {
        length "0..50";
      }
      description
        "IC8 SCM Status";
    }
    leaf ic9-scm {
      type string {
        length "0..50";
      }
      description
        "IC9 SCM Status";
    }
    leaf ic10-scm {
      type string {
        length "0..50";
      }
      description
        "IC10 SCM Status";
    }
    leaf ic11-scm {
      type string {
        length "0..50";
      }
      description
        "IC11 SCM Status";
    }
    leaf ic1-los {
      type string {
        length "0..50";
      }
      description
        "IC1 LOS Status";
    }
    leaf ic2-los {
      type string {
        length "0..50";
      }
      description
        "IC2 LOS Status";
    }
    leaf ic3-los {
      type string {
        length "0..50";
      }
      description
        "IC3 LOS Status";
    }
    leaf ic4-los {
      type string {
        length "0..50";
      }
      description
        "IC4 LOS Status";
    }
    leaf ic5-los {
      type string {
        length "0..50";
      }
      description
        "IC5 LOS Status";
    }
    leaf ic6-los {
      type string {
        length "0..50";
      }
      description
        "IC6 LOS Status";
    }
    leaf ic7-los {
      type string {
        length "0..50";
      }
      description
        "IC7 LOS Status";
    }
    leaf ic8-los {
      type string {
        length "0..50";
      }
      description
        "IC8 LOS Status";
    }
    leaf ic9-los {
      type string {
        length "0..50";
      }
      description
        "IC9 LOS Status";
    }
    leaf ic10-los {
      type string {
        length "0..50";
      }
      description
        "IC10 LOS Status";
    }
    leaf ic11-los {
      type string {
        length "0..50";
      }
      description
        "IC11 LOS Status";
    }
    leaf ffo-data-present {
      type boolean;
      description
        "Whether bag has FFO data";
    }
    leaf ic1-ffo {
      type string {
        length "0..50";
      }
      description
        "IC1 Fractional freq offset";
    }
    leaf ic2-ffo {
      type string {
        length "0..50";
      }
      description
        "IC2 Fractional freq offset";
    }
    leaf ic3-ffo {
      type string {
        length "0..50";
      }
      description
        "IC3 Fractional freq offset";
    }
    leaf ic4-ffo {
      type string {
        length "0..50";
      }
      description
        "IC4 Fractional freq offset";
    }
    leaf ic5-ffo {
      type string {
        length "0..50";
      }
      description
        "IC5 Fractional freq offset";
    }
    leaf ic6-ffo {
      type string {
        length "0..50";
      }
      description
        "IC6 Fractional freq offset";
    }
    leaf ic7-ffo {
      type string {
        length "0..50";
      }
      description
        "IC7 Fractional freq offset";
    }
    leaf ic8-ffo {
      type string {
        length "0..50";
      }
      description
        "IC8 Fractional freq offset";
    }
    leaf ic9-ffo {
      type string {
        length "0..50";
      }
      description
        "IC9 Fractional freq offset";
    }
    leaf ic10-ffo {
      type string {
        length "0..50";
      }
      description
        "IC10 Fractional freq offset";
    }
    leaf ic11-ffo {
      type string {
        length "0..50";
      }
      description
        "IC11 Fractional freq offset";
    }
  }

  grouping TMG-PLL-INFO {
    description
      "Timing PLL status";
    leaf pll0-present {
      type boolean;
      description
        "PLL0 present";
    }
    leaf pll1-present {
      type boolean;
      description
        "PLL1 present";
    }
    leaf pll2-present {
      type boolean;
      description
        "PLL2 present";
    }
    leaf t4-spll {
      type uint8;
      description
        "T4 SPLL";
    }
    leaf pll0-name {
      type string {
        length "0..50";
      }
      description
        "PLL0 name";
    }
    leaf pll1-name {
      type string {
        length "0..50";
      }
      description
        "PLL1 name";
    }
    leaf pll2-name {
      type string {
        length "0..50";
      }
      description
        "PLL2 name";
    }
    leaf pll0-state {
      type string {
        length "0..50";
      }
      description
        "PLL0 state";
    }
    leaf pll1-state {
      type string {
        length "0..50";
      }
      description
        "PLL1 state";
    }
    leaf pll2-state {
      type string {
        length "0..50";
      }
      description
        "PLL2 state";
    }
    leaf pll0-selected {
      type string {
        length "0..50";
      }
      description
        "PLL0 selected";
    }
    leaf pll1-selected {
      type string {
        length "0..50";
      }
      description
        "PLL1 selected";
    }
    leaf pll2-selected {
      type string {
        length "0..50";
      }
      description
        "PLL2 selected";
    }
    leaf pll0-pll-mode {
      type string {
        length "0..50";
      }
      description
        "PLL0 PLL mode";
    }
    leaf pll2-pll-mode {
      type string {
        length "0..50";
      }
      description
        "PLL2 PLL mode";
    }
    leaf pll1-pll-mode {
      type string {
        length "0..50";
      }
      description
        "PLL1 PLL mode";
    }
    leaf pll0-pll-ic1-prio {
      type uint8;
      description
        "PLL0 PLL IC1 Priority";
    }
    leaf pll0-pll-ic2-prio {
      type uint8;
      description
        "PLL0 PLL IC2 Priority";
    }
    leaf pll0-pll-ic3-prio {
      type uint8;
      description
        "PLL0 PLL IC3 Priority";
    }
    leaf pll0-pll-ic4-prio {
      type uint8;
      description
        "PLL0 PLL IC4 Priority";
    }
    leaf pll0-pll-ic5-prio {
      type uint8;
      description
        "PLL0 PLL IC5 Priority";
    }
    leaf pll0-pll-ic6-prio {
      type uint8;
      description
        "PLL0 PLL IC6 Priority";
    }
    leaf pll0-pll-ic7-prio {
      type uint8;
      description
        "PLL0 PLL IC7 Priority";
    }
    leaf pll0-pll-ic8-prio {
      type uint8;
      description
        "PLL0 PLL IC8 Priority";
    }
    leaf pll0-pll-ic9-prio {
      type uint8;
      description
        "PLL0 PLL IC9 Priority";
    }
    leaf pll0-pll-ic10-prio {
      type uint8;
      description
        "PLL0 PLL IC10 Priority";
    }
    leaf pll0-pll-ic11-prio {
      type uint8;
      description
        "PLL0 PLL IC11 Priority";
    }
    leaf pll2-pll-ic1-prio {
      type uint8;
      description
        "PLL2 PLL IC1 Priority";
    }
    leaf pll2-pll-ic2-prio {
      type uint8;
      description
        "PLL2 PLL IC2 Priority";
    }
    leaf pll2-pll-ic3-prio {
      type uint8;
      description
        "PLL2 PLL IC3 Priority";
    }
    leaf pll2-pll-ic4-prio {
      type uint8;
      description
        "PLL2 PLL IC4 Priority";
    }
    leaf pll2-pll-ic5-prio {
      type uint8;
      description
        "PLL2 PLL IC5 Priority";
    }
    leaf pll2-pll-ic6-prio {
      type uint8;
      description
        "PLL2 PLL IC6 Priority";
    }
    leaf pll2-pll-ic7-prio {
      type uint8;
      description
        "PLL2 PLL IC7 Priority";
    }
    leaf pll2-pll-ic8-prio {
      type uint8;
      description
        "PLL2 PLL IC8 Priority";
    }
    leaf pll2-pll-ic9-prio {
      type uint8;
      description
        "PLL2 PLL IC9 Priority";
    }
    leaf pll2-pll-ic10-prio {
      type uint8;
      description
        "PLL2 PLL IC10 Priority";
    }
    leaf pll2-pll-ic11-prio {
      type uint8;
      description
        "PLL2 PLL IC11 Priority";
    }
    leaf pll1-pll-ic1-prio {
      type uint8;
      description
        "PLL1 PLL IC1 Priority";
    }
    leaf pll1-pll-ic2-prio {
      type uint8;
      description
        "PLL1 PLL IC2 Priority";
    }
    leaf pll1-pll-ic3-prio {
      type uint8;
      description
        "PLL1 PLL IC3 Priority";
    }
    leaf pll1-pll-ic4-prio {
      type uint8;
      description
        "PLL1 PLL IC4 Priority";
    }
    leaf pll1-pll-ic5-prio {
      type uint8;
      description
        "PLL1 PLL IC5 Priority";
    }
    leaf pll1-pll-ic6-prio {
      type uint8;
      description
        "PLL1 PLL IC6 Priority";
    }
    leaf pll1-pll-ic7-prio {
      type uint8;
      description
        "PLL1 PLL IC7 Priority";
    }
    leaf pll1-pll-ic8-prio {
      type uint8;
      description
        "PLL1 PLL IC8 Priority";
    }
    leaf pll1-pll-ic9-prio {
      type uint8;
      description
        "PLL1 PLL IC9 Priority";
    }
    leaf pll1-pll-ic10-prio {
      type uint8;
      description
        "PLL1 PLL IC10 Priority";
    }
    leaf pll1-pll-ic11-prio {
      type uint8;
      description
        "PLL1 PLL IC11 Priority";
    }
    leaf ic1-valid {
      type boolean;
      description
        "IC Valid 1";
    }
    leaf ic2-valid {
      type boolean;
      description
        "IC Valid 2";
    }
    leaf ic3-valid {
      type boolean;
      description
        "IC Valid 3";
    }
    leaf ic4-valid {
      type boolean;
      description
        "IC Valid 4";
    }
    leaf ic5-valid {
      type boolean;
      description
        "IC Valid 5";
    }
    leaf ic6-valid {
      type boolean;
      description
        "IC Valid 6";
    }
    leaf ic7-valid {
      type boolean;
      description
        "IC Valid 7";
    }
    leaf ic8-valid {
      type boolean;
      description
        "IC Valid 8";
    }
    leaf ic9-valid {
      type boolean;
      description
        "IC Valid 9";
    }
    leaf ic10-valid {
      type boolean;
      description
        "IC Valid 10";
    }
    leaf ic11-valid {
      type boolean;
      description
        "IC Valid 11";
    }
    leaf pll0-pll-freq-offset {
      type int32;
      description
        "PLL0 PLL Frequency Offset";
    }
    leaf pll2-pll-freq-offset {
      type int32;
      description
        "PLL2 PLL Frequency Offset";
    }
    leaf pll1-pll-freq-offset {
      type int32;
      description
        "PLL1 PLL Frequency Offset";
    }
    leaf pll0-pll-bandwidth {
      type string {
        length "0..50";
      }
      description
        "PLL0 PLL Bandwidth";
    }
    leaf pll2-pll-bandwidth {
      type string {
        length "0..50";
      }
      description
        "PLL2 PLL Bandwidth";
    }
    leaf pll1-pll-bandwidth {
      type string {
        length "0..50";
      }
      description
        "PLL1 PLL Bandwidth";
    }
    leaf pll0-pll-psl {
      type string {
        length "0..50";
      }
      description
        "PLL0 PLL PSL";
    }
    leaf pll2-pll-psl {
      type string {
        length "0..50";
      }
      description
        "PLL2 PLL PSL";
    }
    leaf pll1-pll-psl {
      type string {
        length "0..50";
      }
      description
        "PLL1 PLL PSL";
    }
    leaf ic1-qual-min {
      type string {
        length "0..50";
      }
      description
        "IC1 Pull-in/Hold-in Min";
    }
    leaf ic1-qual-max {
      type string {
        length "0..50";
      }
      description
        "IC1 Pull-in/Hold-in Min";
    }
    leaf ic2-qual-min {
      type string {
        length "0..50";
      }
      description
        "IC2 Pull-in/Hold-in Min";
    }
    leaf ic2-qual-max {
      type string {
        length "0..50";
      }
      description
        "IC2 Pull-in/Hold-in Min";
    }
    leaf ic3-qual-min {
      type string {
        length "0..50";
      }
      description
        "IC3 Pull-in/Hold-in Min";
    }
    leaf ic3-qual-max {
      type string {
        length "0..50";
      }
      description
        "IC3 Pull-in/Hold-in Min";
    }
    leaf ic4-qual-min {
      type string {
        length "0..50";
      }
      description
        "IC4 Pull-in/Hold-in Min";
    }
    leaf ic4-qual-max {
      type string {
        length "0..50";
      }
      description
        "IC4 Pull-in/Hold-in Min";
    }
    leaf ic5-qual-min {
      type string {
        length "0..50";
      }
      description
        "IC5 Pull-in/Hold-in Min";
    }
    leaf ic5-qual-max {
      type string {
        length "0..50";
      }
      description
        "IC5 Pull-in/Hold-in Min";
    }
    leaf ic6-qual-min {
      type string {
        length "0..50";
      }
      description
        "IC6 Pull-in/Hold-in Min";
    }
    leaf ic6-qual-max {
      type string {
        length "0..50";
      }
      description
        "IC6 Pull-in/Hold-in Min";
    }
    leaf ic7-qual-min {
      type string {
        length "0..50";
      }
      description
        "IC7 Pull-in/Hold-in Min";
    }
    leaf ic7-qual-max {
      type string {
        length "0..50";
      }
      description
        "IC7 Pull-in/Hold-in Min";
    }
    leaf ic8-qual-min {
      type string {
        length "0..50";
      }
      description
        "IC8 Pull-in/Hold-in Min";
    }
    leaf ic8-qual-max {
      type string {
        length "0..50";
      }
      description
        "IC8 Pull-in/Hold-in Min";
    }
    leaf ic9-qual-min {
      type string {
        length "0..50";
      }
      description
        "IC9 Pull-in/Hold-in Min";
    }
    leaf ic9-qual-max {
      type string {
        length "0..50";
      }
      description
        "IC9 Pull-in/Hold-in Min";
    }
    leaf ic10-qual-min {
      type string {
        length "0..50";
      }
      description
        "IC10 Pull-in/Hold-in Min";
    }
    leaf ic10-qual-max {
      type string {
        length "0..50";
      }
      description
        "IC10 Pull-in/Hold-in Min";
    }
    leaf ic11-qual-min {
      type string {
        length "0..50";
      }
      description
        "IC11 Pull-in/Hold-in Min";
    }
    leaf ic11-qual-max {
      type string {
        length "0..50";
      }
      description
        "IC11 Pull-in/Hold-in Min";
    }
    leaf ic-freq-present {
      type boolean;
      description
        "IC Freq present";
    }
    leaf ic1-freq {
      type string {
        length "0..50";
      }
      description
        "IC1 Frequency";
    }
    leaf ic2-freq {
      type string {
        length "0..50";
      }
      description
        "IC2 Frequency";
    }
    leaf ic3-freq {
      type string {
        length "0..50";
      }
      description
        "IC3 Frequency";
    }
    leaf ic4-freq {
      type string {
        length "0..50";
      }
      description
        "IC4 Frequency";
    }
    leaf ic5-freq {
      type string {
        length "0..50";
      }
      description
        "IC5 Frequency";
    }
    leaf ic6-freq {
      type string {
        length "0..50";
      }
      description
        "IC6 Frequency";
    }
    leaf ic7-freq {
      type string {
        length "0..50";
      }
      description
        "IC7 Frequency";
    }
    leaf ic8-freq {
      type string {
        length "0..50";
      }
      description
        "IC8 Frequency";
    }
    leaf ic9-freq {
      type string {
        length "0..50";
      }
      description
        "IC9 Frequency";
    }
    leaf ic10-freq {
      type string {
        length "0..50";
      }
      description
        "IC10 Frequency";
    }
    leaf ic11-freq {
      type string {
        length "0..50";
      }
      description
        "IC11 Frequency";
    }
  }
}
