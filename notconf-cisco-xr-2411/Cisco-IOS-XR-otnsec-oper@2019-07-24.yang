module Cisco-IOS-XR-otnsec-oper {
  namespace "http://cisco.com/ns/yang/Cisco-IOS-XR-otnsec-oper";
  prefix otnsec-oper;

  import Cisco-IOS-XR-types {
    prefix xr;
  }
  import cisco-semver {
    prefix semver;
  }

  include Cisco-IOS-XR-otnsec-oper-sub1 {
    revision-date 2019-07-24;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR otnsec package operational data.

     This module contains definitions
     for the following management objects:
       odu-otnsec: Otnsec operational data

     Copyright (c) 2013-2019 by Cisco Systems, Inc.
     All rights reserved.";

  revision 2019-07-24 {
    semver:module-version "1.1.0";
    description
      "Addition for leaf 'Time to Rekey' to display the key expiry time";
  }
  revision 2019-04-05 {
    semver:module-version "1.0.0";
    description
      "Establish semantic version baseline.";
  }
  revision 2018-11-10 {
    description
      "Initial Operational Schema Support";
  }
  revision 2015-11-09 {
    description
      "IOS XR 6.0 revision.";
  }

  container odu-otnsec {
    config false;
    description
      "Otnsec operational data";
    container controllers {
      description
        "ALL Otnsec Port oper data";
      list controller {
        key "controller-name";
        description
          "Otnsec Port oper data";
        container detail {
          description
            "Otnsec detail operational data";
          uses OTNSEC-EDM-DETAIL;
        }
        container summary {
          description
            "Otnsec summary  operational data";
          uses OTNSEC-EDM-SUMMARY;
        }
        leaf controller-name {
          type xr:Interface-name;
          description
            "Port name";
        }
      }
    }
  }
}
