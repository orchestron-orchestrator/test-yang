module SNMP-TARGET-MIB {
  namespace "http://tail-f.com/ns/mibs/SNMP-TARGET-MIB/200210140000Z";
  prefix SNMP_TARGET_MIB;

  import ietf-yang-types {
    prefix yang;
  }
  import tailf-common {
    prefix tailf;
  }
  import SNMPv2-TC {
    prefix SNMPv2_TC;
  }
  import SNMP-FRAMEWORK-MIB {
    prefix SNMP_FRAMEWORK_MIB;
  }

  revision 2002-10-14 {
    description
      "";
  }

  tailf:id "";
  tailf:snmp-mib-module-name "SNMP-TARGET-MIB";

  typedef UDPIPv4TAddress {
    tailf:info "ipv4+port (6 dot-separated octets)";
    type tailf:octet-list {
      tailf:value-length "6";
    }
  }

  typedef UDPIPv6TAddress {
    tailf:info "ipv6+port (18 dot-separated octets)";
    type tailf:octet-list {
      tailf:value-length "18";
    }
  }

  typedef UDPTAddress {
    type union {
      type UDPIPv4TAddress;
      type UDPIPv6TAddress;
    }
  }

  typedef EmptyOctetList {
    type tailf:octet-list {
      tailf:value-length "0";
    }
  }

  typedef UDPTMask {
    tailf:info "octectList, 0, 6 or 18 octets long";
    type union {
      type UDPTAddress;
      type EmptyOctetList;
    }
  }

  typedef snmpTargetAddrEngineIDType {
    type tailf:hex-list {
      tailf:value-length "min .. 32";
      pattern "(((([0-9A-Fa-f]{2}):){4,31})([0-9A-Fa-f]{2}))?";
    }
  }

  typedef snmpTargetAddrMMSType {
    type int32 {
      range "0 | 484 .. 2147483647";
    }
  }

  typedef SnmpTagValue {
    type string {
      length "min .. 255";
    }
  }

  typedef SnmpTagList {
    type string {
      length "min .. 255";
    }
  }

  typedef snmpTargetAddrNameType {
    type string {
      length "1 .. 32";
    }
  }

  typedef snmpTargetAddrRetryCountType {
    type int32 {
      range "0 .. 255";
    }
  }

  typedef snmpTargetAddrParamsType {
    type string {
      length "1 .. 32";
    }
  }

  typedef snmpTargetParamsNameType {
    type string {
      length "1 .. 32";
    }
  }

  typedef snmpTargetParamsSecurityModelType {
    type int32 {
      range "1 .. 2147483647";
    }
  }

  container SNMP-TARGET-MIB {
    container snmpTargetObjects {
      tailf:snmp-oid "1.3.6.1.6.3.12.1";
      config false;
      leaf snmpUnavailableContexts {
        tailf:snmp-oid "1.3.6.1.6.3.12.1.4";
        type yang:counter32;
        config false;
      }
      leaf snmpUnknownContexts {
        tailf:snmp-oid "1.3.6.1.6.3.12.1.5";
        type yang:counter32;
        config false;
      }
    }
    container snmpTargetAddrTable {
      list snmpTargetAddrEntry {
        tailf:sort-order "snmp-implied";
        tailf:snmp-oid "1.3.6.1.6.3.12.1.2";
        tailf:snmp-name "snmpTargetAddrTable";
        tailf:snmp-name "SNMP-COMMUNITY-MIB:snmpTargetAddrExtTable";
        key "snmpTargetAddrName";
        leaf snmpTargetAddrName {
          tailf:snmp-oid "1.3.6.1.6.3.12.1.2.1.1";
          type snmpTargetAddrNameType;
        }
        leaf snmpTargetAddrTDomain {
          tailf:snmp-oid "1.3.6.1.6.3.12.1.2.1.2";
          type SNMPv2_TC:TDomain;
          mandatory true;
        }
        leaf snmpTargetAddrTAddress {
          tailf:snmp-oid "1.3.6.1.6.3.12.1.2.1.3";
          type UDPTAddress;
          mandatory true;
        }
        leaf snmpTargetAddrTimeout {
          tailf:snmp-oid "1.3.6.1.6.3.12.1.2.1.4";
          type SNMPv2_TC:TimeInterval;
          default "1500";
        }
        leaf snmpTargetAddrRetryCount {
          tailf:snmp-oid "1.3.6.1.6.3.12.1.2.1.5";
          type snmpTargetAddrRetryCountType;
          default "3";
        }
        leaf snmpTargetAddrTagList {
          tailf:snmp-oid "1.3.6.1.6.3.12.1.2.1.6";
          type SnmpTagList;
          default "";
        }
        leaf snmpTargetAddrParams {
          tailf:snmp-oid "1.3.6.1.6.3.12.1.2.1.7";
          type snmpTargetAddrParamsType;
          mandatory true;
        }
        leaf snmpTargetAddrStorageType {
          tailf:snmp-oid "1.3.6.1.6.3.12.1.2.1.8";
          type SNMPv2_TC:StorageType;
          default "nonVolatile";
        }
        leaf snmpTargetAddrEngineID {
          type snmpTargetAddrEngineIDType;
          default "";
        }
        leaf snmpTargetAddrTMask {
          tailf:snmp-name "SNMP-COMMUNITY-MIB:snmpTargetAddrExtTable:snmpTargetAddrTMask";
          type UDPTMask;
          default "";
        }
        leaf snmpTargetAddrMMS {
          tailf:snmp-name "SNMP-COMMUNITY-MIB:snmpTargetAddrExtTable:snmpTargetAddrMMS";
          type snmpTargetAddrMMSType;
          default "2048";
        }
        leaf enabled {
          type boolean;
          default "true";
        }
      }
    }
    container snmpTargetParamsTable {
      list snmpTargetParamsEntry {
        tailf:sort-order "snmp-implied";
        tailf:snmp-oid "1.3.6.1.6.3.12.1.3";
        key "snmpTargetParamsName";
        leaf snmpTargetParamsName {
          tailf:snmp-oid "1.3.6.1.6.3.12.1.3.1.1";
          type snmpTargetParamsNameType;
        }
        leaf snmpTargetParamsMPModel {
          tailf:snmp-oid "1.3.6.1.6.3.12.1.3.1.2";
          type SNMP_FRAMEWORK_MIB:SnmpMessageProcessingModel;
          mandatory true;
        }
        leaf snmpTargetParamsSecurityModel {
          tailf:snmp-oid "1.3.6.1.6.3.12.1.3.1.3";
          type snmpTargetParamsSecurityModelType;
          mandatory true;
        }
        leaf snmpTargetParamsSecurityName {
          tailf:snmp-oid "1.3.6.1.6.3.12.1.3.1.4";
          type SNMP_FRAMEWORK_MIB:SnmpAdminString;
          mandatory true;
        }
        leaf snmpTargetParamsSecurityLevel {
          tailf:snmp-oid "1.3.6.1.6.3.12.1.3.1.5";
          type SNMP_FRAMEWORK_MIB:SnmpSecurityLevel;
          mandatory true;
        }
        leaf snmpTargetParamsStorageType {
          tailf:snmp-oid "1.3.6.1.6.3.12.1.3.1.6";
          type SNMPv2_TC:StorageType;
          default "nonVolatile";
        }
      }
    }
  }
}
