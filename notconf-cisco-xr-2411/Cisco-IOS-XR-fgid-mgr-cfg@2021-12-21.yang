module Cisco-IOS-XR-fgid-mgr-cfg {
  namespace "http://cisco.com/ns/yang/Cisco-IOS-XR-fgid-mgr-cfg";
  prefix fgid-mgr-cfg;

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR fgid-mgr package configuration.

     This module contains definitions
     for the following management objects:
       fgid-mgr-config: none

     Copyright (c) 2013-2021 by Cisco Systems, Inc.
     All rights reserved.";

  revision 2021-12-21 {
    semver:module-version "1.0.0";
    description
      "Yang Schema added with task-name.";
  }
  revision 2019-04-05 {
    description
      "Establish semantic version baseline.";
  }
  revision 2015-11-09 {
    description
      "IOS XR 6.0 revision.";
  }

  container fgid-mgr-config {
    description
      "none";
    container fabric-fgid {
      description
        "Configure FGID consistency checker";
      leaf consistency-checker-timeout {
        type uint32;
        description
          "configure timeout 1 min=1, 10 mins=10, 60
           mins=60; off=0";
      }
    }
  }
}
