module Cisco-IOS-XR-shellutil-delete-act {
  namespace "http://cisco.com/ns/yang/Cisco-IOS-XR-shellutil-delete-act";
  prefix shellutil-delete-act;

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR action package configuration.

     Copyright (c) 2016-2019 by Cisco Systems, Inc.
     All rights reserved.";

  revision 2019-10-01 {
    semver:module-version "1.1.0";
    description
      "Made changes to be RFC6087 compliant";
  }
  revision 2019-04-05 {
    semver:module-version "1.0.0";
    description
      "Establish semantic version baseline.";
  }
  revision 2019-02-07 {
    description
      "Updated the task group for delete *-ext.yang";
  }
  revision 2018-01-20 {
    description
      "IOS XR 7.0.1 revision.";
  }

  rpc delete {
    description
      "Delete";

    input {
      leaf name {
        type string;
        mandatory true;
        description
          "file name";
      }
      leaf location {
        type string;
        description
          "location";
      }
      leaf recurse {
        type boolean;
        description
          "Files in dir";
      }
    }
    output {
      leaf response {
        type string;
        description
          "Status of delete operation";
      }
    }
  }
}
