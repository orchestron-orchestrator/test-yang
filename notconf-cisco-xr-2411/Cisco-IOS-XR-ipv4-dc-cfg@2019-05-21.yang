module Cisco-IOS-XR-ipv4-dc-cfg {
  namespace "http://cisco.com/ns/yang/Cisco-IOS-XR-ipv4-dc-cfg";
  prefix ipv4-dc-cfg;

  import cisco-semver {
    prefix semver;
  }
  import Cisco-IOS-XR-ifmgr-cfg {
    prefix a1;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ipv4-dc package configuration.

     This YANG module augments the
       Cisco-IOS-XR-ifmgr-cfg
     module with configuration data.

     Copyright (c) 2013-2019 by Cisco Systems, Inc.
     All rights reserved.";

  revision 2019-05-21 {
    semver:module-version "1.0.0";
    description
      "Fixing yang gaps.";
  }
  revision 2019-04-05 {
    description
      "Establish semantic version baseline.";
  }
  revision 2015-11-09 {
    description
      "IOS XR 6.0 revision.";
  }

  typedef Opt61-sub {
    type enumeration {
      enum "ascii" {
        value 1;
        description
          "ascii";
      }
      enum "sn-chassis" {
        value 3;
        description
          "sn chassis";
      }
    }
    description
      "Opt61 sub";
  }

  typedef Option61 {
    type enumeration {
      enum "option61" {
        value 61;
        description
          "OPTION61";
      }
    }
    description
      "Option61";
  }

  typedef Option60 {
    type enumeration {
      enum "option60" {
        value 60;
        description
          "OPTION60";
      }
    }
    description
      "Option60";
  }

  typedef Option77 {
    type enumeration {
      enum "option77" {
        value 77;
        description
          "OPTION77";
      }
    }
    description
      "Option77";
  }

  augment "/a1:interface-configurations/a1:interface-configuration" {
    description
      "This augment extends the configuration data of
       'Cisco-IOS-XR-ifmgr-cfg'";
    container ipv4-dhcp-client-config {
      presence "Indicates a ipv4-dhcp-client-config node is configured.";
      description
        "Interface IPv4 dhcp-addres-client-options
         configuration";
      container option61-config {
        presence "Indicates a option61-config node is configured.";
        description
          "Option 61";
        leaf opt61 {
          type Option61;
          mandatory true;
          description
            "Option 61";
        }
        leaf subtype {
          type Opt61-sub;
          mandatory true;
          description
            "Enter Option61 SubType";
        }
        leaf ascii-string {
          type string {
            length "1..255";
          }
          description
            "Enter ascii string for opt61Subtype ascii";
        }
      }
      container option60-config {
        presence "Indicates a option60-config node is configured.";
        description
          "Option 60";
        leaf opt60 {
          type Option60;
          mandatory true;
          description
            "Option 60";
        }
        leaf enable {
          type empty;
          mandatory true;
          description
            "Option 60 is enabled";
        }
        leaf ascii-string {
          type string {
            length "1..255";
          }
          mandatory true;
          description
            "Enter ascii string";
        }
      }
      container option77-config {
        presence "Indicates a option77-config node is configured.";
        description
          "Option 77";
        leaf opt77 {
          type Option77;
          mandatory true;
          description
            "Option 77";
        }
        leaf enable {
          type empty;
          mandatory true;
          description
            "Option 77 is enabled";
        }
        leaf ascii-string {
          type string {
            length "1..255";
          }
          mandatory true;
          description
            "Enter ascii string";
        }
      }
      leaf ipv4-dhcp-client {
        type empty;
        mandatory true;
        description
          "ipv4 address dhcp-client-options is enabled";
      }
    }
  }
}
