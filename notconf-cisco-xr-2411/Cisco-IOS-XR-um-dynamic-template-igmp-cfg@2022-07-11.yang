module Cisco-IOS-XR-um-dynamic-template-igmp-cfg {
  namespace "http://cisco.com/ns/yang/Cisco-IOS-XR-um-dynamic-template-igmp-cfg";
  prefix um-dynamic-template-igmp-cfg;

  import Cisco-IOS-XR-types {
    prefix xr;
  }
  import Cisco-IOS-XR-um-dynamic-template-cfg {
    prefix a1;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR dynamic-template-igmp package configuration.

     This YANG module augments the
     modules with configuration data.

     Copyright (c) 2020-2022 by Cisco Systems, Inc.
     All rights reserved.";

  revision 2022-07-11 {
    semver:module-version "1.1.0";
    description
      "Added missing description statement to nodes";
  }
  revision 2020-04-12 {
    semver:module-version "1.0.0";
    description
      "Initial release";
  }

  grouping TEMPLATE-BODY {
    description
      "Grouping for template";
    container igmp {
      description
        "IPv4 Address Family";
      leaf query-interval {
        type uint32 {
          range "1..3600" {
            description
              "Query interval in seconds";
          }
        }
        description
          "IGMP IGMP host query interval";
      }
      leaf query-max-response-time {
        type uint32 {
          range "1..25" {
            description
              "query response value in seconds";
          }
        }
        description
          "IGMP max query response value";
      }
      container explicit-tracking {
        presence "Indicates a explicit-tracking node is configured.";
        description
          "IGMPv3 explicit host tracking";
        leaf access-list-name {
          type xr:Cisco-ios-xr-string {
            length "1..32" {
              description
                "Access list specifying tracking group range";
            }
          }
          description
            "Access list specifying tracking group range";
        }
      }
      container access-group {
        description
          "IGMP access group";
        leaf access-list-name {
          type xr:Cisco-ios-xr-string {
            length "1..32" {
              description
                "IP Named Standard Access list";
            }
          }
          description
            "IP Named Standard Access list";
        }
      }
      leaf max-groups {
        type uint32 {
          range "1..40000" {
            description
              "max groups";
          }
        }
        description
          "IGMP max groups";
      }
      leaf threshold {
        type uint32 {
          range "1..504" {
            description
              "Threshold warning";
          }
        }
        must "../max-groups";
        description
          "Threshold warning";
      }
      leaf name-of-acl {
        type xr:Cisco-ios-xr-string {
          length "1..800" {
            description
              "Name of ACL";
          }
        }
        must "../max-groups";
        description
          "Name of ACL";
      }
      leaf version {
        type uint32 {
          range "1..3" {
            description
              "version";
          }
        }
        description
          "IGMP version";
      }
      container multicast {
        description
          "multicast mode";
        container ipv4 {
          description
            "IPv4 address family";
          container passive {
            must "not(../qos-correlation)";
            presence "Indicates a passive node is configured.";
            description
              "Enable forwarding functionality";
          }
          container qos-correlation {
            must "not(../passive)";
            presence "Indicates a qos-correlation node is configured.";
            description
              "Enable QOS correlation functionality";
          }
        }
      }
    }
  }

  augment "/a1:dynamic-template/a1:type/a1:ppp/a1:template" {
    description
      "This augment extends dynamic-template ppp nodes
       configuration";
    uses TEMPLATE-BODY;
  }
  augment "/a1:dynamic-template/a1:type/a1:ipsubscriber/a1:template" {
    description
      "This augment extends dynamic-template ipsubscriber nodes
       configuration";
    uses TEMPLATE-BODY;
  }
}
