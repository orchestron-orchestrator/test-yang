module Cisco-IOS-XR-ncs1001-hw-module-eth-oper {
  namespace "http://cisco.com/ns/yang/Cisco-IOS-XR-ncs1001-hw-module-eth-oper";
  prefix ncs1001-hw-module-eth-oper;

  import cisco-semver {
    prefix semver;
  }

  include Cisco-IOS-XR-ncs1001-hw-module-eth-oper-sub1 {
    revision-date 2022-08-23;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ncs1001-hw-module-eth package operational data.

     This module contains definitions
     for the following management objects:
       hw-module: ncs1001 hw-module command chain

     Copyright (c) 2013-2022 by Cisco Systems, Inc.
     All rights reserved.";

  revision 2022-08-23 {
    semver:module-version "1.0.0";
    description
      "first release.";
  }
  revision 2019-04-05 {
    description
      "Establish semantic version baseline.";
  }
  revision 2015-11-09 {
    description
      "IOS XR 6.0 revision.";
  }

  typedef Esd-hw-module-eth-port {
    type enumeration {
      enum "sfp-udc3" {
        value 0;
        description
          "SFP  slot 3 port    ( 0)";
      }
      enum "sfp-udc2" {
        value 4;
        description
          "SFP  slot 2 port    ( 4)";
      }
      enum "sfp-udc1" {
        value 8;
        description
          "SFP  slot 1 port    ( 8)";
      }
      enum "rj45-udc1" {
        value 12;
        description
          "UDC1 port           (12)";
      }
      enum "rj45-udc2" {
        value 16;
        description
          "UDC2 port           (16)";
      }
      enum "rj45-udc3" {
        value 20;
        description
          "UDC3 port           (20)";
      }
      enum "cpu-mgmt" {
        value 24;
        description
          "CPU side Mgmt ports (24)";
      }
      enum "rj45-mgmt" {
        value 26;
        description
          "RJ45 Mgmt port      (26)";
      }
      enum "sfp-mgmt" {
        value 27;
        description
          "SFP  Mgmt port      (27)";
      }
    }
    description
      "Esd hw module eth port";
  }

  container hw-module {
    config false;
    description
      "ncs1001 hw-module command chain";
    container eth-switch {
      description
        "ethernet operational data";
      container eth-switch-data {
        description
          "ethernet operational data";
        container eth-switch-action-ports-attrs {
          description
            "ports attributes";
          uses ESD-HWMOD-ETH-SWITCH-PORTS-ATTRS-OP;
        }
        container eth-switch-actionvlans {
          description
            "available vlans";
          uses ESD-HWMOD-ETH-SWITCH-VLANS-OP;
        }
        container eth-switch-action-stat-ports {
          description
            "ethernet operational data";
          list eth-switch-action-stat-port {
            key "hw-module-eth-port-type";
            description
              "ethernet port statistics";
            leaf hw-module-eth-port-type {
              type Esd-hw-module-eth-port;
              description
                "Details associated with a particular Data
                 type";
            }
            uses ESD-HWMOD-ETH-SWITCH-PORT-STAT-OP;
          }
        }
      }
    }
  }
}
