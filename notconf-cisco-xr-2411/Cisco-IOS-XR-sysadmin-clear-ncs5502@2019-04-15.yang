module Cisco-IOS-XR-sysadmin-clear-ncs5502 {
  namespace "http://www.cisco.com/ns/yang/Cisco-IOS-XR-sysadmin-clear-ncs5502";
  prefix calvados_clear;

  import tailf-common {
    prefix tailf;
  }
  import Cisco-IOS-XR-sysadmin-ethsw-esdma-cli-ncs5500 {
    prefix esdma;
  }
  import Cisco-IOS-XR-sysadmin-asic-errors-ael {
    prefix aelclear;
  }
  import Cisco-IOS-XR-sysadmin-fabric-ncs5502 {
    prefix fabric;
  }
  import cisco-semver {
    prefix semver;
  }

  organization
    "Cisco Systems Inc.";
  contact
    "Cisco Systems, Inc.
     Customer Service

     Postal: 170 West Tasman Drive
     San Jose, CA 95134

     Tel: +1 800 553-NETS

     E-mail: cs-yang@cisco.com";
  description
    "This module contains a collection of YANG
     definitions for Cisco IOS-XR SysAdmin configuration.

     This module defines the top level container for
     all 'clear' commands for Sysadmin.

     Copyright (c) 2015-2020 by Cisco Systems, Inc.
     All rights reserved.";

  revision 2019-04-15 {
    semver:module-version "1.0.0";
    description
      "Establish semantic version baseline.";
  }
  revision 2019-01-30 {
    description
      "Changed the namespace to be consistent with module name";
  }
  revision 2017-10-11 {
    description
      "Changed the namespace to unique namespace per unique model";
  }
  revision 2017-01-31 {
    description
      "Changed the namespace and module name";
  }
  revision 2015-03-20 {
    description
      "Created initial 'clear' implementation for Fretta";
  }

  grouping asic_clear {
    tailf:action "statistics";
  }

  container clear {
    container controller {
      container switch {
        uses esdma:switch_clear;
      }
      uses fabric:fabric_clear;
    }
    uses aelclear:ael-clear-asic-errors-grp;
  }
}
