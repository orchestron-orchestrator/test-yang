submodule Cisco-IOS-XR-mirror-oper-sub1 {
  belongs-to Cisco-IOS-XR-mirror-oper {
    prefix Cisco-IOS-XR-mirror-oper;
  }

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR mirror package operational data.

     Copyright (c) 2013-2019 by Cisco Systems, Inc.
     All rights reserved.";

  revision 2019-04-05 {
    semver:module-version "1.0.0";
    description
      "Establish semantic version baseline.";
  }
  revision 2015-11-09 {
    description
      "IOS XR 6.0 revision.";
  }

  typedef Change-bag-reason {
    type enumeration {
      enum "checksum" {
        description
          "Checksum";
      }
      enum "size" {
        description
          "Size";
      }
      enum "mod-time" {
        description
          "Modification time";
      }
      enum "permissions" {
        description
          "Permissions changed";
      }
      enum "owner" {
        description
          "Owner changed";
      }
      enum "group" {
        description
          "Group changed";
      }
      enum "reserved" {
        description
          "<reserved>";
      }
      enum "acl" {
        description
          "ACL changed";
      }
      enum "xattr" {
        description
          "Extended attributes changed";
      }
      enum "none" {
        description
          "Unknown or no mismatch. When UT_UNKNOWN or
           UT_NONE.";
      }
      enum "sub-item" {
        description
          "Sub item of this dir has a change";
      }
      enum "new-item" {
        description
          "This item is newly created";
      }
    }
    description
      "ChangeReason";
  }

  typedef File-bag {
    type enumeration {
      enum "file" {
        description
          "File";
      }
      enum "directory" {
        description
          "Directory";
      }
      enum "symlink" {
        description
          "Symlink";
      }
      enum "device" {
        description
          "Device";
      }
      enum "special" {
        description
          "Special";
      }
      enum "unknown" {
        description
          "<unknown>";
      }
    }
    description
      "ItemType";
  }

  typedef Update-bag {
    type enumeration {
      enum "send" {
        description
          "Send changes to standby";
      }
      enum "recv" {
        description
          "Receive changes from standby";
      }
      enum "create" {
        description
          "Create on standby";
      }
      enum "hardlink" {
        description
          "Hardlink";
      }
      enum "unknown" {
        description
          "Unexpected reason, use update_msg field";
      }
      enum "none" {
        description
          "In sync on both active and standby";
      }
      enum "delete" {
        description
          "Delete on standby";
      }
      enum "sub-item" {
        description
          "Sub item of this dir needs a change";
      }
    }
    description
      "Update";
  }

  typedef Mirror-bag-state {
    type enumeration {
      enum "no" {
        description
          "Not mirrored, and no sync in progress";
      }
      enum "yes" {
        description
          "Mirrored";
      }
      enum "in-progress" {
        description
          "Not mirrored, but sync in progress";
      }
    }
    description
      "MirrorState";
  }

  grouping MIRROR-FILE-ENTRY {
    description
      "One item in the mirror dir";
    leaf path-xr {
      type string;
      description
        "Path item";
    }
    leaf state {
      type Mirror-bag-state;
      description
        "What sync state item is in";
    }
    leaf update {
      type Update-bag;
      description
        "What update should be done";
    }
    leaf update-msg {
      type string;
      description
        "In case of unknown update";
    }
    leaf type {
      type File-bag;
      description
        "Item type";
    }
    leaf reason {
      type Change-bag-reason;
      description
        "Reason for mismatch";
    }
    leaf checksum {
      type string;
      description
        "MD5 checksum for mirrored files";
    }
    leaf mod-time {
      type uint64;
      description
        "Mod time for mirrored files";
    }
  }

  grouping MIRROR-SYNC-ENTRY {
    description
      "One sync dir status";
    leaf directory-xr {
      type string;
      description
        "Directory being synced";
    }
    leaf sync-in-progress {
      type boolean;
      description
        "True if sync is in progress";
    }
    leaf start-time {
      type uint64;
      description
        "Unix Epoch of when sync started";
    }
    leaf scan-error {
      type string;
      description
        "Empty if no error, else the dir scanning error
         which prevents mirroring on this dir";
    }
    leaf standby-up {
      type boolean;
      description
        "If false, standby is not syncable";
    }
  }
}
