module Cisco-IOS-XR-watchd-cfg {
  namespace "http://cisco.com/ns/yang/Cisco-IOS-XR-watchd-cfg";
  prefix watchd-cfg;

  import Cisco-IOS-XR-config-mda-cfg {
    prefix node;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR watchd package configuration.

     This module contains definitions
     for the following management objects:
       watchdog: Watchdog configuration commands
       watchd: Watchdog configuration commands

     This YANG module augments the
       Cisco-IOS-XR-config-mda-cfg
     module with configuration data.

     Copyright (c) 2013-2023 by Cisco Systems, Inc.
     All rights reserved.";

  revision 2023-07-07 {
    semver:module-version "1.1.0";
    description
      "Corrected disk threshold range.";
  }
  revision 2019-04-05 {
    semver:module-version "1.0.1";
    description
      "Establish semantic version baseline.";
  }
  revision 2015-11-09 {
    description
      "IOS XR 6.0 revision.";
  }
  revision 2015-10-12 {
    description
      "Descriptions updated.";
  }

  grouping NODE-CFG {
    description
      "active/preconfigured nodes configuration";
    container watchdog-node-threshold {
      description
        "Watchdog threshold configuration";
      container disk-threshold {
        description
          "Disk thresholds";
        leaf minor {
          type uint32 {
            range "1..97";
          }
          description
            "Threshold, Range(1, 97)";
        }
        leaf severe {
          type uint32 {
            range "2..98";
          }
          description
            "Threshold, Range(<minor>, 98)";
        }
        leaf critical {
          type uint32 {
            range "3..99";
          }
          description
            "Threshold, Range(<severe>, 99)";
        }
      }
      container memory-threshold {
        description
          "Memory thresholds";
        leaf minor {
          type uint32 {
            range "5..40";
          }
          description
            "Threshold, Range(5, 40)";
        }
        leaf severe {
          type uint32 {
            range "4..40";
          }
          description
            "Threshold, Range(4, minor)";
        }
        leaf critical {
          type uint32 {
            range "3..40";
          }
          description
            "Threshold, Range(3, severe)";
        }
      }
    }
  }

  container watchdog {
    description
      "Watchdog configuration commands";
    container threshold-memory {
      description
        "Memory thresholds";
      leaf minor {
        type uint32 {
          range "5..40";
        }
        description
          "Threshold, Range (5, 40)";
      }
      leaf severe {
        type uint32 {
          range "4..40";
        }
        description
          "Threshold, Range (4, minor)";
      }
      leaf critical {
        type uint32 {
          range "3..40";
        }
        description
          "Threshold, Range (3, severe)";
      }
    }
    container disk-limit {
      description
        "Disk thresholds";
      leaf minor {
        type uint32 {
          range "1..97";
        }
        description
          "Threshold, Range (1, 97)";
      }
      leaf severe {
        type uint32 {
          range "2..98";
        }
        description
          "Threshold, Range (<minor>, 98)";
      }
      leaf critical {
        type uint32 {
          range "3..99";
        }
        description
          "Threshold, Range (<severe>, 99)";
      }
    }
    leaf overload-notification {
      type empty;
      description
        "Disable critical event notification";
    }
    leaf restart-deadlock-disable {
      type empty;
      description
        "Disable watchdog restart deadlock";
    }
    leaf restart-memoryhog-disable {
      type empty;
      description
        "Disable watchdog restart memory-hog";
    }
    leaf overload-throttle-timeout {
      type uint32 {
        range "5..120";
      }
      units "second";
      description
        "Watchdog overload throttle timeout configuration";
    }
  }
  container watchd {
    description
      "Watchdog configuration commands";
    leaf timeout {
      type uint32 {
        range "1..10";
      }
      units "second";
      description
        "Length of timeout in seconds";
    }
  }

  augment "/node:active-nodes/node:active-node" {
    description
      "This augment extends active nodes configuration";
    uses NODE-CFG;
  }
  augment "/node:preconfigured-nodes/node:preconfigured-node" {
    description
      "This augment extends preconfigured nodes
       configuration";
    uses NODE-CFG;
  }
}
