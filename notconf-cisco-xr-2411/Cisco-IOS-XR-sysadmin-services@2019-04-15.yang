module Cisco-IOS-XR-sysadmin-services {
  namespace "http://www.cisco.com/ns/yang/Cisco-IOS-XR-sysadmin-services";
  prefix calvados_services;

  import cisco-semver {
    prefix semver;
  }

  organization
    "Cisco Systems Inc.";
  contact
    "Cisco Systems, Inc.
     Customer Service

     Postal: 170 West Tasman Drive
     San Jose, CA 95134

     Tel: +1 800 553-NETS

     E-mail: cs-yang@cisco.com";
  description
    "This module contains a collection of YANG
     definitions for Cisco IOS-XR SysAdmin configuration.

     This module defines the services offered in the
     sysadmin plane.

     Copyright(c) 2016 by Cisco Systems, Inc.
     All rights reserved.

     Copyright (c) 2012-2020 by Cisco Systems, Inc.
     All rights reserved.";

  revision 2019-04-15 {
    semver:module-version "1.0.0";
    description
      "Establish semantic version baseline.";
  }
  revision 2016-11-10 {
    description
      "Initial revision";
  }

  container service {
    config true;
    container cli {
      container interactive {
        leaf enabled {
          type boolean;
          default "true";
        }
      }
    }
  }
}
