module Cisco-IOS-XR-l2-eth-infra-oper {
  namespace "http://cisco.com/ns/yang/Cisco-IOS-XR-l2-eth-infra-oper";
  prefix l2-eth-infra-oper;

  import Cisco-IOS-XR-types {
    prefix xr;
  }
  import cisco-semver {
    prefix semver;
  }
  import Cisco-IOS-XR-l2-eth-infra-datatypes {
    prefix dt1;
  }

  include Cisco-IOS-XR-l2-eth-infra-oper-sub3 {
    revision-date 2022-03-11;
  }
  include Cisco-IOS-XR-l2-eth-infra-oper-sub2 {
    revision-date 2022-03-11;
  }
  include Cisco-IOS-XR-l2-eth-infra-oper-sub1 {
    revision-date 2022-03-11;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR l2-eth-infra package operational data.

     This module contains definitions
     for the following management objects:
       mac-accounting: MAC accounting operational data
       vlan: VLAN operational data
       ethernet-encapsulation: Ethernet encapsulation operational
         data

     Copyright (c) 2013-2022 by Cisco Systems, Inc.
     All rights reserved.";

  revision 2022-03-11 {
    semver:module-version "1.1.0";
    description
      "Added leaf number-of-ranges indicating count of vlan-ranges in tags-to-match.
       2021-07-07
         Added hardware timestamp support for MAC accounting stats.";
  }
  revision 2019-04-05 {
    semver:module-version "1.0.1";
    description
      "Establish semantic version baseline.";
  }
  revision 2015-11-09 {
    description
      "IOS XR 6.0 revision.";
  }

  container mac-accounting {
    config false;
    description
      "MAC accounting operational data";
    container interfaces {
      description
        "MAC accounting interface table in MIB
         lexicographic order";
      list interface {
        key "interface-name";
        description
          "Operational data and statistics for an
           interface configured with MAC accounting
           enabled";
        leaf interface-name {
          type xr:Interface-name;
          description
            "The interface name";
        }
        uses MAC-ACC-INTF;
      }
    }
  }
  container vlan {
    config false;
    description
      "VLAN operational data";
    container nodes {
      description
        "Per node VLAN operational data";
      list node {
        key "node-id";
        description
          "The VLAN operational data for a particular node";
        container trunks {
          description
            "VLAN trunk table (specific to this node)";
          list trunk {
            key "interface";
            description
              "Operational data for trunk interfaces
               configured with VLANs";
            leaf interface {
              type xr:Interface-name;
              description
                "The interface name";
            }
            uses VLAN-TRUNK;
          }
        }
        container interfaces {
          description
            "VLAN interface table (specific to this node)";
          list interface {
            key "interface";
            description
              "Operational data for a sub-interface
               configured with VLANs";
            leaf interface {
              type xr:Interface-name;
              description
                "The interface name";
            }
            uses VLAN-INTF;
          }
        }
        container tag-allocations {
          description
            "VLAN tag allocation table (specific to this
             node)";
          list tag-allocation {
            description
              "Operational data for a sub-interface
               configured with VLANs";
            leaf interface {
              type xr:Interface-name;
              description
                "The interface name";
            }
            leaf first-tag {
              type dt1:Vlan-tag;
              description
                "The first (outermost) tag";
            }
            leaf second-tag {
              type dt1:Vlan-tag-or-any;
              description
                "The second tag";
            }
            uses VLAN-INTF;
          }
        }
        leaf node-id {
          type xr:Node-id;
          description
            "The identifier for the node";
        }
      }
    }
  }
  container ethernet-encapsulation {
    config false;
    description
      "Ethernet encapsulation operational data";
    container nodes {
      description
        "Per node Ethernet encapsulation operational data";
      list node {
        key "node-name";
        description
          "The Ethernet encaps operational data for a
           particular node";
        container unicast-mac-filters {
          description
            "Unicast MAC filter table (specific to this
             node)";
          list unicast-mac-filter {
            key "interface-name";
            description
              "Operational data for interface with MAC
               filters configured";
            leaf interface-name {
              type xr:Interface-name;
              description
                "The interface name";
            }
            uses ETHER-CAPS-UCAST-FILTER;
          }
        }
        leaf node-name {
          type xr:Node-id;
          description
            "The identifier for the node";
        }
      }
    }
  }
}
