module SNMP-FRAMEWORK-MIB {
  namespace "http://tail-f.com/ns/mibs/SNMP-FRAMEWORK-MIB/200210140000Z";
  prefix SNMP_FRAMEWORK_MIB;

  import tailf-common {
    prefix tailf;
  }

  revision 2002-10-14 {
    description
      "";
  }

  tailf:id "";
  tailf:snmp-mib-module-name "SNMP-FRAMEWORK-MIB";

  typedef SnmpEngineID {
    type tailf:hex-list {
      tailf:value-length "5 .. 32";
      pattern "(((([0-9A-Fa-f]{2}):){4,31})([0-9A-Fa-f]{2}))";
    }
  }

  typedef SnmpSecurityModel {
    type int32 {
      range "0 .. 2147483647";
    }
  }

  typedef SnmpMessageProcessingModel {
    type int32 {
      range "0 .. 2147483647";
    }
  }

  typedef SnmpSecurityLevel {
    type enumeration {
      enum "noAuthNoPriv" {
        value 1;
      }
      enum "authNoPriv" {
        value 2;
      }
      enum "authPriv" {
        value 3;
      }
    }
  }

  typedef SnmpAdminString {
    type string {
      length "min .. 255";
    }
  }

  typedef snmpEngineBootsType {
    type int32 {
      range "1 .. 2147483647";
    }
  }

  typedef snmpEngineTimeType {
    type int32 {
      range "0 .. 2147483647";
    }
  }

  typedef snmpEngineMaxMessageSizeType {
    type int32 {
      range "484 .. 2147483647";
    }
  }

  container SNMP-FRAMEWORK-MIB {
    config false;
    container snmpEngine {
      tailf:snmp-oid "1.3.6.1.6.3.10.2.1";
      leaf snmpEngineID {
        tailf:snmp-oid "1.3.6.1.6.3.10.2.1.1";
        type SnmpEngineID;
        config false;
      }
      leaf snmpEngineBoots {
        tailf:snmp-oid "1.3.6.1.6.3.10.2.1.2";
        type snmpEngineBootsType;
        config false;
      }
      leaf snmpEngineTime {
        tailf:snmp-oid "1.3.6.1.6.3.10.2.1.3";
        type snmpEngineTimeType;
        config false;
      }
      leaf snmpEngineMaxMessageSize {
        tailf:snmp-oid "1.3.6.1.6.3.10.2.1.4";
        type snmpEngineMaxMessageSizeType;
        config false;
      }
    }
  }
}
