submodule Cisco-IOS-XR-8000-platforms-npu-evict-voq-buff-oper-sub1 {
  belongs-to Cisco-IOS-XR-8000-platforms-npu-evict-voq-buff-oper {
    prefix Cisco-IOS-XR-8000-platforms-npu-evict-voq-buff-oper;
  }

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR 8000-platforms-npu-evict-voq-buff package operational data.

     Copyright (c) 2013-2019 by Cisco Systems, Inc.
     All rights reserved.";

  revision 2019-04-05 {
    semver:module-version "1.0.0";
    description
      "Establish semantic version baseline.";
  }
  revision 2015-11-09 {
    description
      "IOS XR 6.0 revision.";
  }

  grouping OFA-SYSDB-EVICT-VOQ-BUFF-USAGE {
    description
      "Per NPU structure for a evict voq usage";
    leaf tc {
      type uint8;
      description
        "tc";
    }
    leaf slice {
      type uint8;
      description
        "slice";
    }
    leaf voq-base {
      type uint32;
      description
        "voq base";
    }
    leaf buff-usage {
      type uint32;
      description
        "buff usage";
    }
    leaf in-bytes {
      type uint32;
      description
        "in bytes";
    }
    leaf ifhandle {
      type uint32;
      description
        "ifhandle";
    }
  }

  grouping OFA-SYSDB-EVICT-VOQ-BUFF-USAGE-ARRAY-ST {
    description
      "Resource level information";
    leaf max-voqs {
      type uint32;
      description
        "max voqs";
    }
    leaf device-id {
      type uint8;
      description
        "device id";
    }
    leaf slot {
      type uint8;
      description
        "slot";
    }
    list entry {
      description
        "entry";
      uses OFA-SYSDB-EVICT-VOQ-BUFF-USAGE;
    }
  }
}
