module Cisco-IOS-XR-ip-pfilter-subscriber-cfg {
  namespace "http://cisco.com/ns/yang/Cisco-IOS-XR-ip-pfilter-subscriber-cfg";
  prefix ip-pfilter-subscriber-cfg;

  import Cisco-IOS-XR-types {
    prefix xr;
  }
  import cisco-semver {
    prefix semver;
  }
  import Cisco-IOS-XR-subscriber-infra-tmplmgr-cfg {
    prefix a1;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ip-pfilter-subscriber package configuration.

     This YANG module augments the
       Cisco-IOS-XR-subscriber-infra-tmplmgr-cfg
     module with configuration data.

     Copyright (c) 2013-2019 by Cisco Systems, Inc.
     All rights reserved.";

  revision 2019-04-05 {
    semver:module-version "1.0.0";
    description
      "Establish semantic version baseline.";
  }
  revision 2015-11-09 {
    description
      "IOS XR 6.0 revision.";
  }

  grouping IPV6-PACKET-FILTER {
    description
      "Common node of ppp, subscriber-service,
       ip-subscriber";
    container ipv6-packet-filter {
      description
        "IPv6 Packet Filtering configuration for the
         interface";
      container inbound {
        description
          "IPv6 Packet filter to be applied to inbound
           packets";
        leaf common-acl-name {
          type xr:Cisco-ios-xr-string {
            length "1..64";
          }
          description
            "Not supported (Leave unspecified).";
        }
        leaf name {
          type xr:Cisco-ios-xr-string {
            length "1..64";
          }
          description
            "IPv6 Packet Filter Name to be applied to
             Inbound  NOTE: This parameter is mandatory if
             'CommonACLName' is not specified.";
        }
        leaf interface-statistics {
          type empty;
          description
            "Not supported (Leave unspecified).";
        }
      }
      container outbound {
        description
          "IPv6 Packet filter to be applied to outbound
           packets";
        leaf common-acl-name {
          type xr:Cisco-ios-xr-string {
            length "1..64";
          }
          description
            "Not supported (Leave unspecified).";
        }
        leaf name {
          type xr:Cisco-ios-xr-string {
            length "1..64";
          }
          description
            "IPv6 Packet Filter Name to be applied to
             Outbound packets.";
        }
        leaf interface-statistics {
          type empty;
          description
            "Not supported (Leave unspecified).";
        }
      }
    }
  }

  grouping IPV4-PACKET-FILTER {
    description
      "Common node of ppp, subscriber-service,
       ip-subscriber";
    container ipv4-packet-filter {
      description
        "IPv4 Packet Filtering configuration for the
         template";
      container outbound {
        description
          "IPv4 Packet filter to be applied to outbound
           packets";
        leaf common-acl-name {
          type xr:Cisco-ios-xr-string {
            length "1..64";
          }
          description
            "Not supported (Leave unspecified).";
        }
        leaf name {
          type xr:Cisco-ios-xr-string {
            length "1..64";
          }
          description
            "IPv4 Packet Filter Name to be applied to
             Outbound packets.";
        }
        leaf hardware-count {
          type empty;
          description
            "Not supported (Leave unspecified).";
        }
        leaf interface-statistics {
          type empty;
          description
            "Not supported (Leave unspecified).";
        }
      }
      container inbound {
        description
          "IPv4 Packet filter to be applied to inbound
           packets";
        leaf common-acl-name {
          type xr:Cisco-ios-xr-string {
            length "1..64";
          }
          description
            "Not supported (Leave unspecified).";
        }
        leaf name {
          type xr:Cisco-ios-xr-string {
            length "1..64";
          }
          description
            "IPv4 Packet Filter Name to be applied to
             Inbound packets NOTE: This parameter is
             mandatory if 'CommonACLName' is not specified.";
        }
        leaf hardware-count {
          type empty;
          description
            "Not supported (Leave unspecified).";
        }
        leaf interface-statistics {
          type empty;
          description
            "Not supported (Leave unspecified).";
        }
      }
    }
  }

  augment "/a1:dynamic-template/a1:ip-subscribers/a1:ip-subscriber" {
    description
      "This augment extends the configuration data of
       'Cisco-IOS-XR-subscriber-infra-tmplmgr-cfg'";
    uses IPV4-PACKET-FILTER;
  }
  augment "/a1:dynamic-template/a1:subscriber-services/a1:subscriber-service" {
    description
      "This augment extends the configuration data of
       'Cisco-IOS-XR-subscriber-infra-tmplmgr-cfg'";
    uses IPV4-PACKET-FILTER;
  }
  augment "/a1:dynamic-template/a1:ppps/a1:ppp" {
    description
      "This augment extends the configuration data of
       'Cisco-IOS-XR-subscriber-infra-tmplmgr-cfg'";
    uses IPV4-PACKET-FILTER;
  }
  augment "/a1:dynamic-template/a1:ip-subscribers/a1:ip-subscriber" {
    description
      "This augment extends the configuration data of
       'Cisco-IOS-XR-subscriber-infra-tmplmgr-cfg'";
    uses IPV6-PACKET-FILTER;
  }
  augment "/a1:dynamic-template/a1:subscriber-services/a1:subscriber-service" {
    description
      "This augment extends the configuration data of
       'Cisco-IOS-XR-subscriber-infra-tmplmgr-cfg'";
    uses IPV6-PACKET-FILTER;
  }
  augment "/a1:dynamic-template/a1:ppps/a1:ppp" {
    description
      "This augment extends the configuration data of
       'Cisco-IOS-XR-subscriber-infra-tmplmgr-cfg'";
    uses IPV6-PACKET-FILTER;
  }
}
