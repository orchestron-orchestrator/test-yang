module Cisco-IOS-XR-yiny-oper {
  namespace "http://cisco.com/ns/yang/Cisco-IOS-XR-yiny-oper";
  prefix yiny-oper;

  import cisco-semver {
    prefix semver;
  }
  import Cisco-IOS-XR-config-cfgmgr-oper {
    prefix a1;
  }

  include Cisco-IOS-XR-yiny-oper-sub1 {
    revision-date 2019-04-05;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR yiny package operational data.

     This YANG module augments the
       Cisco-IOS-XR-config-cfgmgr-oper
     module with state data.

     Copyright (c) 2013-2019 by Cisco Systems, Inc.
     All rights reserved.";

  revision 2019-04-05 {
    semver:module-version "1.0.0";
    description
      "Establish semantic version baseline.";
  }
  revision 2015-11-09 {
    description
      "IOS XR 6.0 revision.";
  }

  augment "/a1:config" {
    description
      "This augment extends the operational data of
       'Cisco-IOS-XR-config-cfgmgr-oper'";
    container out-of-sync-items {
      description
        "Inconsistencies between the OpenConfig
         configuration store and the device's running
         configuration, caused by errors encountered when
         attempting to apply the OpenConfig configuration";
      uses YINY-OPER-BAG-OOS-ITEMS-BAG;
    }
  }
}
