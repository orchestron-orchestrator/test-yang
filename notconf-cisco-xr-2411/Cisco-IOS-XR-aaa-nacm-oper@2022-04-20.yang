module Cisco-IOS-XR-aaa-nacm-oper {
  namespace "http://cisco.com/ns/yang/Cisco-IOS-XR-aaa-nacm-oper";
  prefix aaa-nacm-oper;

  import Cisco-IOS-XR-types {
    prefix xr;
  }
  import cisco-semver {
    prefix semver;
  }

  include Cisco-IOS-XR-aaa-nacm-oper-sub1 {
    revision-date 2022-04-20;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR aaa-nacm package operational data.

     This module contains definitions
     for the following management objects:
       aaa-nacm: AAA Nacm Information

     Copyright (c) 2013-2022 by Cisco Systems, Inc.
     All rights reserved.";

  revision 2022-04-20 {
    semver:module-version "1.1.0";
    description
      "Added nacm enable-dynamic CLI.";
  }
  revision 2019-04-05 {
    semver:module-version "1.0.1";
    description
      "Establish semantic version baseline.";
  }
  revision 2015-11-09 {
    description
      "IOS XR 6.0 revision.";
  }

  container aaa-nacm {
    config false;
    description
      "AAA Nacm Information";
    container counters {
      description
        "AAA NACM summary";
      uses NACM-COUNTERS;
    }
    container users {
      description
        "AAA NACM User summary";
      list user {
        key "user";
        description
          "AAA NACM User detail";
        leaf user {
          type xr:Cisco-ios-xr-string {
            length "1..256";
          }
          description
            "User";
        }
        uses NACM-USER-DETAIL;
      }
    }
    container summary {
      description
        "AAA NACM summary";
      uses NACM-SUMMARY;
    }
    container rules {
      description
        "AAA NACM Rulelist summary";
      list rule {
        description
          "AAA NACM Rulelist detail";
        container rulelist-rules {
          description
            "AAA NACM Rulelist detail";
          list rulelist-rule {
            key "rule";
            description
              "AAA NACM Rulelist detail";
            leaf rule {
              type xr:Cisco-ios-xr-string {
                length "1..256";
              }
              description
                "Rule";
            }
            uses NACM-RULE-DETAIL;
          }
        }
        leaf ordering-index {
          type xr:Cisco-ios-xr-string {
            length "1..256";
          }
          description
            "Rulelist Ordering Index";
        }
        leaf rulelist-name {
          type xr:Cisco-ios-xr-string {
            length "1..256";
          }
          description
            "Rulelist Name";
        }
      }
    }
    container groups {
      description
        "AAA NACM Group summary";
      list group {
        key "group";
        description
          "AAA NACM Group detail";
        leaf group {
          type xr:Cisco-ios-xr-string {
            length "1..256";
          }
          description
            "Group";
        }
        uses NACM-GROUP-DETAIL;
      }
    }
  }
}
