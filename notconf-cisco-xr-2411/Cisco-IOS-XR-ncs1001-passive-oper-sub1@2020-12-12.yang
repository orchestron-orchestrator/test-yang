submodule Cisco-IOS-XR-ncs1001-passive-oper-sub1 {
  belongs-to Cisco-IOS-XR-ncs1001-passive-oper {
    prefix Cisco-IOS-XR-ncs1001-passive-oper;
  }

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR ncs1001-passive package operational data.

     Copyright (c) 2013-2020 by Cisco Systems, Inc.
     All rights reserved.";

  revision 2020-12-12 {
    semver:module-version "1.0.0";
    description
      "XML query for CLI show hw-module ampli-trail-view/channel-trail-view does not return a response";
  }
  revision 2019-04-05 {
    description
      "Establish semantic version baseline.";
  }
  revision 2015-11-09 {
    description
      "IOS XR 6.0 revision.";
  }

  grouping HWMOD-PASSIVE-EEPROM-IL-LIST-B {
    description
      "Passive il list";
    leaf from {
      type string {
        length "0..32";
      }
      description
        "from value";
    }
    leaf to {
      type string {
        length "0..32";
      }
      description
        "to value";
    }
    leaf il-int {
      type uint8;
      description
        "insertion loss inte part";
    }
    leaf il-dec {
      type uint8;
      description
        "insertion loss dec  part";
    }
  }

  grouping HWMOD-PASSIVE-EEPROM-DATA-B {
    description
      "Passive Eeprom ascii";
    leaf eeprom-image {
      type string {
        length "0..8192";
      }
      description
        "Eeprom Image in ascii format";
    }
  }

  grouping OTS-HWMOD-PASSIVE-EEPROM-OP {
    description
      "HwModule Passive Eeprom";
    list passive-eeprom-data {
      description
        "Passive Eeprom Data";
      uses HWMOD-PASSIVE-EEPROM-DATA-B;
    }
    list passive-eeprom-il {
      description
        "Passive Eeprom Il list";
      uses HWMOD-PASSIVE-EEPROM-IL-LIST-B;
    }
  }
}
