module SNMP-USER-BASED-SM-MIB {
  namespace "http://tail-f.com/ns/mibs/SNMP-USER-BASED-SM-MIB/200210160000Z";
  prefix SNMP_USER_BASED_SM_MIB;

  import ietf-yang-types {
    prefix yang;
  }
  import tailf-common {
    prefix tailf;
  }
  import SNMPv2-TC {
    prefix SNMPv2_TC;
  }
  import SNMP-FRAMEWORK-MIB {
    prefix SNMP_FRAMEWORK_MIB;
  }

  revision 2002-10-16 {
    description
      "";
  }

  tailf:id "";
  tailf:snmp-mib-module-name "SNMP-USER-BASED-SM-MIB";

  typedef KeyChange {
    type tailf:hex-list {
      pattern "(((([0-9A-Fa-f]{2}):)*([0-9A-Fa-f]{2}))){0,1}";
    }
  }

  typedef usmUserNameType {
    type string {
      length "1 .. 32";
    }
  }

  typedef usmUserPublicType {
    type tailf:hex-list {
      tailf:value-length "min .. 32";
      pattern "(((([0-9A-Fa-f]{2}):){0,31}([0-9A-Fa-f]{2}))){0,1}";
    }
  }

  container SNMP-USER-BASED-SM-MIB {
    container usmStats {
      tailf:snmp-oid "1.3.6.1.6.3.15.1.1";
      config false;
      leaf usmStatsUnsupportedSecLevels {
        tailf:snmp-oid "1.3.6.1.6.3.15.1.1.1";
        type yang:counter32;
        config false;
      }
      leaf usmStatsNotInTimeWindows {
        tailf:snmp-oid "1.3.6.1.6.3.15.1.1.2";
        type yang:counter32;
        config false;
      }
      leaf usmStatsUnknownUserNames {
        tailf:snmp-oid "1.3.6.1.6.3.15.1.1.3";
        type yang:counter32;
        config false;
      }
      leaf usmStatsUnknownEngineIDs {
        tailf:snmp-oid "1.3.6.1.6.3.15.1.1.4";
        type yang:counter32;
        config false;
      }
      leaf usmStatsWrongDigests {
        tailf:snmp-oid "1.3.6.1.6.3.15.1.1.5";
        type yang:counter32;
        config false;
      }
      leaf usmStatsDecryptionErrors {
        tailf:snmp-oid "1.3.6.1.6.3.15.1.1.6";
        type yang:counter32;
        config false;
      }
    }
    container usmUserTable {
      list usmUserEntry {
        tailf:sort-order "snmp";
        tailf:snmp-oid "1.3.6.1.6.3.15.1.2.2";
        key "usmUserEngineID usmUserName";
        unique "usmUserEngineID usmUserSecurityName";
        leaf usmUserEngineID {
          tailf:snmp-oid "1.3.6.1.6.3.15.1.2.2.1.1";
          type SNMP_FRAMEWORK_MIB:SnmpEngineID;
        }
        leaf usmUserName {
          tailf:snmp-oid "1.3.6.1.6.3.15.1.2.2.1.2";
          type usmUserNameType;
        }
        leaf usmUserSecurityName {
          tailf:snmp-oid "1.3.6.1.6.3.15.1.2.2.1.3";
          type SNMP_FRAMEWORK_MIB:SnmpAdminString;
          mandatory true;
        }
        leaf usmUserCloneFrom {
          tailf:snmp-oid "1.3.6.1.6.3.15.1.2.2.1.4";
          type SNMPv2_TC:RowPointer;
        }
        leaf usmUserAuthProtocol {
          tailf:snmp-oid "1.3.6.1.6.3.15.1.2.2.1.5";
          type SNMPv2_TC:AutonomousType;
          default "1.3.6.1.6.3.10.1.1.1";
        }
        leaf usmUserAuthKeyChange {
          tailf:snmp-oid "1.3.6.1.6.3.15.1.2.2.1.6";
          type KeyChange;
        }
        leaf usmUserOwnAuthKeyChange {
          tailf:snmp-oid "1.3.6.1.6.3.15.1.2.2.1.7";
          type KeyChange;
        }
        leaf usmUserPrivProtocol {
          tailf:snmp-oid "1.3.6.1.6.3.15.1.2.2.1.8";
          type SNMPv2_TC:AutonomousType;
          default "1.3.6.1.6.3.10.1.2.1";
        }
        leaf usmUserPrivKeyChange {
          tailf:snmp-oid "1.3.6.1.6.3.15.1.2.2.1.9";
          type KeyChange;
        }
        leaf usmUserOwnPrivKeyChange {
          tailf:snmp-oid "1.3.6.1.6.3.15.1.2.2.1.10";
          type KeyChange;
        }
        leaf usmUserPublic {
          tailf:snmp-oid "1.3.6.1.6.3.15.1.2.2.1.11";
          type usmUserPublicType;
        }
        leaf usmUserStorageType {
          tailf:snmp-oid "1.3.6.1.6.3.15.1.2.2.1.12";
          type SNMPv2_TC:StorageType;
          default "nonVolatile";
        }
        leaf usmUserAuthKey {
          type KeyChange;
        }
        leaf usmUserPrivKey {
          type KeyChange;
        }
      }
    }
  }
}
