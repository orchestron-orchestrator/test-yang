module Cisco-IOS-XR-uea-optics-driver-quad-cfg {
  namespace "http://cisco.com/ns/yang/Cisco-IOS-XR-uea-optics-driver-quad-cfg";
  prefix uea-optics-driver-quad-cfg;

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR uea-optics-driver-quad package configuration.

     This module contains definitions
     for the following management objects:
       node: HW module Quad Config

     Copyright (c) 2013-2020 by Cisco Systems, Inc.
     All rights reserved.";

  revision 2020-04-13 {
    semver:module-version "1.0.0";
    description
      "Schema added.";
  }
  revision 2019-04-05 {
    description
      "Establish semantic version baseline.";
  }
  revision 2015-11-09 {
    description
      "IOS XR 6.0 revision.";
  }

  container node {
    description
      "HW module Quad Config";
    container slot-configs {
      description
        "slot configuration";
      list slot-config {
        key "id2";
        description
          "none";
        container quad-configs {
          description
            "quad configuration";
          list quad-config {
            key "id1";
            description
              "none";
            container mode {
              description
                "select mode 10g or 25g or 50g for a
                 quad(group of 4 ports).";
              leaf speed {
                type string;
                description
                  "speed 10g or 25g or 50g";
              }
            }
            leaf id1 {
              type uint32;
              description
                "none";
            }
          }
        }
        leaf id2 {
          type uint32;
          description
            "none";
        }
      }
    }
  }
}
