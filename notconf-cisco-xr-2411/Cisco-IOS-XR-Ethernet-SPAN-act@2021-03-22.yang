module Cisco-IOS-XR-Ethernet-SPAN-act {
  namespace "http://cisco.com/ns/yang/Cisco-IOS-XR-Ethernet-SPAN-act";
  prefix ethernet-span-act;

  import Cisco-IOS-XR-types {
    prefix xr;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR Ethernet-SPAN action commands.

     Copyright (c) 2020-2021 by Cisco Systems, Inc.
     All rights reserved.";

  revision 2021-03-22 {
    semver:module-version "1.0.0";
    description
      "Remove unnecessary module imports
       2020-11-09
       First implementation of action yang for File destinations";
  }

  rpc packet-collection-start {
    xr:xr-task "ethernet-services";
    xr:cli-command "monitor-session <session> packet-collection start";
    description
      "Start packet collection on this session";

    input {
      leaf session {
        type string {
          length "1..63";
        }
        mandatory true;
        description
          "Session name";
      }
    }
  }
  rpc packet-collection-stop-discard {
    xr:xr-task "ethernet-services";
    xr:cli-command "monitor-session <session> packet-collection stop discard-data";
    description
      "Stop packet collection on this session and discard data in buffer";

    input {
      leaf session {
        type string {
          length "1..63";
        }
        mandatory true;
        description
          "Session name";
      }
    }
  }
  rpc packet-collection-stop-write {
    xr:xr-task "ethernet-services";
    xr:cli-command "monitor-session <session> packet-collection stop write directory <dirname> filename <filename>";
    description
      "Stop packet collection on this session and write contents to file";

    input {
      leaf session {
        type string {
          length "1..63";
        }
        mandatory true;
        description
          "Session name";
      }
      leaf dirname {
        type string {
          length "1..63";
        }
        mandatory true;
        description
          "Directory name";
      }
      leaf filename {
        type string {
          length "1..63";
        }
        mandatory true;
        description
          "File name";
      }
    }
  }
}
