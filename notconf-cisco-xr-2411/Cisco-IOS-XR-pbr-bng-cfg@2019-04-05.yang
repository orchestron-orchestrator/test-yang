module Cisco-IOS-XR-pbr-bng-cfg {
  namespace "http://cisco.com/ns/yang/Cisco-IOS-XR-pbr-bng-cfg";
  prefix pbr-bng-cfg;

  import Cisco-IOS-XR-types {
    prefix xr;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR pbr-bng package configuration.

     This module contains definitions
     for the following management objects:
       bng-pbr: Subscriber PBR configuration

     Copyright (c) 2013-2019 by Cisco Systems, Inc.
     All rights reserved.";

  revision 2019-04-05 {
    semver:module-version "1.0.0";
    description
      "Establish semantic version baseline.";
  }
  revision 2015-11-09 {
    description
      "IOS XR 6.0 revision.";
  }

  typedef Bng-pbr-http-enrichment-params {
    type enumeration {
      enum "subscriber-mac" {
        value 1;
        description
          "Subscriber Mac";
      }
      enum "subscriber-ip" {
        value 2;
        description
          "Subscriber IPv4/IPv6 address";
      }
      enum "host-name" {
        value 4;
        description
          "Bng Router Hostname";
      }
      enum "bng-identifier-interface" {
        value 8;
        description
          "Bng Identifier interface";
      }
    }
    description
      "Bng pbr http enrichment params";
  }

  container bng-pbr {
    description
      "Subscriber PBR configuration";
    container http-enrichment {
      description
        "HTTP Enrichment";
      container parameters {
        presence "Indicates a parameters node is configured.";
        description
          "HTTP Enrichment parameters";
        leaf arg1 {
          type Bng-pbr-http-enrichment-params;
          mandatory true;
          description
            "first argument ";
        }
        leaf arg2 {
          type Bng-pbr-http-enrichment-params;
          description
            "second argument ";
        }
        leaf arg3 {
          type Bng-pbr-http-enrichment-params;
          description
            "Third argument ";
        }
        leaf arg4 {
          type Bng-pbr-http-enrichment-params;
          description
            "Fourth argument ";
        }
      }
    }
    leaf bng-interface {
      type xr:Interface-name;
      description
        "Interface for source address";
    }
  }
}
