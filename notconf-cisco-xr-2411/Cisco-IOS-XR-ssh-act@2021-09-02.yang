module Cisco-IOS-XR-ssh-act {
  namespace "http://cisco.com/ns/yang/Cisco-IOS-XR-ssh-act";
  prefix ssh-act;

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR action package configuration.

     Copyright (c) 2021 by Cisco Systems, Inc.
     All rights reserved.";

  revision 2021-09-02 {
    semver:module-version "1.0.0";
    description
      "Action model for SSH";
  }

  rpc clear-ssh-session {
    description
      "clears specific incoming session based on the session id";

    input {
      leaf incoming-session-id {
        type uint32 {
          range "1..4294967295";
        }
        description
          "incoming session id";
      }
    }
  }
  rpc clear-ssh-all {
    description
      "clears all incoming SSH session";
  }

  rpc clear-ssh-outgoing-session {
    description
      "Disconnect client connection";

    input {
      leaf outgoing-session-id {
        type uint32 {
          range "1..4294967295";
        }
        description
          "outgoing session id";
      }
    }
  }
  rpc clear-ssh-stale-session {
    description
      "clear stale incoming SSH sessions";
  }
}
