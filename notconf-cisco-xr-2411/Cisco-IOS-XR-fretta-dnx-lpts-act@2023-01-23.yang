module Cisco-IOS-XR-fretta-dnx-lpts-act {
  namespace "http://cisco.com/ns/yang/Cisco-IOS-XR-fretta-dnx-lpts-act";
  prefix fretta-dnx-lpts-act;

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR fretta-dnx-lpts package action data to clear stats.

     Copyright (c) 2022-2023 by Cisco Systems, Inc.
     All rights reserved.";

  revision 2023-01-23 {
    description
      "Initial revision.";
  }

  rpc clear-lpts-pifib-hardware-statistics-location {
    description
      "Clear lpts pifib hardware statistics location";

    input {
      leaf node-location {
        type string;
        mandatory true;
        description
          "Node location";
      }
    }
  }
}
