submodule Cisco-IOS-XR-coherent-portmode-oper-sub1 {
  belongs-to Cisco-IOS-XR-coherent-portmode-oper {
    prefix Cisco-IOS-XR-coherent-portmode-oper;
  }

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR coherent-portmode package operational data.

     Copyright (c) 2013-2021 by Cisco Systems, Inc.
     All rights reserved.";

  revision 2021-03-03 {
    semver:module-version "1.1.0";
    description
      "for portmode oper data.";
  }
  revision 2019-04-05 {
    semver:module-version "1.0.0";
    description
      "Establish semantic version baseline.";
  }
  revision 2015-11-09 {
    description
      "IOS XR 6.0 revision.";
  }

  grouping PORTMODE-INFO {
    description
      "portmode entry of optics controller";
    leaf intf-name {
      type string {
        length "0..128";
      }
      description
        "intf name";
    }
    leaf speed {
      type string {
        length "0..128";
      }
      description
        "speed";
    }
    leaf fec {
      type string {
        length "0..128";
      }
      description
        "fec";
    }
    leaf diff {
      type string {
        length "0..128";
      }
      description
        "diff";
    }
    leaf modulation {
      type string {
        length "0..128";
      }
      description
        "modulation";
    }
    leaf client-mode {
      type string {
        length "0..128";
      }
      description
        "client mode";
    }
    leaf dac-rate {
      type string {
        length "0..128";
      }
      description
        "dac rate";
    }
  }
}
