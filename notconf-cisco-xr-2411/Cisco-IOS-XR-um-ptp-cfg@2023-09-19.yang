module Cisco-IOS-XR-um-ptp-cfg {
  namespace "http://cisco.com/ns/yang/Cisco-IOS-XR-um-ptp-cfg";
  prefix um-ptp-cfg;

  import Cisco-IOS-XR-types {
    prefix xr;
  }
  import ietf-inet-types {
    prefix inet;
  }
  import ietf-yang-types {
    prefix yang;
  }
  import Cisco-IOS-XR-um-interface-cfg {
    prefix a1;
  }
  import Cisco-IOS-XR-um-snmp-server-cfg {
    prefix a2;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ptp package configuration.

     This YANG module augments the
     modules with configuration data.

     Copyright (c) 2023 by Cisco Systems, Inc.
     All rights reserved.";

  revision 2023-09-19 {
    semver:module-version "2.0.0";
    description
      "Added PTP phase difference config options
       2022-07-11
         Added missing description statement to nodes
       2021-12-23
         Added leaf double-failure-clock-class";
  }
  revision 2020-12-11 {
    semver:module-version "1.0.0";
    description
      "Initial release";
  }

  grouping IF-BODY {
    description
      "Grouping for interface";
    container ptp {
      presence "Indicates a ptp node is configured.";
      description
        "Precision Time Protocol config";
      leaf profile {
        type xr:Cisco-ios-xr-string {
          length "1..800" {
            description
              "Name of Profile";
          }
        }
        description
          "PTP Profile to use on this interface";
      }
      container transport {
        description
          "PTP transport type to use on this interface";
        container ipv4 {
          must "not(../ethernet or ../ipv6)";
          presence "Indicates a ipv4 node is configured.";
          description
            "IPv4 transport";
        }
        container ethernet {
          must "not(../ipv4 or ../ipv6)";
          presence "Indicates a ethernet node is configured.";
          description
            "Ethernet transport";
        }
        container ipv6 {
          must "not(../ipv4 or ../ethernet)";
          presence "Indicates a ipv6 node is configured.";
          description
            "IPv6 transport";
        }
      }
      container clock {
        description
          "PTP clock-operation to use";
        container operation {
          description
            "PTP clock-operation to use";
          container one-step {
            must "not(../two-step)";
            presence "Indicates a one-step node is configured.";
            description
              "One-step clock-operation";
          }
          container two-step {
            must "not(../one-step)";
            presence "Indicates a two-step node is configured.";
            description
              "Two-step clock-operation";
          }
        }
      }
      container announce {
        description
          "Announce message options";
        leaf interval {
          type enumeration {
            enum "1" {
              value 0;
              description
                "One second interval";
            }
            enum "2" {
              value 1;
              description
                "Two second interval";
            }
            enum "4" {
              value 2;
              description
                "Four second interval";
            }
            enum "8" {
              value 3;
              description
                "Eight second interval";
            }
            enum "16" {
              value 4;
              description
                "Sixteen second interval";
            }
            enum "32" {
              value 5;
              description
                "Thirty Two second interval";
            }
            enum "64" {
              value 6;
              description
                "Sixty Four second interval";
            }
            enum "128" {
              value 7;
              description
                "One Hundred and Twenty Eight second interval";
            }
          }
          must "not(../frequency)";
          description
            "Send Announce messages once every one or more seconds";
        }
        leaf frequency {
          type enumeration {
            enum "1" {
              value 0;
              description
                "One per second frequency";
            }
            enum "2" {
              value 1;
              description
                "Two per second frequency";
            }
            enum "4" {
              value 2;
              description
                "Four per second frequency";
            }
            enum "8" {
              value 3;
              description
                "Eight per second frequency";
            }
            enum "16" {
              value 4;
              description
                "Sixteen per second frequency";
            }
            enum "32" {
              value 5;
              description
                "Thirty Two per second frequency";
            }
            enum "64" {
              value 6;
              description
                "Sixty Four second frequency";
            }
            enum "128" {
              value 7;
              description
                "One Hundred and Twenty Eight second frequency";
            }
          }
          must "not(../interval)";
          description
            "Send Announce messages one or more times a second";
        }
        leaf timeout {
          type uint32 {
            range "2..10" {
              description
                "The number of announce intervals before timeout";
            }
          }
          description
            "Configure the announce timeout value";
        }
        leaf grant-duration {
          type uint32 {
            range "60..1000" {
              description
                "The grant duration, in seconds";
            }
          }
          description
            "Configure the announce unicast grant duration value";
        }
      }
      container sync {
        description
          "Sync message options";
        leaf interval {
          type enumeration {
            enum "1" {
              value 0;
              description
                "One second interval";
            }
            enum "2" {
              value 1;
              description
                "Two second interval";
            }
            enum "4" {
              value 2;
              description
                "Four second interval";
            }
            enum "8" {
              value 3;
              description
                "Eight second interval";
            }
            enum "16" {
              value 4;
              description
                "Sixteen second interval";
            }
            enum "32" {
              value 5;
              description
                "Thirty Two second interval";
            }
            enum "64" {
              value 6;
              description
                "Sixty Four second interval";
            }
            enum "128" {
              value 7;
              description
                "One Hundred and Twenty Eight second interval";
            }
          }
          must "not(../frequency)";
          description
            "Send Announce messages once every one or more seconds";
        }
        leaf frequency {
          type enumeration {
            enum "1" {
              value 0;
              description
                "One per second frequency";
            }
            enum "2" {
              value 1;
              description
                "Two per second frequency";
            }
            enum "4" {
              value 2;
              description
                "Four per second frequency";
            }
            enum "8" {
              value 3;
              description
                "Eight per second frequency";
            }
            enum "16" {
              value 4;
              description
                "Sixteen per second frequency";
            }
            enum "32" {
              value 5;
              description
                "Thirty Two per second frequency";
            }
            enum "64" {
              value 6;
              description
                "Sixty Four second frequency";
            }
            enum "128" {
              value 7;
              description
                "One Hundred and Twenty Eight second frequency";
            }
          }
          must "not(../interval)";
          description
            "Send Announce messages one or more times a second";
        }
        leaf grant-duration {
          type uint32 {
            range "60..1000" {
              description
                "The grant duration, in seconds";
            }
          }
          description
            "Configure the sync unicast grant duration value";
        }
        leaf timeout {
          type uint32 {
            range "100..100000" {
              description
                "The timeout value, in milliseconds";
            }
          }
          description
            "Configure the sync timeout value";
        }
      }
      container delay-request {
        description
          "Configure the sending of delay-request messages";
        leaf interval {
          type enumeration {
            enum "1" {
              value 0;
              description
                "One second interval";
            }
            enum "2" {
              value 1;
              description
                "Two second interval";
            }
            enum "4" {
              value 2;
              description
                "Four second interval";
            }
            enum "8" {
              value 3;
              description
                "Eight second interval";
            }
            enum "16" {
              value 4;
              description
                "Sixteen second interval";
            }
            enum "32" {
              value 5;
              description
                "Thirty Two second interval";
            }
            enum "64" {
              value 6;
              description
                "Sixty Four second interval";
            }
            enum "128" {
              value 7;
              description
                "One Hundred and Twenty Eight second interval";
            }
          }
          must "not(../frequency)";
          description
            "Send Announce messages once every one or more seconds";
        }
        leaf frequency {
          type enumeration {
            enum "1" {
              value 0;
              description
                "One per second frequency";
            }
            enum "2" {
              value 1;
              description
                "Two per second frequency";
            }
            enum "4" {
              value 2;
              description
                "Four per second frequency";
            }
            enum "8" {
              value 3;
              description
                "Eight per second frequency";
            }
            enum "16" {
              value 4;
              description
                "Sixteen per second frequency";
            }
            enum "32" {
              value 5;
              description
                "Thirty Two per second frequency";
            }
            enum "64" {
              value 6;
              description
                "Sixty Four second frequency";
            }
            enum "128" {
              value 7;
              description
                "One Hundred and Twenty Eight second frequency";
            }
          }
          must "not(../interval)";
          description
            "Send Announce messages one or more times a second";
        }
      }
      leaf cos {
        type uint32 {
          range "0..7" {
            description
              "The COS value to use";
          }
        }
        description
          "Specify the COS value to use";
      }
      leaf event-cos {
        type uint32 {
          range "0..7" {
            description
              "The COS value to use";
          }
        }
        description
          "Specify the COS value to use";
      }
      leaf general-cos {
        type uint32 {
          range "0..7" {
            description
              "The COS value to use";
          }
        }
        description
          "Specify the COS value to use";
      }
      leaf dscp {
        type uint32 {
          range "0..63" {
            description
              "The DSCP value to use";
          }
        }
        description
          "Specify the DSCP value to use";
      }
      leaf event-dscp {
        type uint32 {
          range "0..63" {
            description
              "The DSCP value to use";
          }
        }
        description
          "Specify the DSCP value to use";
      }
      leaf general-dscp {
        type uint32 {
          range "0..63" {
            description
              "The DSCP value to use";
          }
        }
        description
          "Specify the DSCP value to use";
      }
      leaf ipv4-ttl {
        type uint32 {
          range "1..255" {
            description
              "The IPv4 TTL value to use";
          }
        }
        description
          "Specify the IPv4 TTL value to use";
      }
      leaf ipv6-hop-limit {
        type uint32 {
          range "1..255" {
            description
              "The IPv6 hop limit value to use";
          }
        }
        description
          "Specify the IPv6 hop limit value to use";
      }
      leaf delay-asymmetry {
        type int32 {
          range "-500000000..500000000" {
            description
              "How much longer the primary to subordinate path takes than the reverse";
          }
        }
        description
          "Delay asymmetry to apply to all primarys on the interface";
      }
      container nanoseconds {
        must "not(../microseconds or ../milliseconds)";
        presence "Indicates a nanoseconds node is configured.";
        description
          "Use nanoseconds as the delay asymmetry units";
      }
      container microseconds {
        must "not(../nanoseconds or ../milliseconds)";
        presence "Indicates a microseconds node is configured.";
        description
          "Use microseconds as the delay asymmetry units";
      }
      container milliseconds {
        must "not(../nanoseconds or ../microseconds)";
        presence "Indicates a milliseconds node is configured.";
        description
          "Use milliseconds as the delay asymmetry units";
      }
      container delay-response {
        description
          "Delay-Response message options";
        leaf grant-duration {
          type uint32 {
            range "60..1000" {
              description
                "The grant duration, in seconds";
            }
          }
          description
            "Configure the delay-response unicast grant duration value";
        }
        leaf timeout {
          type uint32 {
            range "100..100000" {
              description
                "The timeout value, in milliseconds";
            }
          }
          description
            "Configure the delay-response timeout value";
        }
      }
      container unicast-grant {
        description
          "Unicast grant options";
        container invalid-request {
          description
            "Configure the response to invalid unicast requests";
          container reduce {
            must "not(../deny)";
            presence "Indicates a reduce node is configured.";
            description
              "Reduce grant parameters";
          }
          container deny {
            must "not(../reduce)";
            presence "Indicates a deny node is configured.";
            description
              "Deny grant";
          }
        }
      }
      container multicast {
        presence "Indicates a multicast node is configured.";
        description
          "Allow multicast messages to be sent";
        container mixed {
          must "not(../disable)";
          presence "Indicates a mixed node is configured.";
          description
            "Mixed-mode multicast";
        }
        container disable {
          must "not(../mixed)";
          presence "Indicates a disable node is configured.";
          description
            "Disable multicast transport";
        }
        container target-address {
          must "ethernet/mac-address-01-1b-19-00-00-00 or ethernet/mac-address-01-80-c2-00-00-0e";
          presence "Indicates a target-address node is configured.";
          description
            "Configure a target address";
          container ethernet {
            description
              "Configure ethernet target address";
            container mac-address-01-1b-19-00-00-00 {
              must "not(../mac-address-01-80-c2-00-00-0e)";
              presence "Indicates a mac-address-01-1b-19-00-00-00 node is configured.";
              description
                "Forwardable mac-address";
            }
            container mac-address-01-80-c2-00-00-0e {
              must "not(../mac-address-01-1b-19-00-00-00)";
              presence "Indicates a mac-address-01-80-c2-00-00-0e node is configured.";
              description
                "Non-forwardable mac-address";
            }
          }
        }
      }
      container port {
        description
          "PTP port options";
        container state {
          description
            "Restrict the port state of this interface";
          container subordinate-only {
            must "not(../primary-only or ../any)";
            presence "Indicates a subordinate-only node is configured.";
            description
              "Restrict the port state to subordinate";
          }
          container primary-only {
            must "not(../subordinate-only or ../any)";
            presence "Indicates a primary-only node is configured.";
            description
              "Restrict the port state to primary";
          }
          container any {
            must "not(../subordinate-only or ../primary-only)";
            presence "Indicates a any node is configured.";
            description
              "Unrestrict the port state on this interface";
          }
        }
      }
      container source {
        description
          "PTP source address options";
        container ipv4 {
          description
            "PTP source IPv4 address options";
          container address {
            description
              "Set the IPv4 address to use when sending IPv4 packets";
            container disable {
              must "not(../ipv4-address)";
              presence "Indicates a disable node is configured.";
              description
                "Use the interface IPv4 address";
            }
            leaf ipv4-address {
              type inet:ipv4-address-no-zone;
              must "not(../disable)";
              description
                "Specify the IPv4 address to use";
            }
          }
        }
        container ipv6 {
          description
            "PTP source IPv6 address options";
          container address {
            description
              "Set the IPv6 address to use when sending IPv6 packets";
            container disable {
              must "not(../ipv6-address)";
              presence "Indicates a disable node is configured.";
              description
                "Use the interface IPv6 address";
            }
            leaf ipv6-address {
              type inet:ipv6-address-no-zone;
              must "not(../disable)";
              description
                "Set the IPv6 address to use when sending IPv6 packets";
            }
          }
        }
      }
      leaf local-priority {
        type uint32 {
          range "1..255" {
            description
              "The local priority value to use";
          }
        }
        description
          "Configure a local priority";
      }
      container subordinate {
        description
          "Add a subordinate to announce to on this interface";
        container ipv4s {
          description
            "IPv4 address";
          list ipv4-non-negotiated {
            must "non-negotiated";
            key "address";
            description
              "IPv4 address";
            leaf address {
              type inet:ipv4-address-no-zone;
              description
                "IPv4 address";
            }
            container non-negotiated {
              presence "Indicates a non-negotiated node is configured.";
              description
                "Use non-negotiated unicast";
            }
          }
        }
        container ipv6s {
          description
            "IPv6 address";
          list ipv6 {
            key "address";
            description
              "IPv6 address";
            leaf address {
              type inet:ipv6-address-no-zone;
              description
                "IPv6 address";
            }
            container non-negotiated {
              presence "Indicates a non-negotiated node is configured.";
              description
                "Use non-negotiated unicast";
            }
          }
        }
        container ethernets {
          description
            "Ethernet address";
          list ethernet {
            must "non-negotiated";
            key "address";
            description
              "Ethernet address";
            leaf address {
              type yang:mac-address;
              description
                "Ethernet address";
            }
            container non-negotiated {
              presence "Indicates a non-negotiated node is configured.";
              description
                "Use non-negotiated unicast";
            }
          }
        }
      }
      container primary {
        description
          "Add a primary to listen to on this interface";
        container ipv4s {
          description
            "IPv4 address";
          list ipv4 {
            key "address";
            description
              "IPv4 address";
            leaf address {
              type inet:ipv4-address-no-zone;
              description
                "IPv4 address";
            }
            leaf priority {
              type uint32 {
                range "0..255" {
                  description
                    "The local priority value to use for this primary";
                }
              }
              description
                "Specify the priority of this primary";
            }
            leaf clock-class {
              type uint32 {
                range "0..255" {
                  description
                    "The clock class to use for this primary";
                }
              }
              description
                "Override the clock-class of this primary";
            }
            container multicast {
              presence "Indicates a multicast node is configured.";
              description
                "Whether this primary sends messages multicast";
              container mixed {
                presence "Indicates a mixed node is configured.";
                description
                  "Mixed-mode multicast";
              }
            }
            container non-negotiated {
              presence "Indicates a non-negotiated node is configured.";
              description
                "Use non-negotiated unicast";
            }
            leaf delay-asymmetry {
              type int32 {
                range "-500000000..500000000" {
                  description
                    "How much longer the primary to subordinate path takes than the reverse";
                }
              }
              description
                "The expected delay asymmetry for this primary";
            }
            container nanoseconds {
              must "not(../microseconds or ../milliseconds)";
              presence "Indicates a nanoseconds node is configured.";
              description
                "Use nanoseconds as the delay asymmetry units";
            }
            container microseconds {
              must "not(../nanoseconds or ../milliseconds)";
              presence "Indicates a microseconds node is configured.";
              description
                "Use microseconds as the delay asymmetry units";
            }
            container milliseconds {
              must "not(../nanoseconds or ../microseconds)";
              presence "Indicates a milliseconds node is configured.";
              description
                "Use milliseconds as the delay asymmetry units";
            }
          }
        }
        container ipv6s {
          description
            "IPv6 address";
          list ipv6 {
            key "address";
            description
              "IPv6 address";
            leaf address {
              type inet:ipv6-address-no-zone;
              description
                "IPv6 address";
            }
            leaf priority {
              type uint32 {
                range "0..255" {
                  description
                    "The local priority value to use for this primary";
                }
              }
              description
                "Specify the priority of this primary";
            }
            leaf clock-class {
              type uint32 {
                range "0..255" {
                  description
                    "The clock class to use for this primary";
                }
              }
              description
                "Override the clock-class of this primary";
            }
            container multicast {
              presence "Indicates a multicast node is configured.";
              description
                "Whether this primary sends messages multicast";
              container mixed {
                presence "Indicates a mixed node is configured.";
                description
                  "Mixed-mode multicast";
              }
            }
            container non-negotiated {
              presence "Indicates a non-negotiated node is configured.";
              description
                "Use non-negotiated unicast";
            }
            leaf delay-asymmetry {
              type int32 {
                range "-500000000..500000000" {
                  description
                    "How much longer the primary to subordinate path takes than the reverse";
                }
              }
              description
                "The expected delay asymmetry for this primary";
            }
            container nanoseconds {
              must "not(../microseconds or ../milliseconds)";
              presence "Indicates a nanoseconds node is configured.";
              description
                "Use nanoseconds as the delay asymmetry units";
            }
            container microseconds {
              must "not(../nanoseconds or ../milliseconds)";
              presence "Indicates a microseconds node is configured.";
              description
                "Use microseconds as the delay asymmetry units";
            }
            container milliseconds {
              must "not(../nanoseconds or ../microseconds)";
              presence "Indicates a milliseconds node is configured.";
              description
                "Use milliseconds as the delay asymmetry units";
            }
          }
        }
        container ethernets {
          description
            "Ethernet address";
          list ethernet {
            key "address";
            description
              "Ethernet address";
            leaf address {
              type yang:mac-address;
              description
                "Ethernet address";
            }
            leaf priority {
              type uint32 {
                range "0..255" {
                  description
                    "The local priority value to use for this primary";
                }
              }
              description
                "Specify the priority of this primary";
            }
            leaf clock-class {
              type uint32 {
                range "0..255" {
                  description
                    "The clock class to use for this primary";
                }
              }
              description
                "Override the clock-class of this primary";
            }
            container multicast {
              presence "Indicates a multicast node is configured.";
              description
                "Whether this primary sends messages multicast";
              container mixed {
                presence "Indicates a mixed node is configured.";
                description
                  "Mixed-mode multicast";
              }
            }
            container non-negotiated {
              presence "Indicates a non-negotiated node is configured.";
              description
                "Use non-negotiated unicast";
            }
            leaf delay-asymmetry {
              type int32 {
                range "-500000000..500000000" {
                  description
                    "How much longer the primary to subordinate path takes than the reverse";
                }
              }
              description
                "The expected delay asymmetry for this primary";
            }
            container nanoseconds {
              must "not(../microseconds or ../milliseconds)";
              presence "Indicates a nanoseconds node is configured.";
              description
                "Use nanoseconds as the delay asymmetry units";
            }
            container microseconds {
              must "not(../nanoseconds or ../milliseconds)";
              presence "Indicates a microseconds node is configured.";
              description
                "Use microseconds as the delay asymmetry units";
            }
            container milliseconds {
              must "not(../nanoseconds or ../microseconds)";
              presence "Indicates a milliseconds node is configured.";
              description
                "Use milliseconds as the delay asymmetry units";
            }
          }
        }
      }
      container interop {
        description
          "This interface should interoperate with a peer clock running a different profile";
        container profile {
          description
            "Specify the profile to interoperate with";
          container default {
            must
              "not(../g-8265-1 or ../g-8275-1
               or ../g-8275-2)";
            presence "Indicates a default node is configured.";
            description
              "Default profile";
          }
          container g-8265-1 {
            must
              "not(../default or ../g-8275-1
               or ../g-8275-2)";
            presence "Indicates a g-8265-1 node is configured.";
            description
              "G.8265.1 telecom profile";
          }
          container g-8275-1 {
            must
              "not(../default or ../g-8265-1
               or ../g-8275-2)";
            presence "Indicates a g-8275-1 node is configured.";
            description
              "G.8275.1 telecom profile";
          }
          container g-8275-2 {
            must
              "not(../default or ../g-8265-1
               or ../g-8275-1)";
            presence "Indicates a g-8275-2 node is configured.";
            description
              "G.8275.2 telecom profile";
          }
        }
        leaf domain {
          type uint32 {
            range "0..255" {
              description
                "Domain of the peer clock";
            }
          }
          description
            "Domain of the peer clock";
        }
        container egress-conversion {
          description
            "Conversion rules to apply on egress";
          leaf priority1 {
            type uint32 {
              range "0..255" {
                description
                  "The priority1 value to use for the peer clock";
              }
            }
            description
              "The priority1 value to use for the peer clock";
          }
          leaf priority2 {
            type uint32 {
              range "0..255" {
                description
                  "The priority2 value to use for the peer clock";
              }
            }
            description
              "The priority2 value to use for the peer clock";
          }
          leaf clock-accuracy {
            type uint32 {
              range "0..254" {
                description
                  "The clock-accuracy value to use for the peer clock";
              }
            }
            description
              "The clock-accuracy value to use for the peer clock";
          }
          leaf offset-scaled-log-variance {
            type uint32 {
              range "0..65535" {
                description
                  "The OSLV value to use for the peer clock";
              }
            }
            description
              "The OSLV value to use for the peer clock";
          }
          container clock-class {
            description
              "The clock class mapping to use";
            leaf default {
              type uint32 {
                range "0..255" {
                  description
                    "Default clock class to use when a more specific mapping is not available";
                }
              }
              description
                "Default clock class to use when a more specific mapping is not available";
            }
            container mappings {
              description
                "Specific mapping for a given clock class value";
              list mapping {
                key "clock-class-to-map-from";
                description
                  "Specific mapping for a given clock class value";
                leaf clock-class-to-map-from {
                  type uint32 {
                    range "0..255" {
                      description
                        "Clock class to map from";
                    }
                  }
                  description
                    "Specific mapping for a given clock class value";
                }
                leaf clock-class-to-map-to {
                  type uint32 {
                    range "0..255" {
                      description
                        "Clock class to map to";
                    }
                  }
                  mandatory true;
                  description
                    "Clock class to map to";
                }
              }
            }
          }
        }
        container ingress-conversion {
          description
            "Conversion rules to apply on ingress";
          leaf priority1 {
            type uint32 {
              range "0..255" {
                description
                  "The priority1 value to use for the peer clock";
              }
            }
            description
              "The priority1 value to use for the peer clock";
          }
          leaf priority2 {
            type uint32 {
              range "0..255" {
                description
                  "The priority2 value to use for the peer clock";
              }
            }
            description
              "The priority2 value to use for the peer clock";
          }
          leaf clock-accuracy {
            type uint32 {
              range "0..254" {
                description
                  "The clock-accuracy value to use for the peer clock";
              }
            }
            description
              "The clock-accuracy value to use for the peer clock";
          }
          leaf offset-scaled-log-variance {
            type uint32 {
              range "0..65535" {
                description
                  "The OSLV value to use for the peer clock";
              }
            }
            description
              "The OSLV value to use for the peer clock";
          }
          container clock-class {
            description
              "The clock class mapping to use";
            leaf default {
              type uint32 {
                range "0..255" {
                  description
                    "Default clock class to use when a more specific mapping is not available";
                }
              }
              description
                "Default clock class to use when a more specific mapping is not available";
            }
            container mappings {
              description
                "Specific mapping for a given clock class value";
              list mapping {
                key "clock-class-to-map-from";
                description
                  "Specific mapping for a given clock class value";
                leaf clock-class-to-map-from {
                  type uint32 {
                    range "0..255" {
                      description
                        "Clock class to map from";
                    }
                  }
                  description
                    "Specific mapping for a given clock class value";
                }
                leaf clock-class-to-map-to {
                  type uint32 {
                    range "0..255" {
                      description
                        "Clock class to map to";
                    }
                  }
                  mandatory true;
                  description
                    "Clock class to map to";
                }
              }
            }
          }
        }
      }
    }
  }

  container ptp {
    presence "Indicates a ptp node is configured.";
    description
      "Precision Time Protocol config";
    container frequency {
      description
        "Precision Time Protocol frequency configuration";
      leaf priority {
        type uint32 {
          range "1..254" {
            description
              "Enter the frequency priority";
          }
        }
        description
          "Frequency priority";
      }
    }
    container time-of-day {
      description
        "Precision Time Protocol time-of-day configuration";
      leaf priority {
        type uint32 {
          range "1..254" {
            description
              "Enter the time-of-day priority";
          }
        }
        description
          "Time-of-day priority";
      }
    }
    container ipv6-verify-checksum {
      presence "Indicates a ipv6-verify-checksum node is configured.";
      description
        "Verify UDP checksum for IPv6 packets";
    }
    leaf min-clock-class {
      type uint32 {
        range "0..255" {
          description
            "Enter the minimum clock class";
        }
      }
      description
        "Clocks with a clock-class higher than minimum clock class will not be considered for selection as a parent clock.";
    }
    container utc-offset {
      description
        "Configure the UTC offset";
      leaf baseline {
        type uint32 {
          range "0..32767" {
            description
              "The UTC offset, in seconds";
          }
        }
        description
          "Configure the baseline UTC offset";
      }
      leaf leap-second-file {
        type xr:Cisco-ios-xr-string {
          length "1..800" {
            description
              "URL of the leap second source file";
          }
        }
        description
          "Configure a file containing leap second information to poll";
      }
      leaf poll-frequency {
        type uint32 {
          range "1..365" {
            description
              "Polling frequency";
          }
        }
        must "../leap-second-file";
        description
          "Frequency at which the URL should be polled, in days";
      }
      container offsets {
        description
          "Configure the UTC offset";
        list offset {
          key "date";
          description
            "Configure the UTC offset";
          leaf date {
            type string {
              pattern "[0-9]{4}-[0-9]{2}-[0-9]{2}" {
                description
                  "in ISO 8601 format (YYYY-MM-DD)";
              }
            }
            description
              "Date to apply the UTC offset, in ISO 8601 format (YYYY-MM-DD)";
          }
          leaf offset-value {
            type uint32 {
              range "0..32767" {
                description
                  "The UTC offset, in seconds";
              }
            }
            mandatory true;
            description
              "The UTC offset, in seconds";
          }
        }
      }
    }
    container uncalibrated-clock-class {
      presence "Indicates a uncalibrated-clock-class node is configured.";
      description
        "Clock class to be used while acquiring phase-lock to a parent clock";
      leaf clock-class {
        type uint32 {
          range "0..255" {
            description
              "Enter the uncalibrated clock class";
          }
        }
        mandatory true;
        description
          "Clock class to be used while acquiring phase-lock to a parent clock";
      }
      container unless-from-holdover {
        presence "Indicates a unless-from-holdover node is configured.";
        description
          "Don't use this clock class if previously in holdover.";
      }
    }
    container uncalibrated-traceable-override {
      presence "Indicates a uncalibrated-traceable-override node is configured.";
      description
        "Override time-traceability to true while acquiring phase lock to a parent clock";
    }
    leaf startup-clock-class {
      type uint32 {
        range "0..255" {
          description
            "The clock class to use";
        }
      }
      description
        "The clock class to use when PTP starts up";
    }
    leaf freerun-clock-class {
      type uint32 {
        range "0..255" {
          description
            "The clock class to use";
        }
      }
      description
        "The clock class to use when the PTP servo is freerunning";
    }
    leaf double-failure-clock-class {
      type uint32 {
        range "0..255" {
          description
            "The clock class to use";
        }
      }
      description
        "The clock class to use when both PTP and syncE are lost";
    }
    container transparent-clock {
      description
        "Configure transparent clock";
      container domain {
        description
          "Domain within which to run as a transparent clock";
        container all {
          presence "Indicates a all node is configured.";
          description
            "All domains";
        }
      }
    }
    container physical-layer-frequency {
      presence "Indicates a physical-layer-frequency node is configured.";
      description
        "Disable PTP as a source for frequency as only physical layer frequency sources are used";
    }
    container network-type {
      description
        "The type of network";
      container high-pdv {
        presence "Indicates a high-pdv node is configured.";
        description
          "The network has high packet delay variation";
      }
    }
    leaf servo-slow-tracking {
      type uint32 {
        range "8..984" {
          description
            "The rate, in nanoseconds per second, to limit tracking to. Must be a multiple of 8.";
        }
      }
      description
        "Restrict the rate, in ns per second, at which the servo may track to update the time and attain sync";
    }
    leaf holdover-spec-clock-class {
      type uint32 {
        range "0..255" {
          description
            "The clock class to use";
        }
      }
      description
        "The clock class to use while in holdover-spec";
    }
    leaf holdover-spec-duration {
      type uint32 {
        range "0..4294967295" {
          description
            "Time (in seconds) holdover-spec will last after sync lost";
        }
      }
      description
        "Specify duration of holdover-spec";
    }
    container holdover-spec-traceable-override {
      presence "Indicates a holdover-spec-traceable-override node is configured.";
      description
        "Override time-traceability to true while in holdover-spec";
    }
    container apts {
      presence "Indicates a apts node is configured.";
      description
        "Enable assisted partial timing support";
    }
    leaf phase-difference-threshold-breach {
      type uint32 {
        range "0..4294967295" {
          description
            "Threshold value in nanoseconds";
        }
      }
      description
        "Value at which a bistate alarm is triggered when the phase difference for any foreign primary is exceeded in nanoseconds";
    }
    container detect-ptsf-unusable {
      presence "Indicates a detect-ptsf-unusable node is configured.";
      description
        "Enable the servo to disqualify a foreign primary from selection if it is found to be PTSF-unusable";
    }
    container log {
      description
        "Precision Time Protocol logging configuration";
      container best-primary-clock {
        description
          "Best primary clock logging options";
        container changes {
          presence "Indicates a changes node is configured.";
          description
            "Log best primary clock changes";
        }
      }
    }
    container profiles {
      description
        "PTP Profile Configuration";
      list profile {
        key "profile-name";
        description
          "PTP Profile Configuration";
        leaf profile-name {
          type xr:Cisco-ios-xr-string {
            length "1..800" {
              description
                "Name of Profile";
            }
          }
          description
            "PTP Profile Configuration";
        }
        container port {
          description
            "PTP port options";
          container state {
            description
              "Restrict the port state of this interface";
            container subordinate-only {
              must "not(../primary-only or ../any)";
              presence "Indicates a subordinate-only node is configured.";
              description
                "Restrict the port state to subordinate";
            }
            container primary-only {
              must "not(../subordinate-only or ../any)";
              presence "Indicates a primary-only node is configured.";
              description
                "Restrict the port state to primary";
            }
            container any {
              must "not(../subordinate-only or ../primary-only)";
              presence "Indicates a any node is configured.";
              description
                "Allow any port state";
            }
          }
        }
        container source {
          description
            "PTP source address options";
          container ipv4 {
            description
              "PTP source IPv4 address options";
            leaf address {
              type inet:ipv4-address-no-zone;
              description
                "Set the IPv4 address to use when sending IPv4 packets";
            }
          }
          container ipv6 {
            description
              "PTP source IPv6 address options";
            leaf address {
              type inet:ipv6-address-no-zone;
              description
                "Set the IPv6 address to use when sending IPv6 packets";
            }
          }
        }
        container multicast {
          presence "Indicates a multicast node is configured.";
          description
            "Allow multicast messages to be sent";
          container mixed {
            must "not(../disable)";
            presence "Indicates a mixed node is configured.";
            description
              "Mixed-mode multicast";
          }
          container disable {
            must "not(../mixed)";
            presence "Indicates a disable node is configured.";
            description
              "Disable multicast transport";
          }
          container target-address {
            must "ethernet/mac-address-01-1b-19-00-00-00 or ethernet/mac-address-01-80-c2-00-00-0e";
            presence "Indicates a target-address node is configured.";
            description
              "Configure a target address";
            container ethernet {
              description
                "Configure ethernet target address";
              container mac-address-01-1b-19-00-00-00 {
                must "not(../mac-address-01-80-c2-00-00-0e)";
                presence "Indicates a mac-address-01-1b-19-00-00-00 node is configured.";
                description
                  "Forwardable mac-address";
              }
              container mac-address-01-80-c2-00-00-0e {
                must "not(../mac-address-01-1b-19-00-00-00)";
                presence "Indicates a mac-address-01-80-c2-00-00-0e node is configured.";
                description
                  "Non-forwardable mac-address";
              }
            }
          }
        }
        container transport {
          description
            "PTP transport type to use on this interface";
          container ipv4 {
            must "not(../ethernet or ../ipv6)";
            presence "Indicates a ipv4 node is configured.";
            description
              "IPv4 transport";
          }
          container ethernet {
            must "not(../ipv4 or ../ipv6)";
            presence "Indicates a ethernet node is configured.";
            description
              "Ethernet transport";
          }
          container ipv6 {
            must "not(../ipv4 or ../ethernet)";
            presence "Indicates a ipv6 node is configured.";
            description
              "IPv6 transport";
          }
        }
        container clock {
          description
            "PTP clock-operation to use";
          container operation {
            description
              "PTP clock-operation to use";
            container one-step {
              must "not(../two-step)";
              presence "Indicates a one-step node is configured.";
              description
                "One-step clock-operation";
            }
            container two-step {
              must "not(../one-step)";
              presence "Indicates a two-step node is configured.";
              description
                "Two-step clock-operation";
            }
          }
        }
        container announce {
          description
            "Announce message options";
          leaf interval {
            type enumeration {
              enum "1" {
                value 0;
                description
                  "One second interval";
              }
              enum "2" {
                value 1;
                description
                  "Two second interval";
              }
              enum "4" {
                value 2;
                description
                  "Four second interval";
              }
              enum "8" {
                value 3;
                description
                  "Eight second interval";
              }
              enum "16" {
                value 4;
                description
                  "Sixteen second interval";
              }
              enum "32" {
                value 5;
                description
                  "Thirty Two second interval";
              }
              enum "64" {
                value 6;
                description
                  "Sixty Four second interval";
              }
              enum "128" {
                value 7;
                description
                  "One Hundred and Twenty Eight second interval";
              }
            }
            must "not(../frequency)";
            description
              "Send Announce messages once every one or more seconds";
          }
          leaf frequency {
            type enumeration {
              enum "1" {
                value 0;
                description
                  "One per second frequency";
              }
              enum "2" {
                value 1;
                description
                  "Two per second frequency";
              }
              enum "4" {
                value 2;
                description
                  "Four per second frequency";
              }
              enum "8" {
                value 3;
                description
                  "Eight per second frequency";
              }
              enum "16" {
                value 4;
                description
                  "Sixteen per second frequency";
              }
              enum "32" {
                value 5;
                description
                  "Thirty Two per second frequency";
              }
              enum "64" {
                value 6;
                description
                  "Sixty Four second frequency";
              }
              enum "128" {
                value 7;
                description
                  "One Hundred and Twenty Eight second frequency";
              }
            }
            must "not(../interval)";
            description
              "Send Announce messages one or more times a second";
          }
          leaf timeout {
            type uint32 {
              range "2..10" {
                description
                  "The number of announce intervals before timeout";
              }
            }
            description
              "Configure the announce timeout value";
          }
          leaf grant-duration {
            type uint32 {
              range "60..1000" {
                description
                  "The grant duration, in seconds";
              }
            }
            description
              "Configure the announce unicast grant duration value";
          }
        }
        container sync {
          description
            "Sync message options";
          leaf interval {
            type enumeration {
              enum "1" {
                value 0;
                description
                  "One second interval";
              }
              enum "2" {
                value 1;
                description
                  "Two second interval";
              }
              enum "4" {
                value 2;
                description
                  "Four second interval";
              }
              enum "8" {
                value 3;
                description
                  "Eight second interval";
              }
              enum "16" {
                value 4;
                description
                  "Sixteen second interval";
              }
              enum "32" {
                value 5;
                description
                  "Thirty Two second interval";
              }
              enum "64" {
                value 6;
                description
                  "Sixty Four second interval";
              }
              enum "128" {
                value 7;
                description
                  "One Hundred and Twenty Eight second interval";
              }
            }
            must "not(../frequency)";
            description
              "Send Announce messages once every one or more seconds";
          }
          leaf frequency {
            type enumeration {
              enum "1" {
                value 0;
                description
                  "One per second frequency";
              }
              enum "2" {
                value 1;
                description
                  "Two per second frequency";
              }
              enum "4" {
                value 2;
                description
                  "Four per second frequency";
              }
              enum "8" {
                value 3;
                description
                  "Eight per second frequency";
              }
              enum "16" {
                value 4;
                description
                  "Sixteen per second frequency";
              }
              enum "32" {
                value 5;
                description
                  "Thirty Two per second frequency";
              }
              enum "64" {
                value 6;
                description
                  "Sixty Four second frequency";
              }
              enum "128" {
                value 7;
                description
                  "One Hundred and Twenty Eight second frequency";
              }
            }
            must "not(../interval)";
            description
              "Send Announce messages one or more times a second";
          }
          leaf grant-duration {
            type uint32 {
              range "60..1000" {
                description
                  "The grant duration, in seconds";
              }
            }
            description
              "Configure the sync unicast grant duration value";
          }
          leaf timeout {
            type uint32 {
              range "100..100000" {
                description
                  "The timeout value, in milliseconds";
              }
            }
            description
              "Configure the sync timeout value";
          }
        }
        container delay-request {
          description
            "Configure the sending of delay-request messages";
          leaf interval {
            type enumeration {
              enum "1" {
                value 0;
                description
                  "One second interval";
              }
              enum "2" {
                value 1;
                description
                  "Two second interval";
              }
              enum "4" {
                value 2;
                description
                  "Four second interval";
              }
              enum "8" {
                value 3;
                description
                  "Eight second interval";
              }
              enum "16" {
                value 4;
                description
                  "Sixteen second interval";
              }
              enum "32" {
                value 5;
                description
                  "Thirty Two second interval";
              }
              enum "64" {
                value 6;
                description
                  "Sixty Four second interval";
              }
              enum "128" {
                value 7;
                description
                  "One Hundred and Twenty Eight second interval";
              }
            }
            must "not(../frequency)";
            description
              "Send Announce messages once every one or more seconds";
          }
          leaf frequency {
            type enumeration {
              enum "1" {
                value 0;
                description
                  "One per second frequency";
              }
              enum "2" {
                value 1;
                description
                  "Two per second frequency";
              }
              enum "4" {
                value 2;
                description
                  "Four per second frequency";
              }
              enum "8" {
                value 3;
                description
                  "Eight per second frequency";
              }
              enum "16" {
                value 4;
                description
                  "Sixteen per second frequency";
              }
              enum "32" {
                value 5;
                description
                  "Thirty Two per second frequency";
              }
              enum "64" {
                value 6;
                description
                  "Sixty Four second frequency";
              }
              enum "128" {
                value 7;
                description
                  "One Hundred and Twenty Eight second frequency";
              }
            }
            must "not(../interval)";
            description
              "Send Announce messages one or more times a second";
          }
        }
        leaf cos {
          type uint32 {
            range "0..7" {
              description
                "The COS value to use";
            }
          }
          description
            "Specify the COS value to use";
        }
        leaf event-cos {
          type uint32 {
            range "0..7" {
              description
                "The COS value to use";
            }
          }
          description
            "Specify the COS value to use";
        }
        leaf general-cos {
          type uint32 {
            range "0..7" {
              description
                "The COS value to use";
            }
          }
          description
            "Specify the COS value to use";
        }
        leaf dscp {
          type uint32 {
            range "0..63" {
              description
                "The DSCP value to use";
            }
          }
          description
            "Specify the DSCP value to use";
        }
        leaf event-dscp {
          type uint32 {
            range "0..63" {
              description
                "The DSCP value to use";
            }
          }
          description
            "Specify the DSCP value to use";
        }
        leaf general-dscp {
          type uint32 {
            range "0..63" {
              description
                "The DSCP value to use";
            }
          }
          description
            "Specify the DSCP value to use";
        }
        leaf ipv4-ttl {
          type uint32 {
            range "1..255" {
              description
                "The IPv4 TTL value to use";
            }
          }
          description
            "Specify the IPv4 TTL value to use";
        }
        leaf ipv6-hop-limit {
          type uint32 {
            range "1..255" {
              description
                "The IPv6 hop limit value to use";
            }
          }
          description
            "Specify the IPv6 hop limit value to use";
        }
        leaf delay-asymmetry {
          type int32 {
            range "-500000000..500000000" {
              description
                "How much longer the primary to subordinate path takes than the reverse";
            }
          }
          description
            "Delay asymmetry to apply to all primarys on an interface";
        }
        container nanoseconds {
          must "not(../microseconds or ../milliseconds)";
          presence "Indicates a nanoseconds node is configured.";
          description
            "Use nanoseconds as the delay asymmetry units";
        }
        container microseconds {
          must "not(../nanoseconds or ../milliseconds)";
          presence "Indicates a microseconds node is configured.";
          description
            "Use microseconds as the delay asymmetry units";
        }
        container milliseconds {
          must "not(../nanoseconds or ../microseconds)";
          presence "Indicates a milliseconds node is configured.";
          description
            "Use milliseconds as the delay asymmetry units";
        }
        container delay-response {
          description
            "Delay-Response message options";
          leaf grant-duration {
            type uint32 {
              range "60..1000" {
                description
                  "The grant duration, in seconds";
              }
            }
            description
              "Configure the delay-response unicast grant duration value";
          }
          leaf timeout {
            type uint32 {
              range "100..100000" {
                description
                  "The timeout value, in milliseconds";
              }
            }
            description
              "Configure the delay-response timeout value";
          }
        }
        container unicast-grant {
          description
            "Unicast grant options";
          container invalid-request {
            description
              "Configure the response to invalid unicast requests";
            container reduce {
              must "not(../deny)";
              presence "Indicates a reduce node is configured.";
              description
                "Reduce grant parameters";
            }
            container deny {
              must "not(../reduce)";
              presence "Indicates a deny node is configured.";
              description
                "Deny grant";
            }
          }
        }
        container subordinate {
          description
            "Add a subordinate to announce to on this interface";
          container ipv4s {
            description
              "IPv4 address";
            list ipv4-non-negotiated {
              must "non-negotiated";
              key "address";
              description
                "IPv4 address";
              leaf address {
                type inet:ipv4-address-no-zone;
                description
                  "IPv4 address";
              }
              container non-negotiated {
                presence "Indicates a non-negotiated node is configured.";
                description
                  "Use non-negotiated unicast";
              }
            }
          }
          container ipv6s {
            description
              "IPv6 address";
            list ipv6 {
              key "address";
              description
                "IPv6 address";
              leaf address {
                type inet:ipv6-address-no-zone;
                description
                  "IPv6 address";
              }
              container non-negotiated {
                presence "Indicates a non-negotiated node is configured.";
                description
                  "Use non-negotiated unicast";
              }
            }
          }
          container ethernets {
            description
              "Ethernet address";
            list ethernet {
              must "non-negotiated";
              key "address";
              description
                "Ethernet address";
              leaf address {
                type yang:mac-address;
                description
                  "Ethernet address";
              }
              container non-negotiated {
                presence "Indicates a non-negotiated node is configured.";
                description
                  "Use non-negotiated unicast";
              }
            }
          }
        }
        container primary {
          description
            "Add a primary to listen to on interfaces using this profile";
          container ipv4s {
            description
              "IPv4 address";
            list ipv4 {
              key "address";
              description
                "IPv4 address";
              leaf address {
                type inet:ipv4-address-no-zone;
                description
                  "IPv4 address";
              }
              leaf priority {
                type uint32 {
                  range "0..255" {
                    description
                      "The priority value to use for this primary";
                  }
                }
                description
                  "Specify the priority of this primary";
              }
              leaf clock-class {
                type uint32 {
                  range "0..255" {
                    description
                      "The clock class to use for this primary";
                  }
                }
                description
                  "Override the clock-class of this primary";
              }
              container multicast {
                presence "Indicates a multicast node is configured.";
                description
                  "Whether this primary sends messages multicast";
                container mixed {
                  presence "Indicates a mixed node is configured.";
                  description
                    "Mixed-mode multicast";
                }
              }
              container non-negotiated {
                presence "Indicates a non-negotiated node is configured.";
                description
                  "Use non-negotiated unicast";
              }
              leaf delay-asymmetry {
                type int32 {
                  range "-500000000..500000000" {
                    description
                      "How much longer the primary to subordinate path takes than the reverse";
                  }
                }
                description
                  "The expected delay asymmetry for this primary";
              }
              container nanoseconds {
                must "not(../microseconds or ../milliseconds)";
                presence "Indicates a nanoseconds node is configured.";
                description
                  "Use nanoseconds as the delay asymmetry units";
              }
              container microseconds {
                must "not(../nanoseconds or ../milliseconds)";
                presence "Indicates a microseconds node is configured.";
                description
                  "Use microseconds as the delay asymmetry units";
              }
              container milliseconds {
                must "not(../nanoseconds or ../microseconds)";
                presence "Indicates a milliseconds node is configured.";
                description
                  "Use milliseconds as the delay asymmetry units";
              }
            }
          }
          container ipv6s {
            description
              "IPv6 address";
            list ipv6 {
              key "address";
              description
                "IPv6 address";
              leaf address {
                type inet:ipv6-address-no-zone;
                description
                  "IPv6 address";
              }
              leaf priority {
                type uint32 {
                  range "0..255" {
                    description
                      "The priority value to use for this primary";
                  }
                }
                description
                  "Specify the priority of this primary";
              }
              leaf clock-class {
                type uint32 {
                  range "0..255" {
                    description
                      "The clock class to use for this primary";
                  }
                }
                description
                  "Override the clock-class of this primary";
              }
              container multicast {
                presence "Indicates a multicast node is configured.";
                description
                  "Whether this primary sends messages multicast";
                container mixed {
                  presence "Indicates a mixed node is configured.";
                  description
                    "Mixed-mode multicast";
                }
              }
              container non-negotiated {
                presence "Indicates a non-negotiated node is configured.";
                description
                  "Use non-negotiated unicast";
              }
              leaf delay-asymmetry {
                type int32 {
                  range "-500000000..500000000" {
                    description
                      "How much longer the primary to subordinate path takes than the reverse";
                  }
                }
                description
                  "The expected delay asymmetry for this primary";
              }
              container nanoseconds {
                must "not(../microseconds or ../milliseconds)";
                presence "Indicates a nanoseconds node is configured.";
                description
                  "Use nanoseconds as the delay asymmetry units";
              }
              container microseconds {
                must "not(../nanoseconds or ../milliseconds)";
                presence "Indicates a microseconds node is configured.";
                description
                  "Use microseconds as the delay asymmetry units";
              }
              container milliseconds {
                must "not(../nanoseconds or ../microseconds)";
                presence "Indicates a milliseconds node is configured.";
                description
                  "Use milliseconds as the delay asymmetry units";
              }
            }
          }
          container ethernets {
            description
              "Ethernet address";
            list ethernet {
              key "address";
              description
                "Ethernet address";
              leaf address {
                type yang:mac-address;
                description
                  "Ethernet address";
              }
              leaf priority {
                type uint32 {
                  range "0..255" {
                    description
                      "The priority value to use for this primary";
                  }
                }
                description
                  "Specify the priority of this primary";
              }
              leaf clock-class {
                type uint32 {
                  range "0..255" {
                    description
                      "The clock class to use for this primary";
                  }
                }
                description
                  "Override the clock-class of this primary";
              }
              container multicast {
                presence "Indicates a multicast node is configured.";
                description
                  "Whether this primary sends messages multicast";
                container mixed {
                  presence "Indicates a mixed node is configured.";
                  description
                    "Mixed-mode multicast";
                }
              }
              container non-negotiated {
                presence "Indicates a non-negotiated node is configured.";
                description
                  "Use non-negotiated unicast";
              }
              leaf delay-asymmetry {
                type int32 {
                  range "-500000000..500000000" {
                    description
                      "How much longer the primary to subordinate path takes than the reverse";
                  }
                }
                description
                  "The expected delay asymmetry for this primary";
              }
              container nanoseconds {
                must "not(../microseconds or ../milliseconds)";
                presence "Indicates a nanoseconds node is configured.";
                description
                  "Use nanoseconds as the delay asymmetry units";
              }
              container microseconds {
                must "not(../nanoseconds or ../milliseconds)";
                presence "Indicates a microseconds node is configured.";
                description
                  "Use microseconds as the delay asymmetry units";
              }
              container milliseconds {
                must "not(../nanoseconds or ../microseconds)";
                presence "Indicates a milliseconds node is configured.";
                description
                  "Use milliseconds as the delay asymmetry units";
              }
            }
          }
        }
        container interop {
          description
            "Interfaces using this profile should interoperate with a peer clock running a different profile";
          container profile {
            description
              "Specify the profile to interoperate with";
            container default {
              must
                "not(../g-8265-1 or ../g-8275-1
                 or ../g-8275-2)";
              presence "Indicates a default node is configured.";
              description
                "Default profile";
            }
            container g-8265-1 {
              must
                "not(../default or ../g-8275-1
                 or ../g-8275-2)";
              presence "Indicates a g-8265-1 node is configured.";
              description
                "G.8265.1 telecom profile";
            }
            container g-8275-1 {
              must
                "not(../default or ../g-8265-1
                 or ../g-8275-2)";
              presence "Indicates a g-8275-1 node is configured.";
              description
                "G.8275.1 telecom profile";
            }
            container g-8275-2 {
              must
                "not(../default or ../g-8265-1
                 or ../g-8275-1)";
              presence "Indicates a g-8275-2 node is configured.";
              description
                "G.8275.2 telecom profile";
            }
          }
          leaf domain {
            type uint32 {
              range "0..255" {
                description
                  "Domain of the peer clock";
              }
            }
            description
              "Domain of the peer clock";
          }
          container egress-conversion {
            description
              "Conversion rules to apply on egress";
            leaf priority1 {
              type uint32 {
                range "0..255" {
                  description
                    "The priority1 value to use for the peer clock";
                }
              }
              description
                "The priority1 value to use for the peer clock";
            }
            leaf priority2 {
              type uint32 {
                range "0..255" {
                  description
                    "The priority2 value to use for the peer clock";
                }
              }
              description
                "The priority2 value to use for the peer clock";
            }
            leaf clock-accuracy {
              type uint32 {
                range "0..254" {
                  description
                    "The clock-accuracy value to use for the peer clock";
                }
              }
              description
                "The clock-accuracy value to use for the peer clock";
            }
            leaf offset-scaled-log-variance {
              type uint32 {
                range "0..65535" {
                  description
                    "The OSLV value to use for the peer clock";
                }
              }
              description
                "The OSLV value to use for the peer clock";
            }
            container clock-class {
              description
                "The clock class mapping to use";
              leaf default {
                type uint32 {
                  range "0..255" {
                    description
                      "Default clock class to use when a more specific mapping is not available";
                  }
                }
                description
                  "Default clock class to use when a more specific mapping is not available";
              }
              container mappings {
                description
                  "Specific mapping for a given clock class value";
                list mapping {
                  key "clock-class-to-map-from";
                  description
                    "Specific mapping for a given clock class value";
                  leaf clock-class-to-map-from {
                    type uint32 {
                      range "0..255" {
                        description
                          "Clock class to map from";
                      }
                    }
                    description
                      "Specific mapping for a given clock class value";
                  }
                  leaf clock-class-to-map-to {
                    type uint32 {
                      range "0..255" {
                        description
                          "Clock class to map to";
                      }
                    }
                    mandatory true;
                    description
                      "Clock class to map to";
                  }
                }
              }
            }
          }
          container ingress-conversion {
            description
              "Conversion rules to apply on ingress";
            leaf priority1 {
              type uint32 {
                range "0..255" {
                  description
                    "The priority1 value to use for the peer clock";
                }
              }
              description
                "The priority1 value to use for the peer clock";
            }
            leaf priority2 {
              type uint32 {
                range "0..255" {
                  description
                    "The priority2 value to use for the peer clock";
                }
              }
              description
                "The priority2 value to use for the peer clock";
            }
            leaf clock-accuracy {
              type uint32 {
                range "0..254" {
                  description
                    "The clock-accuracy value to use for the peer clock";
                }
              }
              description
                "The clock-accuracy value to use for the peer clock";
            }
            leaf offset-scaled-log-variance {
              type uint32 {
                range "0..65535" {
                  description
                    "The OSLV value to use for the peer clock";
                }
              }
              description
                "The OSLV value to use for the peer clock";
            }
            container clock-class {
              description
                "The clock class mapping to use";
              leaf default {
                type uint32 {
                  range "0..255" {
                    description
                      "Default clock class to use when a more specific mapping is not available";
                  }
                }
                description
                  "Default clock class to use when a more specific mapping is not available";
              }
              container mappings {
                description
                  "Specific mapping for a given clock class value";
                list mapping {
                  key "clock-class-to-map-from";
                  description
                    "Specific mapping for a given clock class value";
                  leaf clock-class-to-map-from {
                    type uint32 {
                      range "0..255" {
                        description
                          "Clock class to map from";
                      }
                    }
                    description
                      "Specific mapping for a given clock class value";
                  }
                  leaf clock-class-to-map-to {
                    type uint32 {
                      range "0..255" {
                        description
                          "Clock class to map to";
                      }
                    }
                    mandatory true;
                    description
                      "Clock class to map to";
                  }
                }
              }
            }
          }
        }
      }
    }
    container virtual-port {
      presence "Indicates a virtual-port node is configured.";
      description
        "PTP Virtual Port Configuration";
      leaf priority1 {
        type uint32 {
          range "0..255" {
            description
              "The priority1 value to use";
          }
        }
        description
          "The priority1 value to use when advertising this clock";
      }
      leaf priority2 {
        type uint32 {
          range "0..255" {
            description
              "The priority2 value to use";
          }
        }
        description
          "The priority2 value to use when advertising this clock";
      }
      leaf clock-class {
        type uint32 {
          range "0..255" {
            description
              "The clock class to use";
          }
        }
        description
          "The clock class to use when advertising this clock";
      }
      leaf clock-accuracy {
        type uint32 {
          range "0..254" {
            description
              "The clock accuracy to use";
          }
        }
        description
          "The clock accuracy to use when advertising this clock";
      }
      leaf offset-scaled-log-variance {
        type uint32 {
          range "0..65535" {
            description
              "The OSLV value to use for the virtual port";
          }
        }
        description
          "The OSLV value to use for the virtual port";
      }
      leaf local-priority {
        type uint32 {
          range "1..255" {
            description
              "The local priority value to use";
          }
        }
        description
          "Configure a local priority";
      }
    }
    container clock {
      description
        "PTP Clock Configuration";
      container identity {
        description
          "PTP clock-id options";
        container mac-address {
          description
            "Use a mac-address to determine the clock-id";
          leaf custom {
            type yang:mac-address;
            must "not(../router)";
            description
              "configure this node";
          }
          container router {
            must "not(../custom)";
            presence "Indicates a router node is configured.";
            description
              "Use the router's mac-address";
          }
        }
        leaf eui-64 {
          type xr:Cisco-ios-xr-string {
            length "16" {
              description
                "Enter the EUI-64 number (hex value w/o leading 0x)";
            }
            pattern "[0-9a-fA-F]{16}";
          }
          must "not(../mac-address/router or ../mac-address/custom)";
          description
            "Use the full EUI-64 number to determine";
        }
      }
      leaf domain {
        type uint32 {
          range "0..255" {
            description
              "The domain number to use";
          }
        }
        description
          "The domain number to use for this clock";
      }
      leaf priority1 {
        type uint32 {
          range "0..255" {
            description
              "The priority1 value to use";
          }
        }
        description
          "The priority1 value to use when advertising this clock";
      }
      leaf priority2 {
        type uint32 {
          range "0..255" {
            description
              "The priority2 value to use";
          }
        }
        description
          "The priority2 value to use when advertising this clock";
      }
      leaf clock-class {
        type uint32 {
          range "0..255" {
            description
              "The clock class to use";
          }
        }
        description
          "The clock class to use when advertising this clock";
      }
      container timescale {
        description
          "The timescale to use when advertising this clock";
        container ptp {
          must "not(../arb)";
          presence "Indicates a ptp node is configured.";
          description
            "PTP timescale";
        }
        container arb {
          must "not(../ptp)";
          presence "Indicates a arb node is configured.";
          description
            "ARB timescale";
        }
      }
      container time-source {
        description
          "The time source to use when advertising this clock";
        container atomic-clock {
          must
            "not(../gps or ../terrestrial-radio
             or ../ptp or ../ntp
             or ../hand-set or ../other
             or ../internal-oscillator)";
          presence "Indicates a atomic-clock node is configured.";
          description
            "Atomic clock";
        }
        container gps {
          must
            "not(../atomic-clock or ../terrestrial-radio
             or ../ptp or ../ntp
             or ../hand-set or ../other
             or ../internal-oscillator)";
          presence "Indicates a gps node is configured.";
          description
            "GPS";
        }
        container terrestrial-radio {
          must
            "not(../atomic-clock or ../gps
             or ../ptp or ../ntp
             or ../hand-set or ../other
             or ../internal-oscillator)";
          presence "Indicates a terrestrial-radio node is configured.";
          description
            "Terrestrial radio";
        }
        container ptp {
          must
            "not(../atomic-clock or ../gps
             or ../terrestrial-radio or ../ntp
             or ../hand-set or ../other
             or ../internal-oscillator)";
          presence "Indicates a ptp node is configured.";
          description
            "PTP";
        }
        container ntp {
          must
            "not(../atomic-clock or ../gps
             or ../terrestrial-radio or ../ptp
             or ../hand-set or ../other
             or ../internal-oscillator)";
          presence "Indicates a ntp node is configured.";
          description
            "NTP";
        }
        container hand-set {
          must
            "not(../atomic-clock or ../gps
             or ../terrestrial-radio or ../ptp
             or ../ntp or ../other
             or ../internal-oscillator)";
          presence "Indicates a hand-set node is configured.";
          description
            "Hand-set";
        }
        container other {
          must
            "not(../atomic-clock or ../gps
             or ../terrestrial-radio or ../ptp
             or ../ntp or ../hand-set
             or ../internal-oscillator)";
          presence "Indicates a other node is configured.";
          description
            "Other source";
        }
        container internal-oscillator {
          must
            "not(../atomic-clock or ../gps
             or ../terrestrial-radio or ../ptp
             or ../ntp or ../hand-set
             or ../other)";
          presence "Indicates a internal-oscillator node is configured.";
          description
            "Internal oscillator";
        }
      }
      container profile {
        description
          "PTP profile configuration";
        container g-8265-1 {
          must
            "not(../g-8275-1/clock-type/t-bc or
                 ../g-8275-1/clock-type/t-gm or
                 ../g-8275-1/clock-type/t-tsc or
                 ../g-8275-2/clock-type/t-bc or
                 ../g-8275-2/clock-type/t-gm or
                 ../g-8275-2/clock-type/t-tsc)";
          presence "Indicates a g-8265-1 node is configured.";
          description
            "G.8265.1 telecom profile";
          container clock-type {
            description
              "Clock type for G.8265 profiles";
            container primary {
              must "not(../subordinate)";
              presence "Indicates a primary node is configured.";
              description
                "Configure primary clock";
            }
            container subordinate {
              must "not(../primary)";
              presence "Indicates a subordinate node is configured.";
              description
                "Configure telecom subordinate clock";
            }
          }
        }
        container g-8275-1 {
          description
            "G.8275.1 telecom profile";
          container clock-type {
            description
              "Clock type for G.8275 profiles";
            container t-bc {
              must
                "not(../t-gm or ../t-tsc or
                 ../../../g-8265-1 or
                 ../../../g-8275-2/clock-type/t-bc or
                 ../../../g-8275-2/clock-type/t-gm or
                 ../../../g-8275-2/clock-type/t-tsc)";
              presence "Indicates a t-bc node is configured.";
              description
                "Configure telecom boundary clock";
            }
            container t-gm {
              must
                "not(../t-bc or ../t-tsc or
                 ../../../g-8265-1 or
                 ../../../g-8275-2/clock-type/t-bc or
                 ../../../g-8275-2/clock-type/t-gm or
                 ../../../g-8275-2/clock-type/t-tsc)";
              presence "Indicates a t-gm node is configured.";
              description
                "Configure telecom grand primary clock";
            }
            container t-tsc {
              must
                "not(../t-bc or ../t-gm or
                 ../../../g-8265-1 or
                 ../../../g-8275-2/clock-type/t-bc or
                 ../../../g-8275-2/clock-type/t-gm or
                 ../../../g-8275-2/clock-type/t-tsc)";
              presence "Indicates a t-tsc node is configured.";
              description
                "Configure telecom subordinate clock";
            }
          }
        }
        container g-8275-2 {
          description
            "G.8275.2 telecom profile";
          container clock-type {
            description
              "Clock type for G.8275 profiles";
            container t-bc {
              must
                "not(../t-gm or ../t-tsc or
                 ../../../g-8265-1 or
                 ../../../g-8275-1/clock-type/t-bc or
                 ../../../g-8275-1/clock-type/t-gm or
                 ../../../g-8275-1/clock-type/t-tsc)";
              presence "Indicates a t-bc node is configured.";
              description
                "Configure telecom boundary clock";
            }
            container t-gm {
              must
                "not(../t-bc or ../t-tsc or
                 ../../../g-8265-1 or
                 ../../../g-8275-1/clock-type/t-bc or
                 ../../../g-8275-1/clock-type/t-gm or
                 ../../../g-8275-1/clock-type/t-tsc)";
              presence "Indicates a t-gm node is configured.";
              description
                "Configure telecom grand primary clock";
            }
            container t-tsc {
              must
                "not(../t-bc or ../t-gm or
                 ../../../g-8265-1 or
                 ../../../g-8275-1/clock-type/t-bc or
                 ../../../g-8275-1/clock-type/t-gm or
                 ../../../g-8275-1/clock-type/t-tsc)";
              presence "Indicates a t-tsc node is configured.";
              description
                "Configure telecom subordinate clock";
            }
          }
        }
      }
    }
  }

  augment "/a1:interfaces/a1:interface" {
    description
      "This augment extends active nodes configuration";
    uses IF-BODY;
  }
  augment "/a1:interfaces/a1:interface-preconfigure" {
    description
      "This augment extends preconfigured nodes
       configuration";
    uses IF-BODY;
  }
  augment "/a2:snmp-server/a2:traps" {
    description
      "This augment extends snmp-derver traps nodes
       configuration";
    container ptp {
      description
        "Enable PTP traps";
      leaf clock-class-change {
        type uint32 {
          range "0..255" {
            description
              "Expected clock class";
          }
        }
        description
          "Notifications of change to the clock class";
      }
      container clock-state-change {
        description
          "Notification of change to the clock state";
        container freerun {
          must
            "not(../acquiring or ../freq-locked
             or ../phase-aligned or ../holdover)";
          presence "Indicates a freerun node is configured.";
          description
            "Freerun state";
        }
        container acquiring {
          must
            "not(../freerun or ../freq-locked
             or ../phase-aligned or ../holdover)";
          presence "Indicates a acquiring node is configured.";
          description
            "Acquiring state";
        }
        container freq-locked {
          must
            "not(../freerun or ../acquiring
             or ../phase-aligned or ../holdover)";
          presence "Indicates a freq-locked node is configured.";
          description
            "Frequency locked state";
        }
        container phase-aligned {
          must
            "not(../freerun or ../acquiring
             or ../freq-locked or ../holdover)";
          presence "Indicates a phase-aligned node is configured.";
          description
            "Phase aligned state";
        }
        container holdover {
          must
            "not(../freerun or ../acquiring
             or ../freq-locked or ../phase-aligned)";
          presence "Indicates a holdover node is configured.";
          description
            "Holdover state";
        }
      }
      container time-source {
        description
          "Notification of change to the time source";
        container atomic-clock {
          must
            "not(../gps or ../terrestrial-radio
             or ../ptp or ../ntp
             or ../handset or ../other
             or ../internal)";
          presence "Indicates a atomic-clock node is configured.";
          description
            "Atomic Clock";
        }
        container gps {
          must
            "not(../atomic-clock or ../terrestrial-radio
             or ../ptp or ../ntp
             or ../handset or ../other
             or ../internal)";
          presence "Indicates a gps node is configured.";
          description
            "GPS";
        }
        container terrestrial-radio {
          must
            "not(../atomic-clock or ../gps
             or ../ptp or ../ntp
             or ../handset or ../other
             or ../internal)";
          presence "Indicates a terrestrial-radio node is configured.";
          description
            "Terrestrial Radio";
        }
        container ptp {
          must
            "not(../atomic-clock or ../gps
             or ../terrestrial-radio or ../ntp
             or ../handset or ../other
             or ../internal)";
          presence "Indicates a ptp node is configured.";
          description
            "PTP";
        }
        container ntp {
          must
            "not(../atomic-clock or ../gps
             or ../terrestrial-radio or ../ptp
             or ../handset or ../other
             or ../internal)";
          presence "Indicates a ntp node is configured.";
          description
            "NTP";
        }
        container handset {
          must
            "not(../atomic-clock or ../gps
             or ../terrestrial-radio or ../ptp
             or ../ntp or ../other
             or ../internal)";
          presence "Indicates a handset node is configured.";
          description
            "Handset";
        }
        container other {
          must
            "not(../atomic-clock or ../gps
             or ../terrestrial-radio or ../ptp
             or ../ntp or ../handset
             or ../internal)";
          presence "Indicates a other node is configured.";
          description
            "Other";
        }
        container internal {
          must
            "not(../atomic-clock or ../gps
             or ../terrestrial-radio or ../ptp
             or ../ntp or ../handset
             or ../other)";
          presence "Indicates a internal node is configured.";
          description
            "Internal Oscillator";
        }
      }
      container utc-offset-change {
        presence "Indicates a utc-offset-change node is configured.";
        description
          "Notification of change to the UTC offset";
        leaf expected-utc-offset {
          type uint32 {
            range "0..65535" {
              description
                "Expected UTC offset. Defaults to 37";
            }
          }
          description
            "Expected UTC offset. Defaults to 37";
        }
      }
      container offset-threshold-breach {
        description
          "Notification of changes to the offset from primary";
        leaf warning {
          type uint32 {
            range "0..4294967295" {
              description
                "Warning threshold in nsecs";
            }
          }
          must "../critical";
          description
            "Warning threshold";
        }
        leaf critical {
          type uint32 {
            range "0..4294967295" {
              description
                "Critical threshold in nsecs";
            }
          }
          must "../warning";
          description
            "Critical threshold";
        }
      }
      container primary-lost {
        presence "Indicates a primary-lost node is configured.";
        description
          "Notification of lost primarys";
      }
      container subordinate-lost {
        presence "Indicates a subordinate-lost node is configured.";
        description
          "Notification of last subordinates";
      }
      container all-subordinates-lost {
        presence "Indicates a all-subordinates-lost node is configured.";
        description
          "Notification of if all subordinates are lost";
      }
    }
  }
}
