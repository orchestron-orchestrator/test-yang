module Cisco-IOS-XR-sysadmin-fpd {
  namespace "http://www.cisco.com/ns/yang/Cisco-IOS-XR-sysadmin-fpd";
  prefix fpd;

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "FPD CLI support for both oper and config

     Copyright (c) 2012-2020 by Cisco Systems, Inc.
     All rights reserved.";

  revision 2022-11-18 {
    semver:module-version "1.0.0";
    description
      "Initial revision.";
  }

  grouping fpd {
    container config {
      description
        "FPD config mode";
      uses global-fpd-config-group;
    }
  }

  grouping global-fpd-config-group {
    leaf auto-upgrade {
      type enumeration {
        enum "enable" {
          value 1;
        }
        enum "disable" {
          value 0;
        }
      }
      default "enable";
      config true;
    }
  }

  container fpd {
    uses fpd;
  }
}
