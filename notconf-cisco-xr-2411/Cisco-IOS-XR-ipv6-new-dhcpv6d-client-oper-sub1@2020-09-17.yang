submodule Cisco-IOS-XR-ipv6-new-dhcpv6d-client-oper-sub1 {
  belongs-to Cisco-IOS-XR-ipv6-new-dhcpv6d-client-oper {
    prefix Cisco-IOS-XR-ipv6-new-dhcpv6d-client-oper;
  }

  import ietf-yang-types {
    prefix yang;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR ipv6-new-dhcpv6d-client package operational data.

     Copyright (c) 2013-2020 by Cisco Systems, Inc.
     All rights reserved.";

  revision 2020-09-17 {
    semver:module-version "1.1.0";
    description
      "Added prefix-len option for dhcpv6 client";
  }
  revision 2019-11-16 {
    semver:module-version "1.0.0";
    description
      "Added Support for DHCPv6 Client.";
  }
  revision 2019-04-05 {
    description
      "Establish semantic version baseline.";
  }
  revision 2015-11-09 {
    description
      "IOS XR 6.0 revision.";
  }

  typedef Bag-duid {
    type enumeration {
      enum "duid-llt" {
        value 1;
        description
          "DUID LLT";
      }
      enum "duid" {
        value 2;
        description
          "DUID EN";
      }
      enum "duid-ll" {
        value 3;
        description
          "DUID LL";
      }
    }
    description
      "Bag duid";
  }

  typedef Bag-dhcpv6-client-option {
    type enumeration {
      enum "rapid-commit" {
        value 14;
        description
          "Rapid Commit";
      }
      enum "user-class" {
        value 15;
        description
          "User Class";
      }
      enum "vendor-class" {
        value 16;
        description
          "Vendor Class";
      }
      enum "dns-servers" {
        value 23;
        description
          "DNS Servers";
      }
      enum "domain-list" {
        value 24;
        description
          "Domain List";
      }
    }
    description
      "Bag dhcpv6 client option";
  }

  typedef Bag-dhcpv6-client-cfg-timer {
    type enumeration {
      enum "sol-max-delay" {
        value 0;
        description
          "Solicit Max Delay";
      }
      enum "sol-timeout" {
        value 1;
        description
          "Solicit Timeout";
      }
      enum "sol-max-rt" {
        value 2;
        description
          "Solicit Max RT";
      }
      enum "req-timeout" {
        value 3;
        description
          "Request Timeout";
      }
      enum "req-max-rt" {
        value 4;
        description
          "Request Max RT";
      }
      enum "rel-timeout" {
        value 5;
        description
          "Release Timeout";
      }
    }
    description
      "Bag dhcpv6 client cfg timer";
  }

  typedef Bag-dhcpv6-client-state {
    type enumeration {
      enum "none" {
        value 0;
        description
          "None state";
      }
      enum "idle" {
        value 1;
        description
          "Idle state";
      }
      enum "solicit" {
        value 2;
        description
          "Solicit state";
      }
      enum "request" {
        value 3;
        description
          "Request state";
      }
      enum "confirm" {
        value 4;
        description
          "Confirm state";
      }
      enum "info-req" {
        value 5;
        description
          "InfoReq state";
      }
      enum "bound" {
        value 6;
        description
          "Bound state";
      }
      enum "renew" {
        value 7;
        description
          "Renew state";
      }
      enum "rebind" {
        value 8;
        description
          "Rebind state";
      }
      enum "release" {
        value 9;
        description
          "Release state";
      }
      enum "verify" {
        value 10;
        description
          "Verify state";
      }
      enum "decline" {
        value 11;
        description
          "Decline state";
      }
    }
    description
      "Bag dhcpv6 client state";
  }

  typedef Rsi-tbl-id {
    type uint32;
    description
      "Rsi tbl id";
  }

  typedef Rsi-vrf-id {
    type uint32;
    description
      "Rsi vrf id";
  }

  grouping DHCPV6-CLIENT-TIMER-STATS-BAG {
    description
      "DHCPv6 client timer statistics";
    leaf timer-started {
      type uint32;
      description
        "Timer started";
    }
    leaf timer-stopped {
      type uint32;
      description
        "Timer stopped";
    }
    leaf timer-expired {
      type uint32;
      description
        "Timer expired";
    }
  }

  grouping DHCPV6-CLIENT-PACKET-STATS-BAG {
    description
      "DHCPv6 client packet statistics";
    leaf received-packets {
      type uint32;
      description
        "Received packets";
    }
    leaf transmitted-packets {
      type uint32;
      description
        "Transmitted packets";
    }
    leaf dropped-packets {
      type uint32;
      description
        "Dropped packets";
    }
  }

  grouping DHCPV6-CLIENT-EDM-STATS-BAG {
    description
      "ipv6 dhcp client statistics";
    container solicit {
      description
        "DHCPV6 Solicit packets";
      uses DHCPV6-CLIENT-PACKET-STATS-BAG;
    }
    container advertise {
      description
        "DHCPV6 Advertise packets";
      uses DHCPV6-CLIENT-PACKET-STATS-BAG;
    }
    container request {
      description
        "DHCPV6 Request packets";
      uses DHCPV6-CLIENT-PACKET-STATS-BAG;
    }
    container reply {
      description
        "DHCPV6 Reply packets";
      uses DHCPV6-CLIENT-PACKET-STATS-BAG;
    }
    container confirm {
      description
        "DHCPV6 Confirm packets";
      uses DHCPV6-CLIENT-PACKET-STATS-BAG;
    }
    container renew {
      description
        "DHCPV6 Renew packets";
      uses DHCPV6-CLIENT-PACKET-STATS-BAG;
    }
    container rebind {
      description
        "DHCPV6 Rebind packets";
      uses DHCPV6-CLIENT-PACKET-STATS-BAG;
    }
    container release {
      description
        "DHCPV6 Release packets";
      uses DHCPV6-CLIENT-PACKET-STATS-BAG;
    }
    container reconfig {
      description
        "DHCPV6 Reconfig packets";
      uses DHCPV6-CLIENT-PACKET-STATS-BAG;
    }
    container inform {
      description
        "DHCPV6 Inform packets";
      uses DHCPV6-CLIENT-PACKET-STATS-BAG;
    }
    container init {
      description
        "DHCPV6 Init timer";
      uses DHCPV6-CLIENT-TIMER-STATS-BAG;
    }
    container vbind {
      description
        "DHCPV6 Vbind timer";
      uses DHCPV6-CLIENT-TIMER-STATS-BAG;
    }
    container t1 {
      description
        "DHCPV6 T1 timer";
      uses DHCPV6-CLIENT-TIMER-STATS-BAG;
    }
    container t2 {
      description
        "DHCPV6 T2 timer";
      uses DHCPV6-CLIENT-TIMER-STATS-BAG;
    }
    container retrans {
      description
        "DHCPV6 Retrans timer";
      uses DHCPV6-CLIENT-TIMER-STATS-BAG;
    }
    container valid {
      description
        "DHCPV6 Valid timer";
      uses DHCPV6-CLIENT-TIMER-STATS-BAG;
    }
    leaf interface-name-xr {
      type string;
      description
        "Dhcpv6 Client interface name";
    }
    leaf vrfid {
      type Rsi-vrf-id;
      description
        "VRF ID";
    }
  }

  grouping DHCPV6-CLIENT-IA-ADDR-BAG {
    description
      "Dhcpv6 Client IA Address Information";
    leaf ia-na-address {
      type string;
      description
        "Dhcpv6 IA NA Address";
    }
    leaf preferred-time {
      type uint32;
      description
        "Dhcpv6 IA NA Preferred Time";
    }
    leaf valid-time {
      type uint32;
      description
        "Dhcpv6 IA NA Valid Time";
    }
    leaf flags {
      type uint32;
      description
        "Dhcpv6 IA NA Flags";
    }
  }

  grouping DHCPV6-CLIENT-IA-NA-BAG {
    description
      "Dhcpv6 Client IA NA Information";
    leaf status {
      type int32;
      description
        "Dhcpv6 IA NA Status";
    }
    leaf iaid {
      type uint32;
      description
        "Dhcpv6 IA NA IAID";
    }
    leaf t1 {
      type uint32;
      description
        "Dhcpv6 IA NA T1";
    }
    leaf t2 {
      type uint32;
      description
        "Dhcpv6 IA NA T2";
    }
    list ia-address {
      description
        "Dhcpv6 IA Address Information";
      uses DHCPV6-CLIENT-IA-ADDR-BAG;
    }
  }

  grouping DHCPV6-CLIENT-SERVER-BAG {
    description
      "Dhcpv6 Server Information";
    leaf server-address {
      type string;
      description
        "Dhcpv6 Server address";
    }
    leaf preference {
      type uint8;
      description
        "Dhcpv6 Server Preference";
    }
    leaf duid {
      type string;
      description
        "Dhcpv6 Server DUID";
    }
    leaf status {
      type int32;
      description
        "Dhcpv6 Server Status";
    }
    list ia-na {
      description
        "Dhcpv6 IA NA Information";
      uses DHCPV6-CLIENT-IA-NA-BAG;
    }
  }

  grouping DHCPV6-CLIENT-CFG-OPTIONS-BAG {
    description
      "Dhcpv6 Client Options Configuration";
    leaf type {
      type Bag-dhcpv6-client-option;
      description
        "Dhcpv6 Client Option Type";
    }
    leaf value {
      type string;
      description
        "Dhcpv6 Client Option Value";
    }
  }

  grouping DHCPV6-CLIENT-CFG-TIMERS-BAG {
    description
      "Dhcpv6 Client Timers Configuration";
    leaf type {
      type Bag-dhcpv6-client-cfg-timer;
      description
        "Dhcpv6 Client Timer Type";
    }
    leaf value {
      type uint32;
      description
        "Dhcpv6 Client Timer Value";
    }
  }

  grouping DHCPV6-CLIENT-CFG-BAG {
    description
      "Dhcpv6 Client Configuration";
    leaf duid-type {
      type Bag-duid;
      description
        "Dhcpv6 Client Duid Type Configuration";
    }
    list timer {
      description
        "Dhcpv6 Client Timers Configuration";
      uses DHCPV6-CLIENT-CFG-TIMERS-BAG;
    }
    list option {
      description
        "Dhcpv6 Client Options Configuration";
      uses DHCPV6-CLIENT-CFG-OPTIONS-BAG;
    }
  }

  grouping DHCPV6-CLIENT-EDM-BAG {
    description
      "ipv6 dhcp client";
    container client-config {
      description
        "Dhcpv6 Client Configuration";
      uses DHCPV6-CLIENT-CFG-BAG;
    }
    leaf interface-name-xr {
      type string;
      description
        "Dhcpv6 Client interface name";
    }
    leaf mac-address {
      type yang:mac-address;
      description
        "Dhcpv6 Client mac address";
    }
    leaf vrfid {
      type Rsi-vrf-id;
      description
        "VRF ID";
    }
    leaf table-id {
      type Rsi-tbl-id;
      description
        "VRF Table Id";
    }
    leaf local-address {
      type string;
      description
        "IPV6 Link local address";
    }
    leaf global-address {
      type string;
      description
        "Dhcpv6 IPV6 Global address";
    }
    leaf prefix-len {
      type uint8;
      description
        "Dhcpv6 Address Prefix Length";
    }
    leaf client-state {
      type Bag-dhcpv6-client-state;
      description
        "Dhcpv6 Client State";
    }
    leaf ipv6-renew-time {
      type uint32;
      description
        "Dhcpv6 Client Renew time";
    }
    leaf ipv6-rebind-time {
      type uint32;
      description
        "Dhcpv6 Client Rebind time";
    }
    leaf ipv6-valid-time {
      type uint32;
      description
        "Dhcpv6 Client Valid time";
    }
    leaf lease-remain {
      type string;
      description
        "Dhcpv6 Client Lease time remaining";
    }
    leaf duid {
      type string;
      description
        "Dhcpv6 Client duid";
    }
    list server-info {
      description
        "Dhcpv6 Server Information";
      uses DHCPV6-CLIENT-SERVER-BAG;
    }
  }
}
