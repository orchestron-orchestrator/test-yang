module Cisco-IOS-XR-ascii-ltrace-oper {
  namespace "http://cisco.com/ns/yang/Cisco-IOS-XR-ascii-ltrace-oper";
  prefix ascii-ltrace-oper;

  import Cisco-IOS-XR-types {
    prefix xr;
  }
  import cisco-semver {
    prefix semver;
  }

  include Cisco-IOS-XR-ascii-ltrace-oper-sub1 {
    revision-date 2019-04-05;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ascii-ltrace package operational data.

     This module contains definitions
     for the following management objects:
       ltrace: ASCII ltrace data

     Copyright (c) 2013-2019 by Cisco Systems, Inc.
     All rights reserved.";

  revision 2019-04-05 {
    semver:module-version "1.0.1";
    description
      "Establish semantic version baseline.";
  }
  revision 2018-01-21 {
    description
      "Initial feature";
  }
  revision 2015-11-09 {
    description
      "IOS XR 6.0 revision.";
  }

  container ltrace {
    config false;
    description
      "ASCII ltrace data";
    container features {
      description
        "feature";
      list feature {
        description
          "feature";
        container traces {
          description
            "trace";
          list trace {
            key "ltrace-id";
            description
              "trace";
            leaf ltrace-id {
              type uint32;
              description
                "Ltrace ID of ltrace";
            }
            uses ASCII-LTRACE;
          }
        }
        leaf feature-name {
          type xr:Cisco-ios-xr-string;
          description
            "feature name";
        }
        leaf trace-buf {
          type xr:Cisco-ios-xr-string;
          description
            "trace buffer name";
        }
      }
    }
  }
}
