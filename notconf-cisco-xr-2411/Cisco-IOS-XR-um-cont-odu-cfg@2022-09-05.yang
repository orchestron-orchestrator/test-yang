module Cisco-IOS-XR-um-cont-odu-cfg {
  namespace "http://cisco.com/ns/yang/Cisco-IOS-XR-um-cont-odu-cfg";
  prefix um-cont-odu-cfg;

  import Cisco-IOS-XR-um-interface-cfg {
    prefix a1;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR cont-odu package configuration.

     This YANG module augments the
     modules with configuration data.

     Copyright (c) 2021-2022 by Cisco Systems, Inc.
     All rights reserved.";

  revision 2022-09-05 {
    semver:module-version "1.1.0";
    description
      "Updated lower-orders nodes
       2022-07-11
         Added missing description statement to nodes
       2022-06-01
         Adjusted controller augmentation hierarchy";
  }
  revision 2021-05-07 {
    semver:module-version "1.0.0";
    description
      "Initial release";
  }

  feature odu_config_supp_check {
    description
      "odu config supp check";
  }

  grouping CONT-BODY {
    description
      "Grouping for controller";
    container perf-mon {
      description
        "Performance Monitoring";
      container disable {
        must "not(../enable)";
        presence "Indicates a disable node is configured.";
        description
          "Disable performance monitoring";
      }
      container enable {
        must "not(../disable)";
        presence "Indicates a enable node is configured.";
        description
          "Enable performance monitoring";
      }
    }
    container gcc1 {
      presence "Indicates a gcc1 node is configured.";
      description
        "Configure General Communication Channel";
    }
    container gcc2 {
      presence "Indicates a gcc2 node is configured.";
      description
        "Configure General Communication Channel";
    }
    container delay {
      description
        "Delay Measurement for ODU";
      container enable {
        presence "Indicates a enable node is configured.";
        description
          "Enable delay measurement at ODU";
      }
    }
    container threshold {
      description
        "Configure threshold for Signal Failure and Signal Degrade";
      leaf sf {
        type uint32 {
          range "5..9" {
            description
              "Signal Failure Threshold(Range 1.0e-n)";
          }
        }
        description
          "Configure SF(Signal Failure) Threshold";
      }
      leaf sd {
        type uint32 {
          range "5..9" {
            description
              "Signal Degrade Threshold Value(Range 1.0e-n)";
          }
        }
        description
          "Configure SD(Signal Degrade) Threshold ";
      }
      leaf pm-tca {
        type uint32 {
          range "3..9" {
            description
              " Threshold crossing alert Value(Range 10e-n, Default 6)";
          }
        }
        description
          "Configure TCA(Threshold crossing alert)";
      }
    }
    leaf secondary-admin-state {
      type enumeration {
        enum "normal" {
          value 0;
          description
            "Normal, Admin-state in normal";
        }
        enum "maintenance" {
          value 1;
          description
            "Maintenance, Admin-state under maintenance";
        }
      }
      description
        "Configure the secondary admin state of the controller";
    }
    leaf tsg {
      type enumeration {
        enum "1.25G" {
          value 0;
          description
            "1.25G Tributary Slot Granularity";
        }
        enum "2.5G" {
          value 1;
          description
            "2.5G Tributary Slot Granularity";
        }
      }
      description
        "Configure TSG level(Tributary Slot Granularity)";
    }
    container pm-tim-ca {
      description
        "Configure Consequent Action for PM(Path Monitoring) TIM";
      container disable {
        must "not(../enable)";
        presence "Indicates a disable node is configured.";
        description
          "Disable PM-TIM-CA";
      }
      container enable {
        must "not(../disable)";
        presence "Indicates a enable node is configured.";
        description
          "Enable PM-TIM-CA";
      }
    }
    container tti {
      description
        "Configure TTI(Trail Trace Identifier)";
      container sent {
        description
          "Set transmit Trail Trace Identifier";
        container sapi {
          description
            "Enter Source Access Point Identifier field 1-15";
          leaf ascii {
            type string {
              length "1..15" {
                description
                  "ASCII text (Max 15 characters)";
              }
            }
            description
              "Enter ascii string";
          }
        }
        container dapi {
          description
            "Enter Destination Access Point Identifier field 1-15";
          leaf ascii {
            type string {
              length "1..15" {
                description
                  "ASCII text (Max 15 characters)";
              }
            }
            description
              "Enter ascii string";
          }
        }
        container operator-specific {
          description
            "Enter Operator Specific field";
          leaf ascii {
            type string {
              length "1..32" {
                description
                  "ASCII text (Max 32 characters)";
              }
            }
            must "not(../hex)";
            description
              "Enter ascii string";
          }
          leaf hex {
            type string {
              length "1..64" {
                description
                  "Hex Text (Max 64 - The string length should be an even number)";
              }
            }
            must "not(../ascii)";
            description
              "Enter hex string of even length";
          }
        }
        leaf ascii {
          type string {
            length "1..64" {
              description
                "ASCII text (Max 64 characters)";
            }
          }
          description
            "Enter Full-Ascii string ";
        }
        leaf hex {
          type string {
            length "1..128" {
              description
                "Hex text (Max 128 characters)";
            }
          }
          must "not(../ascii)";
          description
            "Enter Full-Hex string ";
        }
      }
      container expected {
        description
          "Set expected Trail Trace Identifier";
        container sapi {
          description
            "Enter Source Access Point Identifier field 1-15";
          leaf ascii {
            type string {
              length "1..15" {
                description
                  "ASCII text (Max 15 characters)";
              }
            }
            description
              "Enter ascii string";
          }
        }
        container dapi {
          description
            "Enter Destination Access Point Identifier field 1-15";
          leaf ascii {
            type string {
              length "1..15" {
                description
                  "ASCII text (Max 15 characters)";
              }
            }
            description
              "Enter ascii string";
          }
        }
        container operator-specific {
          description
            "Enter Operator Specific field";
          leaf ascii {
            type string {
              length "1..32" {
                description
                  "ASCII text (Max 32 characters)";
              }
            }
            must "not(../hex)";
            description
              "Enter ascii string";
          }
          leaf hex {
            type string {
              length "1..64" {
                description
                  "Hex Text (Max 64 - The string length should be an even number)";
              }
            }
            must "not(../ascii)";
            description
              "Enter hex string of even length";
          }
        }
        leaf ascii {
          type string {
            length "1..64" {
              description
                "ASCII text (Max 64 characters)";
            }
          }
          description
            "Enter Full-Ascii string ";
        }
        leaf hex {
          type string {
            length "1..128" {
              description
                "Hex text (Max 128 characters)";
            }
          }
          must "not(../ascii)";
          description
            "Enter Full-Hex string ";
        }
      }
    }
    container opu {
      description
        "Configure PRBS for ODU";
      container prbs {
        description
          "Configure pseudo random bit sequence test";
        container mode {
          description
            "prbs-mode for the interface";
          container source {
            presence "Indicates a source node is configured.";
            description
              "source mode";
            container pattern {
              description
                "Select pattern for prbs mode";
              container pn31 {
                must
                  "not(../pn23 or ../pn11
                   or ../invertedpn31 or ../invertedpn11
                   or ../pn15 or ../pn7)";
                presence "Indicates a pn31 node is configured.";
                description
                  "prbs pattern pn31";
              }
              container pn23 {
                must
                  "not(../pn31 or ../pn11
                   or ../invertedpn31 or ../invertedpn11
                   or ../pn15 or ../pn7)";
                presence "Indicates a pn23 node is configured.";
                description
                  "prbs pattern pn23";
              }
              container pn11 {
                must
                  "not(../pn31 or ../pn23
                   or ../invertedpn31 or ../invertedpn11
                   or ../pn15 or ../pn7)";
                presence "Indicates a pn11 node is configured.";
                description
                  "prbs pattern pn11";
              }
              container invertedpn31 {
                must
                  "not(../pn31 or ../pn23
                   or ../pn11 or ../invertedpn11
                   or ../pn15 or ../pn7)";
                presence "Indicates a invertedpn31 node is configured.";
                description
                  "prbs pattern inverted pn31";
              }
              container invertedpn11 {
                must
                  "not(../pn31 or ../pn23
                   or ../pn11 or ../invertedpn31
                   or ../pn15 or ../pn7)";
                presence "Indicates a invertedpn11 node is configured.";
                description
                  "prbs pattern inverted pn11";
              }
              container pn15 {
                must
                  "not(../pn31 or ../pn23
                   or ../pn11 or ../invertedpn31
                   or ../invertedpn11 or ../pn7)";
                presence "Indicates a pn15 node is configured.";
                description
                  "prbs pattern inverted pn15";
              }
              container pn7 {
                must
                  "not(../pn31 or ../pn23
                   or ../pn11 or ../invertedpn31
                   or ../invertedpn11 or ../pn15)";
                presence "Indicates a pn7 node is configured.";
                description
                  "prbs pattern inverted pn7";
              }
            }
          }
          container sink {
            presence "Indicates a sink node is configured.";
            description
              "sink mode";
            container pattern {
              description
                "Select pattern for prbs mode";
              container pn31 {
                must
                  "not(../pn23 or ../pn11
                   or ../invertedpn31 or ../invertedpn11
                   or ../pn15 or ../pn7)";
                presence "Indicates a pn31 node is configured.";
                description
                  "prbs pattern pn31";
              }
              container pn23 {
                must
                  "not(../pn31 or ../pn11
                   or ../invertedpn31 or ../invertedpn11
                   or ../pn15 or ../pn7)";
                presence "Indicates a pn23 node is configured.";
                description
                  "prbs pattern pn23";
              }
              container pn11 {
                must
                  "not(../pn31 or ../pn23
                   or ../invertedpn31 or ../invertedpn11
                   or ../pn15 or ../pn7)";
                presence "Indicates a pn11 node is configured.";
                description
                  "prbs pattern pn11";
              }
              container invertedpn31 {
                must
                  "not(../pn31 or ../pn23
                   or ../pn11 or ../invertedpn11
                   or ../pn15 or ../pn7)";
                presence "Indicates a invertedpn31 node is configured.";
                description
                  "prbs pattern inverted pn31";
              }
              container invertedpn11 {
                must
                  "not(../pn31 or ../pn23
                   or ../pn11 or ../invertedpn31
                   or ../pn15 or ../pn7)";
                presence "Indicates a invertedpn11 node is configured.";
                description
                  "prbs pattern inverted pn11";
              }
              container pn15 {
                must
                  "not(../pn31 or ../pn23
                   or ../pn11 or ../invertedpn31
                   or ../invertedpn11 or ../pn7)";
                presence "Indicates a pn15 node is configured.";
                description
                  "prbs pattern inverted pn15";
              }
              container pn7 {
                must
                  "not(../pn31 or ../pn23
                   or ../pn11 or ../invertedpn31
                   or ../invertedpn11 or ../pn15)";
                presence "Indicates a pn7 node is configured.";
                description
                  "prbs pattern inverted pn7";
              }
            }
          }
          container source-sink {
            presence "Indicates a source-sink node is configured.";
            description
              "source-sink mode";
            container pattern {
              description
                "Select pattern for prbs mode";
              container pn31 {
                must
                  "not(../pn23 or ../pn11
                   or ../invertedpn31 or ../invertedpn11
                   or ../pn15 or ../pn7)";
                presence "Indicates a pn31 node is configured.";
                description
                  "prbs pattern pn31";
              }
              container pn23 {
                must
                  "not(../pn31 or ../pn11
                   or ../invertedpn31 or ../invertedpn11
                   or ../pn15 or ../pn7)";
                presence "Indicates a pn23 node is configured.";
                description
                  "prbs pattern pn23";
              }
              container pn11 {
                must
                  "not(../pn31 or ../pn23
                   or ../invertedpn31 or ../invertedpn11
                   or ../pn15 or ../pn7)";
                presence "Indicates a pn11 node is configured.";
                description
                  "prbs pattern pn11";
              }
              container invertedpn31 {
                must
                  "not(../pn31 or ../pn23
                   or ../pn11 or ../invertedpn11
                   or ../pn15 or ../pn7)";
                presence "Indicates a invertedpn31 node is configured.";
                description
                  "prbs pattern inverted pn31";
              }
              container invertedpn11 {
                must
                  "not(../pn31 or ../pn23
                   or ../pn11 or ../invertedpn31
                   or ../pn15 or ../pn7)";
                presence "Indicates a invertedpn11 node is configured.";
                description
                  "prbs pattern inverted pn11";
              }
              container pn15 {
                must
                  "not(../pn31 or ../pn23
                   or ../pn11 or ../invertedpn31
                   or ../invertedpn11 or ../pn7)";
                presence "Indicates a pn15 node is configured.";
                description
                  "prbs pattern inverted pn15";
              }
              container pn7 {
                must
                  "not(../pn31 or ../pn23
                   or ../pn11 or ../invertedpn31
                   or ../invertedpn11 or ../pn15)";
                presence "Indicates a pn7 node is configured.";
                description
                  "prbs pattern inverted pn7";
              }
            }
          }
          container direction {
            description
              "Select prbs-direction for prbs mode";
            container line {
              must
                "(../../source or ../../sink or ../../source-sink)
                 and not(../system)";
              presence "Indicates a line node is configured.";
              description
                "prbs in line side";
            }
            container system {
              must
                "(../../source or ../../sink or ../../source-sink)
                 and not(../line)";
              presence "Indicates a system node is configured.";
              description
                "prbs in system side";
            }
          }
        }
      }
      container ca {
        description
          "Select CA mode to enable";
        container laser-squelch {
          presence "Indicates a laser-squelch node is configured.";
          description
            "Enable controller laser squelch timer";
          leaf laser-squelch-time-in-ms {
            type uint32 {
              range "20..10000" {
                description
                  "laser squelch time in ms ";
              }
            }
            description
              "laser squelch time in ms ";
          }
        }
        container idle-frame {
          presence "Indicates a idle-frame node is configured.";
          description
            "Enable controller idle frame timer";
          leaf idle-frame-time-in-ms {
            type uint32 {
              range "20..10000" {
                description
                  "idle frame time in ms ";
              }
            }
            description
              "idle frame time in ms ";
          }
        }
      }
    }
    container tcm {
      description
        "Configure Tandem Connection Monitoring";
      container ids {
        description
          "Configure TCM(Tandem Connection Monitoring) level for ODU";
        list id {
          key "id-id";
          description
            "Configure TCM(Tandem Connection Monitoring) level for ODU";
          leaf id-id {
            type uint32 {
              range "1..6" {
                description
                  "Tandem Connection Monitoring ID";
              }
            }
            description
              "Configure TCM(Tandem Connection Monitoring) level for ODU";
          }
          container perf-mon {
            description
              "Performance Monitoring";
            container disable {
              must "not(../enable)";
              presence "Indicates a disable node is configured.";
              description
                "Disable performance monitoring";
            }
            container enable {
              must "not(../disable)";
              presence "Indicates a enable node is configured.";
              description
                "Enable performance monitoring";
            }
          }
          container tcm-mode {
            description
              "TCM Mode";
            container operational {
              presence "Indicates a operational node is configured.";
              description
                "Configure tcm in operational monitoring mode";
              container ltc-ca {
                description
                  "Consequent(ial) action for Enable and Disable";
                container enable {
                  presence "Indicates a enable node is configured.";
                  description
                    "Enable consequent(ial) action for TCM-LTC";
                }
              }
              container tim-ca {
                description
                  "Consequent(ial) action for Enable and Disable";
                container enable {
                  presence "Indicates a enable node is configured.";
                  description
                    "Enable consequent(ial) action for TCM-TIM";
                }
              }
            }
          }
          container delay {
            description
              "Delay Measurement";
            container enable {
              presence "Indicates a enable node is configured.";
              description
                "Enable delay measurement";
            }
          }
          container threshold {
            description
              "Configure threshold for Signal Failure and Signal Degrade";
            leaf sd {
              type uint32 {
                range "5..9" {
                  description
                    "Signal Degrade Threshold Value(Range 1.0e-n)";
                }
              }
              description
                "Configure SD(Signal Degrade) Threshold ";
            }
            leaf sf {
              type uint32 {
                range "5..9" {
                  description
                    "Signal Failure Threshold Value(Range 1.0e-n)";
                }
              }
              description
                "Configure SF(Signal Failure) Threshold";
            }
            leaf pm-tca {
              type uint32 {
                range "3..9" {
                  description
                    "Threshold Crossing Alert Value(Range 10e-n, Default 3)";
                }
              }
              description
                "Configure TCA(Threshold Crossing Alert)";
            }
          }
          container tti {
            description
              "Configure TTI(Trail Trace Identifier)";
            container sent {
              description
                "Set transmit Trail Trace Identifier";
              container sapi {
                description
                  "Enter Source Access Point Identifier field 1-15";
                leaf ascii {
                  type string {
                    length "1..15" {
                      description
                        "ASCII text (Max 15 characters)";
                    }
                  }
                  description
                    "Enter ascii string";
                }
              }
              container dapi {
                description
                  "Enter Destination Access Point Identifier field 1-15";
                leaf ascii {
                  type string {
                    length "1..15" {
                      description
                        "ASCII text (Max 15 characters)";
                    }
                  }
                  description
                    "Enter ascii string";
                }
              }
              container operator-specific {
                description
                  "Enter Operator Specific field";
                leaf ascii {
                  type string {
                    length "1..32" {
                      description
                        "ASCII text (Max 32 characters)";
                    }
                  }
                  must "not(../hex)";
                  description
                    "Enter ascii string";
                }
                leaf hex {
                  type string {
                    length "1..64" {
                      description
                        "Hex Text (Max 64 - The string length should be an even number)";
                    }
                  }
                  must "not(../ascii)";
                  description
                    "Enter hex string of even length";
                }
              }
              leaf ascii {
                type string {
                  length "1..64" {
                    description
                      "ASCII text (Max 64 characters)";
                  }
                }
                description
                  "Enter Full-Ascii string ";
              }
              leaf hex {
                type string {
                  length "1..128" {
                    description
                      "Hex text (Max 128 characters)";
                  }
                }
                must "not(../ascii)";
                description
                  "Enter Full-Hex string ";
              }
            }
            container expected {
              description
                "Set expected Trail Trace Identifier";
              container sapi {
                description
                  "Enter Source Access Point Identifier field 1-15";
                leaf ascii {
                  type string {
                    length "1..15" {
                      description
                        "ASCII text (Max 15 characters)";
                    }
                  }
                  description
                    "Enter ascii string";
                }
              }
              container dapi {
                description
                  "Enter Destination Access Point Identifier field 1-15";
                leaf ascii {
                  type string {
                    length "1..15" {
                      description
                        "ASCII text (Max 15 characters)";
                    }
                  }
                  description
                    "Enter ascii string";
                }
              }
              container operator-specific {
                description
                  "Enter Operator Specific field";
                leaf ascii {
                  type string {
                    length "1..32" {
                      description
                        "ASCII text (Max 32 characters)";
                    }
                  }
                  must "not(../hex)";
                  description
                    "Enter ascii string";
                }
                leaf hex {
                  type string {
                    length "1..64" {
                      description
                        "Hex Text (Max 64 - The string length should be an even number)";
                    }
                  }
                  must "not(../ascii)";
                  description
                    "Enter hex string of even length";
                }
              }
              leaf ascii {
                type string {
                  length "1..64" {
                    description
                      "ASCII text (Max 64 characters)";
                  }
                }
                description
                  "Enter Full-Ascii string ";
              }
              leaf hex {
                type string {
                  length "1..128" {
                    description
                      "Hex text (Max 128 characters)";
                  }
                }
                must "not(../ascii)";
                description
                  "Enter Full-Hex string ";
              }
            }
          }
        }
      }
    }
    leaf loopback {
      type enumeration {
        enum "line" {
          value 2;
          description
            "Select local (facility) loopback";
        }
        enum "internal" {
          value 4;
          description
            "Select local (terminal) loopback";
        }
      }
      description
        "Configure ODU controller loopback mode";
    }
    container create-lower-orders {
      description
        "configure this node";
      list create-lower-order {
        key "create-lower-order-id tpn-number";
        description
          "configure this node";
        leaf create-lower-order-id {
          type enumeration {
            enum "ODU1" {
              value 1;
              description
                "create lower order odu1";
            }
            enum "ODU2" {
              value 2;
              description
                "create lower order odu2";
            }
            enum "ODU3" {
              value 3;
              description
                "create lower order odu3";
            }
            enum "ODU0" {
              value 10;
              description
                "create lower order odu0";
            }
            enum "ODU2E" {
              value 11;
              description
                "create lower order odu2e";
            }
            enum "ODU1E" {
              value 23;
              description
                "create lower order odu1e";
            }
            enum "ODU2F" {
              value 25;
              description
                "create lower order odu2F";
            }
            enum "ODU3E1" {
              value 26;
              description
                "create lower order odu3e1";
            }
            enum "ODU3E2" {
              value 27;
              description
                "create lower order odu3e2";
            }
          }
          description
            "configure this node";
        }
        leaf tpn-number {
          type uint32 {
            range "1..80" {
              description
                "<1 - MAX> Tributary port number as allowed in G.709";
            }
          }
          description
            "Configure tributary port number for odu ";
        }
        leaf ts {
          type string {
            length "1..800" {
              description
                "tributary slot string separated by (:) or (-) from 1 to no of ts in parent controller. (:) indicates individual tributary slot and (-) represent range";
            }
          }
          description
            "Configure Tributary Slots for odu ";
        }
      }
      list create-lower-order-tpn {
        key "tpn-number";
        description
          "configure this node";
        leaf tpn-number {
          type uint32 {
            range "1..80" {
              description
                "<1 - MAX> Tributary port number as allowed in G.709";
            }
          }
          description
            "Configure tributary port number for odu ";
        }
        leaf ts {
          type string {
            length "1..800" {
              description
                "tributary slot string separated by (:) or (-) from 1 to no of ts in parent controller. (:) indicates individual tributary slot and (-) represent range";
            }
          }
          description
            "Configure Tributary Slots for odu ";
        }
      }
    }
    container create-lower-order-odu-flexes {
      description
        "configure this node";
      list create-lower-order-odu-flex {
        key "create-lower-order-odu-flex-id tpn-number";
        description
          "configure this node";
        leaf create-lower-order-odu-flex-id {
          type enumeration {
            enum "ODU-FLEX" {
              value 22;
              description
                "create lower order odu-flex";
            }
          }
          description
            "configure this node";
        }
        leaf tpn-number {
          type uint32 {
            range "1..80" {
              description
                "<1 - MAX> Tributary port number as allowed in G.709";
            }
          }
          description
            "Configure tributary port number for odu ";
        }
        leaf ts {
          type string {
            length "1..230" {
              description
                "tributary slot string separated by (:) or (-) from 1 to no of ts in parent controller. (:) indicates individual tributary slot and (-) represent range";
            }
          }
          must "../bitrate";
          description
            "Configure Tributary Slots for odu ";
        }
        leaf bitrate {
          type uint32 {
            range "1..104124241" {
              description
                "Bitrate for odu-flex GFP-F can be any client rate in given range For CBR Client rate should be equal to FC-400, FC-800 etc.";
            }
          }
          must "../ts and ../mapping";
          description
            "Configure Client Bitrate for odu-flex in kbit/s";
        }
        leaf mapping {
          type enumeration {
            enum "GFP-F-Fixed" {
              value 1;
              description
                "GFP Non resizable mapping";
            }
            enum "CBR" {
              value 3;
              description
                "CBR mapping";
            }
          }
          must "../bitrate";
          description
            "Configure mapping for odu-flex";
        }
      }
      list create-lower-order-odu-flex-tpn {
        key "tpn-number";
        description
          "configure this node";
        leaf tpn-number {
          type uint32 {
            range "1..80" {
              description
                "<1 - MAX> Tributary port number as allowed in G.709";
            }
          }
          description
            "Configure tributary port number for odu ";
        }
        leaf ts {
          type string {
            length "1..230" {
              description
                "tributary slot string separated by (:) or (-) from 1 to no of ts in parent controller. (:) indicates individual tributary slot and (-) represent range";
            }
          }
          must "../bitrate";
          description
            "Configure Tributary Slots for odu ";
        }
        leaf bitrate {
          type uint32 {
            range "1..104124241" {
              description
                "Bitrate for odu-flex GFP-F can be any client rate in given range For CBR Client rate should be equal to FC-400, FC-800 etc.";
            }
          }
          must "../ts and ../mapping";
          description
            "Configure Client Bitrate for odu-flex in kbit/s";
        }
        leaf mapping {
          type enumeration {
            enum "GFP-F-Fixed" {
              value 1;
              description
                "GFP Non resizable mapping";
            }
            enum "CBR" {
              value 3;
              description
                "CBR mapping";
            }
          }
          must "../bitrate";
          description
            "Configure mapping for odu-flex";
        }
      }
    }
    leaf terminate {
      type enumeration {
        enum "ether" {
          value 1;
          description
            "Terminating to Ethernet Interface";
        }
      }
      description
        "Configuring ethernet interface ";
    }
    container mapping {
      description
        "mapping for odu controller";
      leaf f-for-mapping {
        type enumeration {
          enum "GfpF" {
            value 1;
            description
              "gfp_f for mapping";
          }
          enum "gmp" {
            value 4;
            description
              "gmp for mapping";
          }
        }
        must "../f-for-mapping";
        description
          "configure this node";
      }
    }
  }

  augment "/a1:controllers/a1:controller" {
    description
      "This augment extends active nodes configuration";
    uses CONT-BODY;
  }
  augment "/a1:controllers/a1:controller-preconfigure" {
    description
      "This augment extends preconfigured nodes
       configuration";
    uses CONT-BODY;
  }
}
