submodule Cisco-IOS-XR-ncs1001-hw-module-eth-oper-sub1 {
  belongs-to Cisco-IOS-XR-ncs1001-hw-module-eth-oper {
    prefix Cisco-IOS-XR-ncs1001-hw-module-eth-oper;
  }

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR ncs1001-hw-module-eth package operational data.

     Copyright (c) 2013-2022 by Cisco Systems, Inc.
     All rights reserved.";

  revision 2022-08-23 {
    semver:module-version "1.0.0";
    description
      "first release.";
  }
  revision 2019-04-05 {
    description
      "Establish semantic version baseline.";
  }
  revision 2015-11-09 {
    description
      "IOS XR 6.0 revision.";
  }

  grouping HWMOD-ETH-SWITCH-PORT-STAT-B {
    description
      "Eth_switch PortStat ascii";
    leaf port-name {
      type string {
        length "0..32";
      }
      description
        "port name";
    }
    leaf good-octets-rcv {
      type uint64;
      description
        "GoodOctetsRcv";
    }
    leaf bad-octets-rcv {
      type uint64;
      description
        "BadOctetsRcv";
    }
    leaf mac-transmit-err {
      type uint64;
      description
        "MacTransmitErr";
    }
    leaf good-pkts-rcv {
      type uint64;
      description
        "GoodPktsRcv";
    }
    leaf bad-pkts-rcv {
      type uint64;
      description
        "BadPktsRcv";
    }
    leaf brdc-pkts-rcv {
      type uint64;
      description
        "BrdcPktsRcv";
    }
    leaf mc-pkts-rcv {
      type uint64;
      description
        "McPktsRcv";
    }
    leaf pkts64-octets {
      type uint64;
      description
        "Pkts64Octets";
    }
    leaf pkts65to127-octets {
      type uint64;
      description
        "Pkts65to127Octets";
    }
    leaf pkts128to255-octets {
      type uint64;
      description
        "Pkts128to255Octets";
    }
    leaf pkts256to511-octets {
      type uint64;
      description
        "Pkts256to511Octets";
    }
    leaf pkts512to1023-octets {
      type uint64;
      description
        "Pkts512to1023Octets";
    }
    leaf pkts1024tomax-ooctets {
      type uint64;
      description
        "Pkts1024tomaxOoctets";
    }
    leaf good-octets-sent {
      type uint64;
      description
        "GoodOctetsSent";
    }
    leaf good-pkts-sent {
      type uint64;
      description
        "GoodPktsSent";
    }
    leaf excessive-collisions {
      type uint64;
      description
        "ExcessiveCollisions";
    }
    leaf mc-pkts-sent {
      type uint64;
      description
        "McPktsSent";
    }
    leaf brdc-pkts-sent {
      type uint64;
      description
        "BrdcPktsSent";
    }
    leaf unrecog-mac-cntr-rcv {
      type uint64;
      description
        "UnrecogMacCntrRcv";
    }
    leaf fc-sent {
      type uint64;
      description
        "FcSent";
    }
    leaf good-fc-rcv {
      type uint64;
      description
        "GoodFcRcv";
    }
    leaf drop-events {
      type uint64;
      description
        "DropEvents";
    }
    leaf undersize-pkts {
      type uint64;
      description
        "UndersizePkts";
    }
    leaf fragments-pkts {
      type uint64;
      description
        "FragmentsPkts";
    }
    leaf oversize-pkts {
      type uint64;
      description
        "OversizePkts";
    }
    leaf jabber-pkts {
      type uint64;
      description
        "JabberPkts";
    }
    leaf mac-rcv-error {
      type uint64;
      description
        "MacRcvError";
    }
    leaf bad-crc {
      type uint64;
      description
        "BadCrc";
    }
    leaf collisions {
      type uint64;
      description
        "Collisions";
    }
    leaf late-collisions {
      type uint64;
      description
        "LateCollisions";
    }
    leaf bad-fc-rcv {
      type uint64;
      description
        "BadFcRcv";
    }
    leaf uc-pkts-rcv {
      type uint64;
      description
        "UcPktsRcv";
    }
    leaf uc-pkts-sent {
      type uint64;
      description
        "UcPktsSent";
    }
    leaf multiple-pkts-sent {
      type uint64;
      description
        "MultiplePktsSent";
    }
    leaf deferred-pkts-sent {
      type uint64;
      description
        "DeferredPktsSent";
    }
    leaf pkts1024to1518-octets {
      type uint64;
      description
        "Pkts1024to1518Octets";
    }
    leaf pkts1519to-max-octets {
      type uint64;
      description
        "Pkts1519toMaxOctets";
    }
  }

  grouping ESD-HWMOD-ETH-SWITCH-PORT-STAT-OP {
    description
      "HwModule Eth_switch PortStat";
    list eth-switch-port-stat {
      key "port-name";
      description
        "eth switch port counters statistic";
      uses HWMOD-ETH-SWITCH-PORT-STAT-B;
    }
  }

  grouping HWMOD-ETH-SWITCH-VLANS-B {
    description
      "Eth_switch Vlans ascii";
    leaf vlan-index {
      type uint32;
      description
        "Vlan Index";
    }
    leaf ports-members {
      type uint32;
      description
        "PortsMembers";
    }
    leaf ports-tagging {
      type uint32;
      description
        "portsTagging";
    }
    leaf is-valid {
      type uint8;
      description
        "IsValid";
    }
  }

  grouping ESD-HWMOD-ETH-SWITCH-VLANS-OP {
    description
      "HwModule Eth_switch Vlans";
    list eth-switch-vlan {
      key "vlan-index";
      description
        "eth switch Vlans list";
      uses HWMOD-ETH-SWITCH-VLANS-B;
    }
  }

  grouping HWMOD-ETH-SWITCH-PORTS-ATTRS-B {
    description
      "Eth_switch PortsAttrs ascii";
    leaf port-name {
      type string {
        length "0..32";
      }
      description
        "port name";
    }
    leaf port-num {
      type uint16;
      description
        "PortNum";
    }
    leaf status {
      type string {
        length "0..64";
      }
      description
        "status ";
    }
    leaf mru-size {
      type uint32;
      description
        "mrusize ";
    }
    leaf attrport-link-up {
      type string {
        length "0..64";
      }
      description
        "port link up";
    }
    leaf attr-port-speed {
      type string {
        length "0..64";
      }
      description
        "port speed";
    }
    leaf attr-port-duplexity {
      type string {
        length "0..64";
      }
      description
        "port duplex";
    }
    leaf is-clear-on-read {
      type string {
        length "0..64";
      }
      description
        "clear on read";
    }
    leaf loopback {
      type string {
        length "0..64";
      }
      description
        "loopback";
    }
    leaf mode {
      type string {
        length "0..64";
      }
      description
        "mode";
    }
    leaf mode-num {
      type uint8;
      description
        "mode numeric value";
    }
  }

  grouping ESD-HWMOD-ETH-SWITCH-PORTS-ATTRS-OP {
    description
      "HwModule Eth_switch PortsAttrs";
    list eth-switch-ports-attr {
      key "port-name";
      description
        "eth switch ports attributes";
      uses HWMOD-ETH-SWITCH-PORTS-ATTRS-B;
    }
  }
}
