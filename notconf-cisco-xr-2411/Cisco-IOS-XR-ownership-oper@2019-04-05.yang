module Cisco-IOS-XR-ownership-oper {
  namespace "http://cisco.com/ns/yang/Cisco-IOS-XR-ownership-oper";
  prefix ownership-oper;

  import cisco-semver {
    prefix semver;
  }

  include Cisco-IOS-XR-ownership-oper-sub1 {
    revision-date 2019-04-05;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ownership package operational data.

     This module contains definitions
     for the following management objects:
       ownership: Ownership Operational Data

     Copyright (c) 2013-2019 by Cisco Systems, Inc.
     All rights reserved.";

  revision 2019-04-05 {
    semver:module-version "1.0.0";
    description
      "Establish semantic version baseline.";
  }
  revision 2015-11-09 {
    description
      "IOS XR 6.0 revision.";
  }

  container ownership {
    config false;
    description
      "Ownership Operational Data";
    container anti-theft {
      description
        "operational Data for re-image status";
      uses ANTITHEFT-INFO;
    }
    container device-ownership {
      description
        "Oper Data for the device ownership";
      uses OWNERSHIP-INFO;
    }
  }
}
