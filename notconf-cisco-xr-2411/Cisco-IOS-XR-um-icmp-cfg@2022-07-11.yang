module Cisco-IOS-XR-um-icmp-cfg {
  namespace "http://cisco.com/ns/yang/Cisco-IOS-XR-um-icmp-cfg";
  prefix um-icmp-cfg;

  import Cisco-IOS-XR-types {
    prefix xr;
  }
  import ietf-inet-types {
    prefix inet;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR icmp package configuration.

     This YANG module augments the
     modules with configuration data.

     Copyright (c) 2020-2022 by Cisco Systems, Inc.
     All rights reserved.";

  revision 2022-07-11 {
    semver:module-version "1.1.0";
    description
      "Added missing description statement to nodes";
  }
  revision 2020-09-23 {
    semver:module-version "1.0.0";
    description
      "Initial release";
  }

  feature icmp_platform_support_config_check {
    description
      "icmp platform support config check";
  }

  container icmp {
    description
      "ICMP options";
    container ipv4 {
      description
        "IPv4 specific";
      container source {
        description
          "source address selection policy";
        container vrf {
          must "not(../rfc)";
          presence "Indicates a vrf node is configured.";
          description
            "Enable Strct VRF source address selection";
        }
        container rfc {
          must "not(../vrf)";
          presence "Indicates a rfc node is configured.";
          description
            "Enable RFC compliance for source address selection";
        }
      }
      container rate-limit {
        description
          "rate limit generation of ICMP messages";
        container unreachable {
          description
            "Destination Unreachable (type3)";
          leaf rate {
            type uint32 {
              range "1..4294967295" {
                description
                  "One ICMP unreachable message in x milliseconds(default is 500ms)";
              }
            }
            must "not(../disable)";
            description
              "One ICMP unreachable message in x milliseconds(default is 500ms)";
          }
          container disable {
            must "not(../rate)";
            presence "Indicates a disable node is configured.";
            description
              "Disable rate limit of ICMP messages";
          }
          container df {
            description
              "Fragmentation needed and DF set (code4)";
            leaf rate {
              type uint32 {
                range "1..4294967295" {
                  description
                    "One ICMP unreachable message in x milliseconds(default is 500ms)";
                }
              }
              must "not(../disable)";
              description
                "One ICMP unreachable message in x milliseconds(default is 500ms)";
            }
            container disable {
              must "not(../rate)";
              presence "Indicates a disable node is configured.";
              description
                "Disable rate limit of ICMP messages";
            }
          }
        }
      }
    }
    container ipv6 {
      description
        "IPv6 specific";
      container source {
        description
          "source address selection policy";
        container vrf {
          must "not(../rfc)";
          presence "Indicates a vrf node is configured.";
          description
            "Enable Strct VRF source address selection";
        }
        container rfc {
          must "not(../vrf)";
          presence "Indicates a rfc node is configured.";
          description
            "Enable RFC compliance for source address selection";
        }
      }
    }
  }
  container traceroute-filter {
    description
      "traceroute configuration";
    container ipv4 {
      description
        "IPv4 specific";
      container protocol {
        description
          "protocol";
        container udp {
          description
            "udp traceroute";
          list traceroute-filter {
            must
              "(source-address or source-address-any)
               and (destination-address or destination-address-any)";
            key "traceroute-filter-id";
            description
              "udp traceroute";
            leaf traceroute-filter-id {
              type uint32 {
                range "1..256" {
                  description
                    "Unique ID for the policy config";
                }
              }
              description
                "traceroute configuration";
            }
            leaf traceroute-filter-id-duped {
              type uint32 {
                range "1..256" {
                  description
                    "Unique ID for the policy config.
                     It must be same value as traceroute-filter-id";
                }
              }
              mandatory true;
              description
                "traceroute configuration";
            }
            leaf vrf {
              type union {
                type string {
                  pattern "default" {
                    description
                      "Default VRF name";
                  }
                }
                type xr:Cisco-ios-xr-string {
                  length "1..1024" {
                    description
                      "VRF name";
                  }
                }
              }
              mandatory true;
              description
                "specify a vrf";
            }
            leaf source-address {
              type inet:ipv4-address-no-zone;
              must "not(../source-address-any)";
              description
                "ipv4 source address for traceroute";
            }
            container source-address-any {
              must "not(../source-address)";
              presence "Indicates an any node is configured.";
              description
                "No traceroute filter for source address";
            }
            leaf source-port-start {
              type uint32 {
                range "0..65535";
              }
              mandatory true;
              description
                "Source port start of range";
            }
            leaf source-port-end {
              type uint32 {
                range "0..65535" {
                  description
                    "Source port end of range";
                }
              }
              mandatory true;
              description
                "Source port end of range";
            }
            leaf destination-address {
              type inet:ipv4-address-no-zone;
              must "not(../destination-address-any)";
              description
                "ipv4 dest address for traceroute";
            }
            container destination-address-any {
              must "not(../destination-address)";
              presence "Indicates an any node is configured.";
              description
                "No traceroute filter for source address";
            }
            leaf destination-port-start {
              type uint32 {
                range "33435..33535" {
                  description
                    "Dst port start of range";
                }
              }
              mandatory true;
              description
                "Dst port start of range";
            }
            leaf destination-port-end {
              type uint32 {
                range "33435..33535" {
                  description
                    "Dst port end of range";
                }
              }
              mandatory true;
              description
                "Dst port end of range";
            }
          }
        }
        container tcp {
          description
            "tcp traceroute";
          list traceroute-filter {
            must
              "(source-address or source-address-any)
               and (destination-address or destination-address-any)";
            key "traceroute-filter-id";
            description
              "tcp traceroute";
            leaf traceroute-filter-id {
              type uint32 {
                range "1..256" {
                  description
                    "Unique ID for the policy config";
                }
              }
              description
                "traceroute configuration";
            }
            leaf traceroute-filter-id-duped {
              type uint32 {
                range "1..256" {
                  description
                    "Unique ID for the policy config.
                     It must be same value as traceroute-filter-id";
                }
              }
              mandatory true;
              description
                "traceroute configuration";
            }
            leaf vrf {
              type union {
                type string {
                  pattern "default" {
                    description
                      "Default VRF name";
                  }
                }
                type xr:Cisco-ios-xr-string {
                  length "1..1024" {
                    description
                      "VRF name";
                  }
                }
              }
              mandatory true;
              description
                "specify a vrf";
            }
            leaf source-address {
              type inet:ipv4-address-no-zone;
              must "not(../source-address-any)";
              description
                "ipv4 source address for traceroute";
            }
            container source-address-any {
              must "not(../source-address)";
              presence "Indicates an any node is configured.";
              description
                "No traceroute filter for source address";
            }
            leaf source-port-start {
              type uint32 {
                range "0..65535";
              }
              mandatory true;
              description
                "Source port start of range";
            }
            leaf source-port-end {
              type uint32 {
                range "0..65535" {
                  description
                    "Source port end of range";
                }
              }
              mandatory true;
              description
                "Source port end of range";
            }
            leaf destination-address {
              type inet:ipv4-address-no-zone;
              must "not(../destination-address-any)";
              description
                "ipv4 dest address for traceroute";
            }
            container destination-address-any {
              must "not(../destination-address)";
              presence "Indicates an destination-address-any node is configured.";
              description
                "No traceroute filter for source address";
            }
            leaf destination-port-start {
              type uint32 {
                range "33435..33535" {
                  description
                    "Dst port start of range";
                }
              }
              mandatory true;
              description
                "Dst port start of range";
            }
            leaf destination-port-end {
              type uint32 {
                range "33435..33535" {
                  description
                    "Dst port end of range";
                }
              }
              mandatory true;
              description
                "Dst port end of range";
            }
          }
        }
      }
    }
    container ipv6 {
      description
        "IPv6 specific";
      container protocol {
        description
          "protocol";
        container udp {
          description
            "udp traceroute";
          list traceroute-filter {
            must
              "(source-address or source-address-any)
               and (destination-address or destination-address-any)";
            key "traceroute-filter-id";
            description
              "udp traceroute";
            leaf traceroute-filter-id {
              type uint32 {
                range "1..256" {
                  description
                    "Unique ID for the policy config";
                }
              }
              description
                "traceroute configuration";
            }
            leaf traceroute-filter-id-duped {
              type uint32 {
                range "1..256" {
                  description
                    "Unique ID for the policy config.
                     It must be same value as traceroute-filter-id";
                }
              }
              mandatory true;
              description
                "traceroute configuration";
            }
            leaf vrf {
              type union {
                type string {
                  pattern "default" {
                    description
                      "Default VRF name";
                  }
                }
                type xr:Cisco-ios-xr-string {
                  length "1..1024" {
                    description
                      "VRF name";
                  }
                }
              }
              mandatory true;
              description
                "specify a vrf";
            }
            leaf source-address {
              type inet:ipv6-address-no-zone;
              must "not(../source-address-any)";
              description
                "ipv6 source address for traceroute";
            }
            container source-address-any {
              must "not(../source-address)";
              presence "Indicates a source-address-any node is configured.";
              description
                "No traceroute filter for source address";
            }
            leaf source-port-start {
              type uint32 {
                range "0..65535";
              }
              mandatory true;
              description
                "Source port start of range";
            }
            leaf source-port-end {
              type uint32 {
                range "0..65535" {
                  description
                    "Source port end of range";
                }
              }
              mandatory true;
              description
                "Source port end of range";
            }
            leaf destination-address {
              type inet:ipv6-address-no-zone;
              must "not(../destination-address-any)";
              description
                "ipv6 dest address for traceroute";
            }
            container destination-address-any {
              must "not(../destination-address)";
              presence "Indicates a destination-address-any node is configured.";
              description
                "No traceroute filter for source address";
            }
            leaf destination-port-start {
              type uint32 {
                range "33435..33535" {
                  description
                    "Dst port start of range";
                }
              }
              mandatory true;
              description
                "Dst port start of range";
            }
            leaf destination-port-end {
              type uint32 {
                range "33435..33535" {
                  description
                    "Dst port end of range";
                }
              }
              mandatory true;
              description
                "Dst port end of range";
            }
          }
        }
        container tcp {
          description
            "tcp traceroute";
          list traceroute-filter {
            must
              "(source-address or source-address-any)
               and (destination-address or destination-address-any)";
            key "traceroute-filter-id";
            description
              "tcp traceroute";
            leaf traceroute-filter-id {
              type uint32 {
                range "1..256" {
                  description
                    "Unique ID for the policy config";
                }
              }
              description
                "traceroute configuration";
            }
            leaf traceroute-filter-id-duped {
              type uint32 {
                range "1..256" {
                  description
                    "Unique ID for the policy config.
                     It must be same value as traceroute-filter-id";
                }
              }
              mandatory true;
              description
                "traceroute configuration";
            }
            leaf vrf {
              type union {
                type string {
                  pattern "default" {
                    description
                      "Default VRF name";
                  }
                }
                type xr:Cisco-ios-xr-string {
                  length "1..1024" {
                    description
                      "VRF name";
                  }
                }
              }
              mandatory true;
              description
                "specify a vrf";
            }
            leaf source-address {
              type inet:ipv6-address-no-zone;
              must "not(../source-address-any)";
              description
                "ipv6 source address for traceroute";
            }
            container source-address-any {
              must "not(../source-address)";
              presence "Indicates a source-address-any node is configured.";
              description
                "No traceroute filter for source address";
            }
            leaf source-port-start {
              type uint32 {
                range "0..65535";
              }
              mandatory true;
              description
                "Source port start of range";
            }
            leaf source-port-end {
              type uint32 {
                range "0..65535" {
                  description
                    "Source port end of range";
                }
              }
              mandatory true;
              description
                "Source port end of range";
            }
            leaf destination-address {
              type inet:ipv6-address-no-zone;
              must "not(../destination-address-any)";
              description
                "ipv6 dest address for traceroute";
            }
            container destination-address-any {
              must "not(../destination-address)";
              presence "Indicates a destination-address-any node is configured.";
              description
                "No traceroute filter for source address";
            }
            leaf destination-port-start {
              type uint32 {
                range "33435..33535" {
                  description
                    "Dst port start of range";
                }
              }
              mandatory true;
              description
                "Dst port start of range";
            }
            leaf destination-port-end {
              type uint32 {
                range "33435..33535" {
                  description
                    "Dst port end of range";
                }
              }
              mandatory true;
              description
                "Dst port end of range";
            }
          }
        }
      }
    }
  }
}
