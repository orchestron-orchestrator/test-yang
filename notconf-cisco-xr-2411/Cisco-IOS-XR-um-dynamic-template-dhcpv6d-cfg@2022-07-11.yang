module Cisco-IOS-XR-um-dynamic-template-dhcpv6d-cfg {
  namespace "http://cisco.com/ns/yang/Cisco-IOS-XR-um-dynamic-template-dhcpv6d-cfg";
  prefix um-dynamic-template-dhcpv6d-cfg;

  import Cisco-IOS-XR-types {
    prefix xr;
  }
  import Cisco-IOS-XR-um-dynamic-template-cfg {
    prefix a1;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR dynamic-template-dhcpv6d package configuration.

     This YANG module augments the
     modules with configuration data.

     Copyright (c) 2020-2022 by Cisco Systems, Inc.
     All rights reserved.";

  revision 2022-07-11 {
    semver:module-version "1.1.0";
    description
      "Added missing description statement to nodes";
  }
  revision 2020-12-14 {
    semver:module-version "1.0.0";
    description
      "Initial release";
  }

  grouping TEMPLATE-BODY {
    description
      "Grouping for template";
    container dhcpv6 {
      description
        "dhcpv6 subcommands";
      leaf delegated-prefix-pool {
        type xr:Cisco-ios-xr-string {
          length "1..64" {
            description
              "Name of delegated prefix pool";
          }
        }
        description
          "Delegated-Prefix-pool Configuration";
      }
      leaf address-pool {
        type xr:Cisco-ios-xr-string {
          length "1..64" {
            description
              "Name of address pool";
          }
        }
        description
          "Address-pool Configuration";
      }
      leaf class-name {
        type xr:Cisco-ios-xr-string {
          length "1..800" {
            description
              "Name of Class";
          }
        }
        description
          "Class Name Configuration";
      }
    }
  }

  augment "/a1:dynamic-template/a1:type/a1:ppp/a1:template" {
    description
      "This augment extends dynamic-template ppp nodes
       configuration";
    uses TEMPLATE-BODY;
  }
  augment "/a1:dynamic-template/a1:type/a1:ipsubscriber/a1:template" {
    description
      "This augment extends dynamic-template ipsubscriber nodes
       configuration";
    uses TEMPLATE-BODY;
  }
}
