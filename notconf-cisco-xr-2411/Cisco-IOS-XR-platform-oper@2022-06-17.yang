module Cisco-IOS-XR-platform-oper {
  namespace "http://cisco.com/ns/yang/Cisco-IOS-XR-platform-oper";
  prefix platform-oper;

  import Cisco-IOS-XR-types {
    prefix xr;
  }
  import cisco-semver {
    prefix semver;
  }

  include Cisco-IOS-XR-platform-oper-sub1 {
    revision-date 2022-06-17;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR platform package operational data.

     This module contains definitions
     for the following management objects:
       platform: Platform information

     Copyright (c) 2013-2022 by Cisco Systems, Inc.
     All rights reserved.";

  revision 2022-06-17 {
    semver:module-version "1.1.0";
    description
      "Added EDT support for shelfmgr";
  }
  revision 2020-07-07 {
    semver:module-version "1.0.0";
    description
      "Added VM class for Thin XR model";
  }
  revision 2020-05-14 {
    semver:module-version "1.0.0";
    description
      "New model, replaces Cisco-IOS-XR-plat-chas-invmgr-ng-oper";
  }
  revision 2019-04-05 {
    description
      "Establish semantic version baseline.";
  }
  revision 2015-11-09 {
    description
      "IOS XR 6.0 revision.";
  }

  grouping STATE {
    description
      "Common node of instance, slot";
    container state {
      description
        "State information";
      uses PLATFORM-INFO;
    }
  }

  grouping SLOT-TABLE {
    description
      "Common node of rack, rack";
    container slots {
      description
        "Table of slots";
      list slot {
        key "slot-name";
        description
          "Slot name";
        container instances {
          description
            "Table of Instances";
          list instance {
            key "instance-name";
            description
              "Instance name";
            leaf instance-name {
              type string;
              description
                "Instance name";
            }
            uses STATE;
          }
        }
        container vm {
          description
            "VM information";
          uses VM-INFO;
        }
        leaf slot-name {
          type xr:Cisco-ios-xr-string;
          description
            "Slot name";
        }
        uses STATE;
      }
    }
  }

  container platform {
    config false;
    description
      "Platform information";
    container racks {
      description
        "Table of racks";
      list rack {
        key "rack-name";
        description
          "Rack name";
        leaf rack-name {
          type xr:Cisco-ios-xr-string;
          description
            "Rack name";
        }
        uses SLOT-TABLE;
      }
    }
  }
}
