module Cisco-IOS-XR-um-pbr-cfg {
  namespace "http://cisco.com/ns/yang/Cisco-IOS-XR-um-pbr-cfg";
  prefix um-pbr-cfg;

  import Cisco-IOS-XR-types {
    prefix xr;
  }
  import Cisco-IOS-XR-um-subscriber-cfg {
    prefix a2;
  }
  import Cisco-IOS-XR-um-dynamic-template-cfg {
    prefix a3;
  }
  import Cisco-IOS-XR-um-dyn-tmpl-service-policy-cfg {
    prefix a4;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR pbr package configuration.

     This YANG module augments the
     modules with configuration data.

     Copyright (c) 2021-2022 by Cisco Systems, Inc.
     All rights reserved.";

  revision 2022-07-11 {
    semver:module-version "1.1.0";
    description
      "Added missing description statement to nodes";
  }
  revision 2021-05-19 {
    semver:module-version "1.0.0";
    description
      "Initial release";
  }

  grouping TEMPLATE-BODY {
    description
      "Grouping for template";
    container type {
      description
        "Configure PBR Service policy";
      leaf pbr {
        type xr:Cisco-ios-xr-string {
          length "1..800" {
            description
              "Name of the service policy";
          }
          pattern "[a-zA-Z0-9][a-zA-Z0-9._@$%+#:=<>-]{0,62}";
        }
        description
          "PBR Service policy";
      }
    }
  }

  augment "/a2:subscriber" {
    description
      "This augment extends subscriber nodes configuration";
    container http-enrichment {
      description
        "Enable http-enrichment";
      leaf-list parameter-list {
        type enumeration {
          enum "subscriber-mac" {
            value 1;
            description
              "BNG identifier interface";
          }
          enum "subscriber-ip" {
            value 2;
            description
              "Subscriber ipv4 and ipv6 address";
          }
          enum "hostname" {
            value 4;
            description
              "BNG hostname";
          }
          enum "bng-interface" {
            value 8;
            description
              "BNG identifier interface";
          }
        }
        max-elements 4;
        description
          "http-enrichment parameter list";
      }
    }
    leaf bng-interface {
      type xr:Interface-name;
      description
        "BNG identifier interface";
    }
  }
  augment "/a3:dynamic-template/a3:type/a3:ppp/a3:template/a4:service-policy" {
    description
      "This augment extends dynamic-tempalte ppp nodes
       configuration";
    uses TEMPLATE-BODY;
  }
  augment "/a3:dynamic-template/a3:type/a3:ipsubscriber/a3:template/a4:service-policy" {
    description
      "This augment extends dynamic-template ipsubscriber nodes
       configuration";
    uses TEMPLATE-BODY;
  }
  augment "/a3:dynamic-template/a3:type/a3:service/a3:template/a4:service-policy" {
    description
      "This augment extends dynamic-template service nodes
       configuration";
    uses TEMPLATE-BODY;
  }
}
