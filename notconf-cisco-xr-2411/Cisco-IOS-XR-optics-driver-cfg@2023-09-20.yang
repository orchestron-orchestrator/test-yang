module Cisco-IOS-XR-optics-driver-cfg {
  namespace "http://cisco.com/ns/yang/Cisco-IOS-XR-optics-driver-cfg";
  prefix optics-driver-cfg;

  import cisco-semver {
    prefix semver;
  }
  import Cisco-IOS-XR-ifmgr-cfg {
    prefix a1;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR optics-driver package configuration.

     This YANG module augments the
       Cisco-IOS-XR-ifmgr-cfg
     module with configuration data.

     Copyright (c) 2013-2023 by Cisco Systems, Inc.
     All rights reserved.";

  revision 2023-09-20 {
    semver:module-version "3.1.0";
    description
      "New leaf to disable BER monitoring
       2023-02-03
         New breakout mode of 1x40 added
       2022-09-30
         New breakout modes of 8x100 added.
       2022-05-09
         Removed unused module.";
  }
  revision 2021-01-15 {
    semver:module-version "3.0.0";
    description
      "Order of the breakout modes of 4x100 and 4x10 interchanged";
  }
  revision 2020-04-22 {
    semver:module-version "2.0.0";
    description
      "Augmentation to Cisco-IOS-XR-ifmgr-cfg. New breakout modes of 4x100 and 8x50 added";
  }
  revision 2019-04-05 {
    semver:module-version "1.0.0";
    description
      "Establish semantic version baseline.";
  }
  revision 2016-03-21 {
    description
      "Schema added.";
  }
  revision 2015-11-09 {
    description
      "IOS XR 6.0 revision.";
  }

  typedef Breakout-type-list {
    type string {
      pattern "(4x100)|(4x25)|(4x10)|(2x50)|(8x50)|(3x100)|(2x100)|(1x100)|(8x100)|(1x40)";
    }
    description
      "4x100:4x100 optics breakout config, 4x25:4x25
       optics breakout config, 4x10:4x10 optics breakout
       config, 2x50:2x50 optics breakout config, 8x50
       :8x50 optics breakout config, 3x100:3x100 optics
       breakout config, 2x100:2x100 optics breakout
       config, 1x100:1x100 optics breakout config, 8x100
       :8x100 optics breakout config, 1x40:1x40 optics
       breakout config";
  }

  augment "/a1:interface-configurations/a1:interface-configuration" {
    description
      "This augment extends the configuration data of
       'Cisco-IOS-XR-ifmgr-cfg'";
    leaf disable-optics-ber-mon {
      type empty;
      description
        "Disable BER monitoring alarms ";
    }
  }
  augment "/a1:interface-configurations/a1:interface-configuration" {
    description
      "This augment extends the configuration data of
       'Cisco-IOS-XR-ifmgr-cfg'";
    leaf breakout {
      type Breakout-type-list;
      description
        "breakout mode configuration";
    }
  }
}
