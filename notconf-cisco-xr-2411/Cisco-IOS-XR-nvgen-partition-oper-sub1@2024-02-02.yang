submodule Cisco-IOS-XR-nvgen-partition-oper-sub1 {
  belongs-to Cisco-IOS-XR-nvgen-partition-oper {
    prefix Cisco-IOS-XR-nvgen-partition-oper;
  }

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR nvgen-partition package operational data.

     Copyright (c) 2013-2024 by Cisco Systems, Inc.
     All rights reserved.";

  revision 2024-02-02 {
    semver:module-version "1.0.0";
    description
      "Add display partition info";
  }
  revision 2019-04-05 {
    description
      "Establish semantic version baseline.";
  }
  revision 2015-11-09 {
    description
      "IOS XR 6.0 revision.";
  }

  grouping NVGEN-PARTITION-INFO {
    description
      "All nvgen partition information";
    leaf p-name {
      type string;
      description
        "Partition name";
    }
    leaf root-dir {
      type string;
      description
        "root dir name";
    }
    leaf p-subtrees {
      type string;
      description
        "Subtree";
    }
    leaf time-modified {
      type string;
      description
        "Last  time modified ";
    }
  }
}
