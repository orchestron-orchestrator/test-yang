module Cisco-IOS-XR-ipv6-io-oper {
  namespace "http://cisco.com/ns/yang/Cisco-IOS-XR-ipv6-io-oper";
  prefix ipv6-io-oper;

  import Cisco-IOS-XR-types {
    prefix xr;
  }
  import cisco-semver {
    prefix semver;
  }

  include Cisco-IOS-XR-ipv6-io-oper-sub1 {
    revision-date 2019-10-21;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ipv6-io package operational data.

     This module contains definitions
     for the following management objects:
       ipv6-io: IPv6 IO Operational Data

     Copyright (c) 2013-2019 by Cisco Systems, Inc.
     All rights reserved.";

  revision 2019-10-21 {
    semver:module-version "1.1.0";
    description
      "Added List of VRF IDs for path-mtu cache.";
  }
  revision 2019-04-05 {
    semver:module-version "1.0.1";
    description
      "Establish semantic version baseline.";
  }
  revision 2015-11-09 {
    description
      "IOS XR 6.0 revision.";
  }
  revision 2015-08-27 {
    description
      "IOS XR 6.0.0 revision.";
  }

  container ipv6-io {
    config false;
    description
      "IPv6 IO Operational Data";
    container nodes {
      description
        "Node-specific IPv6 IO operational data";
      list node {
        key "node-name";
        description
          "IPv6 network operational data for a particular
           node";
        container statistics {
          description
            "Statistical IPv6 network operational data for
             a node";
          container traffic {
            description
              "Traffic statistics for a node";
            uses IPV6-TRAFFIC;
          }
        }
        container vrfs {
          description
            "VRF specific IPv6 IO operational data";
          list vrf {
            key "vrf-name";
            description
              "VRF name of an IPV6 interface";
            container path-mtu-cache {
              description
                "IPv6 PMTU Cache Information";
              uses IPV6-PMTU-CACHE-LIST;
            }
            leaf vrf-name {
              type xr:Cisco-ios-xr-string;
              description
                "The VRF name";
            }
          }
        }
        leaf node-name {
          type xr:Node-id;
          description
            "Node name";
        }
      }
    }
  }
}
