module Cisco-IOS-XR-gnsi-authorization-act {
  namespace "http://cisco.com/ns/yang/Cisco-IOS-XR-gnsi-authorization-act";
  prefix gnsi-authorization-act;

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR gNSI load policy action package configuration.

     Copyright (c) 2023 by Cisco Systems, Inc.
     All rights reserved.";

  revision 2023-06-05 {
    semver:module-version "1.0.0";
    description
      "IOS XR 7.11.1 revision.";
  }

  typedef authorization-type {
    type enumeration {
      enum "unknown" {
        description
          "Invalid default type";
      }
      enum "service" {
        description
          "Service-level authorization";
      }
      enum "path" {
        description
          "Path-level authorization";
      }
    }
    description
      "Authorization type";
  }

  rpc load-policy {
    description
      "Load an authorization policy";

    input {
      leaf type {
        type authorization-type;
        mandatory true;
        description
          "Authorization type";
      }
      leaf path {
        type string;
        mandatory true;
        description
          "Policy path";
      }
    }
  }
}
