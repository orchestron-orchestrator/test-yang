module Cisco-IOS-XR-ptp-pd-cfg {
  namespace "http://cisco.com/ns/yang/Cisco-IOS-XR-ptp-pd-cfg";
  prefix ptp-pd-cfg;

  import Cisco-IOS-XR-types {
    prefix xr;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ptp-pd package configuration.

     This module contains definitions
     for the following management objects:
       log-servo-root: Servo Log for Platform

     Copyright (c) 2013-2021 by Cisco Systems, Inc.
     All rights reserved.";

  revision 2021-12-15 {
    semver:module-version "1.2.0";
    description
      "Servo-driver-enable added to YANG.";
  }
  revision 2021-01-30 {
    semver:module-version "1.1.0";
    description
      "In-memory timestamps buffer size added.";
  }
  revision 2019-04-05 {
    semver:module-version "1.0.1";
    description
      "Establish semantic version baseline.";
  }
  revision 2018-05-08 {
    description
      "Schema added.";
  }
  revision 2015-11-09 {
    description
      "IOS XR 6.0 revision.";
  }

  container log-servo-root {
    description
      "Servo Log for Platform";
    leaf servo-driver-enable {
      type boolean;
      description
        "Enable Servo driver logs streaming";
    }
    leaf servo-event-enable {
      type boolean;
      description
        "Enable Servo change log events";
    }
    leaf timestamps-memory-size {
      type xr:Hex-integer;
      description
        "Memory size for PTP timestamps logging";
    }
  }
}
