submodule Cisco-IOS-XR-asic-error-oper-sub1 {
  belongs-to Cisco-IOS-XR-asic-error-oper {
    prefix Cisco-IOS-XR-asic-error-oper;
  }

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR asic-error package operational data.

     Copyright (c) 2013-2023 by Cisco Systems, Inc.
     All rights reserved.";

  revision 2023-06-08 {
    semver:module-version "1.1.0";
    description
      "Datatype change from hex to string for Asic Information.";
  }
  revision 2021-02-10 {
    semver:module-version "1.1.0";
    description
      "Introduced working oper model for asic-errors.";
  }
  revision 2019-09-27 {
    semver:module-version "1.0.0";
    description
      "Introduced working oper model for asic-errors.";
  }
  revision 2019-09-24 {
    semver:module-version "1.0.0";
    description
      "Introduced working oper model for asic-errors.";
  }
  revision 2019-04-05 {
    description
      "Establish semantic version baseline.";
  }
  revision 2015-11-09 {
    description
      "IOS XR 6.0 revision.";
  }

  grouping ASIC-SUMMARY-BG {
    description
      "ASIC SUMMARY BG";
    leaf legacy-client {
      type boolean;
      description
        "boolean field for legacy client";
    }
    leaf cih-client {
      type boolean;
      description
        "boolean field for cih client";
    }
    leaf pac-client {
      type boolean;
      description
        "boolean field for pac client";
    }
    list sum-data {
      description
        "summary data for asic error";
      uses SUMMARY-DATA-BG;
    }
  }

  grouping COUNT-INFO-BG {
    description
      "COUNT INFO BG";
    leaf name {
      type string;
      description
        "Name of asic error";
    }
    leaf count {
      type uint32;
      description
        "Number of occurrence";
    }
  }

  grouping SUMMARY-DATA-BG {
    description
      "SUMMARY DATA BG";
    leaf num-nodes {
      type uint32;
      description
        "Number of nodes";
    }
    leaf crc-err-count {
      type uint32;
      description
        "CRC Error Count";
    }
    leaf sbe-err-count {
      type uint32;
      description
        "Single Bit Error Count";
    }
    leaf mbe-err-count {
      type uint32;
      description
        "Multi-Bit Error Count";
    }
    leaf par-err-count {
      type uint32;
      description
        "Parity Error Count";
    }
    leaf gen-err-count {
      type uint32;
      description
        "General Error Count";
    }
    leaf reset-err-count {
      type uint32;
      description
        "Reset Error Count";
    }
    list err-count {
      description
        "Error Count";
      uses COUNT-INFO-BG;
    }
    list pcie-err-count {
      description
        "PCIE Error Count";
      uses COUNT-INFO-BG;
    }
    list pacerr-count {
      description
        "Pac Error Count";
      uses COUNT-INFO-BG;
    }
    list node-key {
      description
        "Keys to the node";
      leaf entry {
        type uint32;
        description
          "Keys to the node";
      }
    }
  }
}
