submodule Cisco-IOS-XR-asic-errors-oper-sub1 {
  belongs-to Cisco-IOS-XR-asic-errors-oper {
    prefix Cisco-IOS-XR-asic-errors-oper;
  }

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR asic-errors package operational data.

     This model is obsolete and is replaced by
     Cisco-IOS-XR-asic-error-oper.yang which will provide the
     compatible functionalities.

     Copyright (c) 2013-2020 by Cisco Systems, Inc.
     All rights reserved.";

  revision 2020-11-11 {
    semver:module-version "1.2.0";
    description
      "The model moved to obsolete list.";
  }
  revision 2019-09-27 {
    semver:module-version "1.1.0";
    description
      "Fixed type translation error.";
  }
  revision 2019-04-05 {
    semver:module-version "1.1.0";
    description
      "Establish semantic version baseline.";
  }
  revision 2017-09-07 {
    description
      "Fixed type translation error.";
  }
  revision 2015-11-09 {
    description
      "IOS XR 6.0 revision.";
  }

  grouping CIHERR-ERROR-DATA-BG {
    description
      "CIHERR ERROR DATA BG";
    leaf at-time {
      type uint64;
      description
        "Asic error time";
    }
    leaf at-time-nsec {
      type uint64;
      description
        "Asic error nsec";
    }
    leaf counter-val {
      type uint32;
      description
        "Number of occurrence";
    }
    leaf error-desc {
      type string;
      description
        "Error description";
    }
    list error-regval {
      description
        "Error register value";
      leaf entry {
        type uint8;
        description
          "Error register value";
      }
    }
  }

  grouping CSRS-INFO-BG {
    description
      "CSRS INFO BG";
    leaf name {
      type string;
      description
        "Name of csrs register";
    }
    leaf address {
      type uint64;
      description
        "Address of csrs register";
    }
    leaf width {
      type uint32;
      description
        "Width of csrs register";
    }
  }

  grouping CIHERR-NODE-BG {
    description
      "CIHERR NODE BG";
    leaf name {
      type string;
      description
        "Name assigned to mem";
    }
    leaf asic-info {
      type string;
      description
        "Name of rack/board/asic";
    }
    leaf node-key {
      type uint32;
      description
        "32 bit key";
    }
    leaf alarm-on {
      type boolean;
      description
        "High threshold crossed";
    }
    leaf thresh-hi {
      type uint32;
      description
        "High threshold value";
    }
    leaf period-hi {
      type uint32;
      description
        "High period value";
    }
    leaf thresh-lo {
      type uint32;
      description
        "High threshold value";
    }
    leaf period-lo {
      type uint32;
      description
        "High period value";
    }
    leaf count {
      type uint32;
      description
        "Accumulated count";
    }
    leaf intr-type {
      type uint32;
      description
        "Type of error";
    }
    leaf leaf-id {
      type uint32;
      description
        "Leaf ID defined in user data";
    }
    leaf last-cleared {
      type uint64;
      description
        "Time  cleared";
    }
    list csrs-info {
      description
        "List of csrs_info";
      uses CSRS-INFO-BG;
    }
    list last-err {
      description
        "Last Printable error information";
      uses CIHERR-ERROR-DATA-BG;
    }
  }

  grouping CIHERR-NODES-BG {
    description
      "CIHERR NODES BG";
    list error {
      description
        "Collection of errors";
      uses CIHERR-NODE-BG;
    }
  }
}
