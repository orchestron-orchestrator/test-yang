module Cisco-IOS-XR-drivers-media-eth-act {
  namespace "http://cisco.com/ns/yang/Cisco-IOS-XR-drivers-media-eth-act";
  prefix eth-drvr-act;

  import cisco-semver {
    prefix semver;
  }
  import Cisco-IOS-XR-types {
    prefix csc;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR action package configuration.

     Copyright (c) 2018-2019, 2021-2022 by Cisco Systems, Inc.
     All rights reserved.";

  revision 2022-04-22 {
    semver:module-version "1.0.1";
    description
      "Moved task and cli details to private model";
  }
  revision 2019-04-05 {
    semver:module-version "1.0.0";
    description
      "Establish semantic version baseline.";
  }
  revision 2018-02-12 {
    description
      "IOS XR 6.5.1 revision.";
  }

  rpc clear-controller-counters {
    description
      "Clear controller stats for Ethernet controllers and interfaces";

    input {
      leaf controller-name {
        type csc:Interface-name;
        mandatory true;
        description
          "Ethernet Controller or Interface name";
      }
    }
  }
}
