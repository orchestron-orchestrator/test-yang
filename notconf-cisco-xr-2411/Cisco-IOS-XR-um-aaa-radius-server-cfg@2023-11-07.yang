module Cisco-IOS-XR-um-aaa-radius-server-cfg {
  namespace "http://cisco.com/ns/yang/Cisco-IOS-XR-um-aaa-radius-server-cfg";
  prefix um-aaa-radius-server-cfg;

  import Cisco-IOS-XR-types {
    prefix xr;
  }
  import ietf-inet-types {
    prefix inet;
  }
  import Cisco-IOS-XR-um-aaa-cfg {
    prefix a1;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR aaa-radius-server package configuration.

     This YANG module augments the
     modules with configuration data.

     Copyright (c) 2021-2023 by Cisco Systems, Inc.
     All rights reserved.";

  revision 2023-11-07 {
    semver:module-version "1.1.0";
    description
      "Added RADIUS over DTLS support
       2022-07-11
         Added missing description statement to nodes";
  }
  revision 2021-02-10 {
    semver:module-version "1.0.0";
    description
      "Initial release";
  }

  feature check_input_typ6_validity {
    description
      "check input typ6 validity";
  }

  augment "/a1:aaa" {
    description
      "This augment extends aaa nodes configuration";
    container group {
      description
        "AAA group definitions";
      container server {
        description
          "AAA Server group definition";
        container radius {
          description
            "RADIUS server-group definition";
          container server-groups {
            description
              "Server group name";
            list server-group {
              key "server-group-name";
              description
                "Server group name";
              leaf server-group-name {
                type string {
                  length "1..253" {
                    description
                      "server-group name.
                       Allowed special chars for radius server group are _,-,.,;,:,$,#,space allowed with backslash";
                  }
                }
                description
                  "Server group name";
              }
              container servers {
                description
                  "Specify a RADIUS server";
                list server {
                  key "ordering-index address auth-port acct-port";
                  description
                    "Specify a RADIUS server";
                  leaf ordering-index {
                    type uint32;
                    description
                      "This is used to sort the users in the order of
                       precedence";
                  }
                  leaf address {
                    type inet:ip-address-no-zone;
                    description
                      "Specify a RADIUS server";
                  }
                  leaf auth-port {
                    type uint32 {
                      range "0..65535" {
                        description
                          "Authentication port number (default 1645)";
                      }
                    }
                    description
                      "RADIUS server authentication port";
                  }
                  leaf acct-port {
                    type uint32 {
                      range "0..65535" {
                        description
                          "Accounting port number (default 1645)";
                      }
                    }
                    description
                      "RADIUS server accounting port";
                  }
                }
              }
              container load-balance {
                description
                  "Radius load-balancing options.";
                container method {
                  description
                    "Method by which the next host will be picked.";
                  container least-outstanding {
                    presence "Indicates a least-outstanding node is configured.";
                    description
                      "Pick the server with the least transactions outstanding.";
                    leaf batch-size {
                      type uint32 {
                        range "1..1500" {
                          description
                            "Batch size for selection of the server (default 25)";
                        }
                      }
                      description
                        "Batch size for selection of the server.";
                    }
                    container ignore-preferred-server {
                      presence "Indicates a ignore-preferred-server node is configured.";
                      description
                        "Disable preferred server for this Server Group";
                    }
                  }
                }
              }
              leaf deadtime {
                type uint32 {
                  range "1..1440" {
                    description
                      "Deadtime limit in minutes (default 0)";
                  }
                }
                description
                  "Time in minutes after which a RADIUS server will be marked UP after it has gone dead";
              }
              container throttle {
                presence "Indicates a throttle node is configured.";
                description
                  "Radius throttling options.";
                leaf access {
                  type uint32 {
                    range "0..65535" {
                      description
                        "Number of outstanding access requests after which throttling should be performed (Preferable value 100)";
                    }
                  }
                  description
                    "To flow control the number of access requests sent to a radius server";
                }
                leaf access-timeout {
                  type uint32 {
                    range "1..10" {
                      description
                        "Number of timeouts for a transaction (default is 3)";
                    }
                  }
                  must "../access";
                  description
                    "Specify the number of timeouts exceeding which a throttled access request is dropped";
                }
                leaf accounting {
                  type uint32 {
                    range "0..65535" {
                      description
                        "Number of outstanding accounting transactions after which throttling should be performed (Preferable value 100)";
                    }
                  }
                  description
                    "To flow control the number of accounting requests sent to a radius server.";
                }
              }
              container server-privates {
                description
                  "Specify a private (to this server group) RADIUS server";
                list server-private {
                  key "ordering-index address auth-port acct-port";
                  description
                    "Specify a private (to this server group) RADIUS server";
                  leaf ordering-index {
                    type uint32;
                    description
                      "This is used to sort the users in the order of
                       precedence";
                  }
                  leaf address {
                    type inet:ip-address-no-zone;
                    description
                      "Specify a private (to this server group) RADIUS server";
                  }
                  leaf auth-port {
                    type uint32 {
                      range "0..65535" {
                        description
                          "Authentication port number (default 1645)";
                      }
                    }
                    description
                      "RADIUS server authentication port";
                  }
                  leaf acct-port {
                    type uint32 {
                      range "0..65535" {
                        description
                          "Accounting port number (default 1645)";
                      }
                    }
                    description
                      "RADIUS server accounting port";
                  }
                  container key {
                    description
                      "RADIUS server key";
                    leaf seven {
                      type xr:Proprietary-password;
                      must "not(../six)";
                      description
                        "Specifies that an encrypted key will follow";
                    }
                    leaf six {
                      if-feature "check_input_typ6_validity";
                      type xr:Proprietary-password;
                      must "not(../seven)";
                      description
                        "Specifies that an encrypted type 6 key will follow";
                    }
                  }
                  leaf timeout {
                    type uint32 {
                      range "1..1000" {
                        description
                          "Timeout value in seconds to wait for server to reply";
                      }
                    }
                    description
                      "Time to wait for a RADIUS server to reply";
                  }
                  leaf retransmit {
                    type uint32 {
                      range "1..100" {
                        description
                          "Retransmit limit";
                      }
                    }
                    description
                      "Number of times a RADIUS request is re-sent to a server";
                  }
                  container test {
                    description
                      "Automated testing functionality";
                    leaf username {
                      type xr:Cisco-ios-xr-string {
                        length "1..800" {
                          description
                            "Username for automated testing";
                        }
                      }
                      description
                        "Username to be tested for automated testing";
                    }
                  }
                  leaf idle-time {
                    type uint32 {
                      range "1..60" {
                        description
                          "Idle-time value";
                      }
                    }
                    description
                      "Idle time after which automated test should start";
                  }
                  container ignore-auth-port {
                    presence "Indicates a ignore-auth-port node is configured.";
                    description
                      "Turn off automated testing on auth-port";
                  }
                  container ignore-acct-port {
                    presence "Indicates a ignore-acct-port node is configured.";
                    description
                      "Turn off automated testing on acct-port";
                  }
                }
              }
              leaf vrf {
                type xr:Cisco-ios-xr-string {
                  length "1..32" {
                    description
                      "Name of the VRF";
                  }
                }
                description
                  "VRF to which this server group belongs to";
              }
              leaf source-interface {
                type xr:Interface-name;
                description
                  "Specify interface for source address in RADIUS packets";
              }
              container authorization {
                description
                  "Specify a RADIUS attribute filter for authorization";
                container request {
                  description
                    "Attibute filtering for Access-Request";
                  container accept {
                    must "not(../reject)";
                    presence "Indicates a accept node is configured.";
                    description
                      "Accept only those attributes specified in this list";
                  }
                  container reject {
                    must "not(../accept)";
                    presence "Indicates a reject node is configured.";
                    description
                      "Reject the attributes specified in this list";
                  }
                  leaf radius-attribute-list {
                    type xr:Cisco-ios-xr-string {
                      length "1..1024" {
                        description
                          "Name of RADIUS attribute list";
                      }
                    }
                    must "../accept or ../reject";
                    description
                      "Name of RADIUS attribute list";
                  }
                }
                container reply {
                  description
                    "Attibute filtering for Access-Request";
                  container accept {
                    must "not(../reject)";
                    presence "Indicates a accept node is configured.";
                    description
                      "Accept only those attributes specified in this list";
                  }
                  container reject {
                    must "not(../accept)";
                    presence "Indicates a reject node is configured.";
                    description
                      "Reject the attributes specified in this list";
                  }
                  leaf radius-attribute-list {
                    type xr:Cisco-ios-xr-string {
                      length "1..1024" {
                        description
                          "Name of RADIUS attribute list";
                      }
                    }
                    must "../accept or ../reject";
                    description
                      "Name of RADIUS attribute list";
                  }
                }
              }
              container accounting {
                description
                  "Specify a RADIUS attribute filter for authorization";
                container request {
                  description
                    "Attibute filtering for Access-Request";
                  container accept {
                    must "not(../reject)";
                    presence "Indicates a accept node is configured.";
                    description
                      "Accept only those attributes specified in this list";
                  }
                  container reject {
                    must "not(../accept)";
                    presence "Indicates a reject node is configured.";
                    description
                      "Reject the attributes specified in this list";
                  }
                  leaf radius-attribute-list {
                    type xr:Cisco-ios-xr-string {
                      length "1..1024" {
                        description
                          "Name of RADIUS attribute list";
                      }
                    }
                    must "../accept or ../reject";
                    description
                      "Name of RADIUS attribute list";
                  }
                }
                container reply {
                  description
                    "Attibute filtering for Access-Request";
                  container accept {
                    must "not(../reject)";
                    presence "Indicates a accept node is configured.";
                    description
                      "Accept only those attributes specified in this list";
                  }
                  container reject {
                    must "not(../accept)";
                    presence "Indicates a reject node is configured.";
                    description
                      "Reject the attributes specified in this list";
                  }
                  leaf radius-attribute-list {
                    type xr:Cisco-ios-xr-string {
                      length "1..1024" {
                        description
                          "Name of RADIUS attribute list";
                      }
                    }
                    must "../accept or ../reject";
                    description
                      "Name of RADIUS attribute list";
                  }
                }
              }
            }
          }
        }
      }
    }
    container server {
      description
        "AAA Server ";
      container radius {
        description
          "AAA Server - Radius Definition";
        container dynamic-author {
          description
            "Radius Dynamic Author Server Configurations";
          leaf port {
            type uint32 {
              range "1000..5000" {
                description
                  "port number";
              }
            }
            description
              "Specify the COA Server port to listen on";
          }
          container ignore {
            description
              "ignore options";
            container server-key {
              presence "Indicates a server-key node is configured.";
              description
                "ignore  server-key";
            }
          }
          container server-key {
            description
              "Set the Shared secret to verify client COA requests";
            leaf seven {
              type xr:Proprietary-password;
              must "not(../six)";
              description
                "Specifies that an encrypted key will follow";
            }
            leaf six {
              if-feature "check_input_typ6_validity";
              type xr:Proprietary-password;
              must "not(../seven)";
              description
                "Specifies that an encrypted type 6 key will follow";
            }
          }
          container clients {
            description
              "COA client configuration";
            list client {
              key "address vrf";
              description
                "COA client configuration";
              leaf address {
                type inet:ip-address-no-zone;
                description
                  "COA client configuration";
              }
              leaf vrf {
                type union {
                  type string {
                    pattern "default" {
                      description
                        "Default VRF";
                    }
                  }
                  type xr:Cisco-ios-xr-string {
                    length "1..32" {
                      description
                        "Name of the VRF";
                    }
                  }
                }
                description
                  "VRF to which COA Client belongs";
              }
              container server-key {
                description
                  "COA client shared secret key";
                leaf seven {
                  type xr:Proprietary-password;
                  must "not(../six)";
                  description
                    "Specifies that an encrypted key will follow";
                }
                leaf six {
                  if-feature "check_input_typ6_validity";
                  type xr:Proprietary-password;
                  must "not(../seven)";
                  description
                    "Specifies that an encrypted type 6 key will follow";
                }
              }
            }
          }
        }
      }
    }
    container radius-server {
      description
        "RADIUS server definition";
      container hosts {
        description
          "Specify a RADIUS server";
        list host {
          key "ordering-index address auth-port acct-port";
          description
            "Specify a RADIUS server";
          leaf ordering-index {
            type uint32;
            description
              "This is used to sort the users in the order of
               precedence";
          }
          leaf address {
            type inet:ip-address-no-zone;
            description
              "IPv4/IPv6 address of RADIUS server";
          }
          leaf auth-port {
            type uint32 {
              range "0..65535" {
                description
                  "Authentication port number (default 1645)";
              }
            }
            description
              "UDP port for RADIUS authentication requests (default is 1645)";
          }
          leaf acct-port {
            type uint32 {
              range "0..65535" {
                description
                  "Accounting port number (default 1646)";
              }
            }
            description
              "UDP port for RADIUS accounting requests (default is 1646)";
          }
          leaf timeout {
            type uint32 {
              range "1..1000" {
                description
                  "Timeout value in seconds to wait for server to reply";
              }
            }
            description
              "Time to wait for this RADIUS server to reply (overrides global timeout)";
          }
          leaf retransmit {
            type uint32 {
              range "1..100" {
                description
                  "Retransmit value";
              }
            }
            description
              "Number of times a RADIUS request is re-sent to a server (overrides global retransmit value)";
          }
          container key {
            description
              "per-server encryption key (overrides default)";
            leaf seven {
              type xr:Proprietary-password;
              must "not(../six)";
              description
                "Specifies that an encrypted key will follow";
            }
            leaf six {
              if-feature "check_input_typ6_validity";
              type xr:Proprietary-password;
              must "not(../seven)";
              description
                "Specifies that an encrypted type 6 key will follow";
            }
          }
          container test {
            description
              "Automated testing functionality";
            leaf username {
              type xr:Cisco-ios-xr-string {
                length "1..800" {
                  description
                    "Username for automated testing";
                }
              }
              description
                "Username to be tested for automated testing";
            }
          }
          leaf idle-time {
            type uint32 {
              range "1..60" {
                description
                  "Idle-time value in min";
              }
            }
            description
              "Idle time after which automated test should start";
          }
          container ignore-auth-port {
            presence "Indicates a ignore-auth-port node is configured.";
            description
              "Turn off automated testing on auth-port";
          }
          container ignore-acct-port {
            presence "Indicates a ignore-acct-port node is configured.";
            description
              "Turn off automated testing on acct-port";
          }
          container dtls-server {
            description
              "RADIUS over DTLS support";
            leaf trustpoint {
              type xr:Cisco-ios-xr-string {
                length "1..800" {
                  description
                    "Trustpoint";
                }
              }
              description
                "Trustpoint to be used for RADIUS over DTLS";
            }
          }
        }
      }
      container key {
        description
          "Set RADIUS encryption key";
        leaf seven {
          type xr:Proprietary-password;
          must "not(../six)";
          description
            "Specifies that an encrypted key will follow";
        }
        leaf six {
          if-feature "check_input_typ6_validity";
          type xr:Proprietary-password;
          must "not(../seven)";
          description
            "Specifies that an encrypted type 6 key will follow";
        }
      }
      leaf timeout {
        type uint32 {
          range "1..1000" {
            description
              "Timeout value in seconds to wait for server to reply";
          }
        }
        description
          "Time to wait for a RADIUS server to reply (default 5)";
      }
      container retransmit {
        description
          "Specify the number of retries to active server";
        leaf retries {
          type uint32 {
            range "1..100" {
              description
                "<1-100>  Number of retries for a transaction (default is 3)";
            }
          }
          must "not(../disable)";
          description
            "<1-100>  Number of retries for a transaction (default is 3)";
        }
        container disable {
          must "not(../retries)";
          presence "Indicates a disable node is configured.";
          description
            "Disable Radius server retransmit";
        }
      }
      container load-balance {
        description
          "Radius load-balancing options.";
        container method {
          description
            "Method by which the next host will be picked.";
          container least-outstanding {
            presence "Indicates a least-outstanding node is configured.";
            description
              "Pick the server with the least transactions outstanding.";
            leaf batch-size {
              type uint32 {
                range "1..1500" {
                  description
                    "Batch size for selection of the server (default 25)";
                }
              }
              description
                "Batch size for selection of the server.";
            }
            container ignore-preferred-server {
              presence "Indicates a ignore-preferred-server node is configured.";
              description
                "Disable preferred server for this Server Group";
            }
          }
        }
      }
      container throttle {
        presence "Indicates a throttle node is configured.";
        description
          "Radius throttling options.";
        leaf access {
          type uint32 {
            range "0..65535" {
              description
                "Number of outstanding access requests after which throttling should be performed (Preferable value 100)";
            }
          }
          description
            "To flow control the number of access requests sent to a radius server";
        }
        leaf access-timeout {
          type uint32 {
            range "1..10" {
              description
                "Number of timeouts for a transaction (default is 3)";
            }
          }
          must "../access";
          description
            "Specify the number of timeouts exceeding which a throttled access request is dropped";
        }
        leaf accounting {
          type uint32 {
            range "0..65535" {
              description
                "Number of outstanding accounting transactions after which throttling should be performed (Preferable value 100)";
            }
          }
          description
            "To flow control the number of accounting requests sent to a radius server.";
        }
      }
      leaf deadtime {
        type uint32 {
          range "1..1440" {
            description
              "Deadtime limit in minutes (default 0)";
          }
        }
        description
          "Time in minutes for which a RADIUS server will be marked dead";
      }
      container dead-criteria {
        description
          "Dead server detection criteria for a configured RADIUS server";
        leaf time {
          type uint32 {
            range "1..120" {
              description
                "Time in seconds";
            }
          }
          description
            "Minimum time that must elapse since a response was received from this RADIUS server";
        }
        leaf tries {
          type uint32 {
            range "1..100" {
              description
                "Number of tries";
            }
          }
          description
            "The minimum number of transmissions (original attempts plus retransmits) to this RADIUS server";
        }
      }
      container source-port {
        description
          "Source-Port";
        container extended {
          presence "Indicates a extended node is configured.";
          description
            "Extended";
        }
      }
      container ipv4 {
        description
          "Mark the dscp bit for ipv4 packets";
        leaf dscp {
          type union {
            type uint32 {
              range "0..63" {
                description
                  "Differentiated services codepoint value";
              }
            }
            type enumeration {
              enum "default" {
                value 0;
                description
                  "Match packets with default dscp (000000)";
              }
              enum "cs1" {
                value 8;
                description
                  "Match packets with CS1(precedence 1) dscp (001000)";
              }
              enum "af11" {
                value 10;
                description
                  "Match packets with AF11 dscp (001010)";
              }
              enum "af12" {
                value 12;
                description
                  "Match packets with AF12 dscp (001100)";
              }
              enum "af13" {
                value 14;
                description
                  "Match packets with AF13 dscp (001110)";
              }
              enum "cs2" {
                value 16;
                description
                  "Match packets with CS2(precedence 2) dscp (010000)";
              }
              enum "af21" {
                value 18;
                description
                  "Match packets with AF21 dscp (010010)";
              }
              enum "af22" {
                value 20;
                description
                  "Match packets with AF22 dscp (010100)";
              }
              enum "af23" {
                value 22;
                description
                  "Match packets with AF23 dscp (010110)";
              }
              enum "cs3" {
                value 24;
                description
                  "Match packets with CS3(precedence 3) dscp (011000)";
              }
              enum "af31" {
                value 26;
                description
                  "Match packets with AF31 dscp (011010)";
              }
              enum "af32" {
                value 28;
                description
                  "Match packets with AF32 dscp (011100)";
              }
              enum "af33" {
                value 30;
                description
                  "Match packets with AF33 dscp (011110)";
              }
              enum "cs4" {
                value 32;
                description
                  "Match packets with CS4(precedence 4) dscp (100000)";
              }
              enum "af41" {
                value 34;
                description
                  "Match packets with AF41 dscp (100010)";
              }
              enum "af42" {
                value 36;
                description
                  "Match packets with AF42 dscp (100100)";
              }
              enum "af43" {
                value 38;
                description
                  "Match packets with AF43 dscp (100110)";
              }
              enum "cs5" {
                value 40;
                description
                  "Match packets with CS5(precedence 5) dscp (101000)";
              }
              enum "ef" {
                value 46;
                description
                  "Match packets with EF dscp (101110)";
              }
              enum "cs6" {
                value 48;
                description
                  "Match packets with CS6(precedence 6) dscp (110000)";
              }
              enum "cs7" {
                value 56;
                description
                  "Match packets with CS7(precedence 7) dscp (111000)";
              }
            }
          }
          description
            "Set IP DSCP (DiffServ CodePoint)";
        }
      }
      container ipv6 {
        description
          "Mark the dscp bit for ipv6 packets";
        leaf dscp {
          type union {
            type uint32 {
              range "0..63" {
                description
                  "Differentiated services codepoint value";
              }
            }
            type enumeration {
              enum "default" {
                value 0;
                description
                  "Match packets with default dscp (000000)";
              }
              enum "cs1" {
                value 8;
                description
                  "Match packets with CS1(precedence 1) dscp (001000)";
              }
              enum "af11" {
                value 10;
                description
                  "Match packets with AF11 dscp (001010)";
              }
              enum "af12" {
                value 12;
                description
                  "Match packets with AF12 dscp (001100)";
              }
              enum "af13" {
                value 14;
                description
                  "Match packets with AF13 dscp (001110)";
              }
              enum "cs2" {
                value 16;
                description
                  "Match packets with CS2(precedence 2) dscp (010000)";
              }
              enum "af21" {
                value 18;
                description
                  "Match packets with AF21 dscp (010010)";
              }
              enum "af22" {
                value 20;
                description
                  "Match packets with AF22 dscp (010100)";
              }
              enum "af23" {
                value 22;
                description
                  "Match packets with AF23 dscp (010110)";
              }
              enum "cs3" {
                value 24;
                description
                  "Match packets with CS3(precedence 3) dscp (011000)";
              }
              enum "af31" {
                value 26;
                description
                  "Match packets with AF31 dscp (011010)";
              }
              enum "af32" {
                value 28;
                description
                  "Match packets with AF32 dscp (011100)";
              }
              enum "af33" {
                value 30;
                description
                  "Match packets with AF33 dscp (011110)";
              }
              enum "cs4" {
                value 32;
                description
                  "Match packets with CS4(precedence 4) dscp (100000)";
              }
              enum "af41" {
                value 34;
                description
                  "Match packets with AF41 dscp (100010)";
              }
              enum "af42" {
                value 36;
                description
                  "Match packets with AF42 dscp (100100)";
              }
              enum "af43" {
                value 38;
                description
                  "Match packets with AF43 dscp (100110)";
              }
              enum "cs5" {
                value 40;
                description
                  "Match packets with CS5(precedence 5) dscp (101000)";
              }
              enum "ef" {
                value 46;
                description
                  "Match packets with EF dscp (101110)";
              }
              enum "cs6" {
                value 48;
                description
                  "Match packets with CS6(precedence 6) dscp (110000)";
              }
              enum "cs7" {
                value 56;
                description
                  "Match packets with CS7(precedence 7) dscp (111000)";
              }
            }
          }
          description
            "Set IP DSCP (DiffServ CodePoint)";
        }
      }
      container vsa {
        description
          "unknown vsa ignore configuration for RADIUS server";
        container attribute {
          description
            "Vendor Specific Attribute ";
          container ignore {
            description
              "ignore the VSA ";
            container unknown {
              presence "Indicates a unknown node is configured.";
              description
                "ignore the VSA and no prefix will reject the unkown VSA ";
            }
          }
        }
      }
      container disallow {
        description
          "disallow null-username";
        container null-username {
          presence "Indicates a null-username node is configured.";
          description
            "null-username";
        }
      }
      container attribute {
        description
          "Customize selected radius attributes";
        list list {
          key "list-name";
          description
            "List of Attribute Types";
          leaf list-name {
            type xr:Cisco-ios-xr-string {
              length "1..800" {
                description
                  "List name";
              }
            }
            description
              "List of Attribute Types";
          }
          container attribute {
            description
              "Specify a list of RADIUS attributes";
            leaf radius-attributes {
              type xr:Cisco-ios-xr-string {
                length "1..800" {
                  description
                    "Comma-delimited list of RADIUS attributes";
                }
              }
              description
                "Comma-delimited list of RADIUS attributes";
            }
            container vendor-ids {
              description
                "vendor-id";
              list vendor-id {
                key "id";
                description
                  "vendor-id";
                leaf id {
                  type uint32 {
                    range "0..4294967295" {
                      description
                        "vendor-id";
                    }
                  }
                  description
                    "vendor-id";
                }
                container vendor-types {
                  description
                    "Specify vendor-type";
                  list vendor-type {
                    key "vendor-type-id";
                    description
                      "Specify vendor-type";
                    leaf vendor-type-id {
                      type uint32 {
                        range "1..254" {
                          description
                            "vendor-type";
                        }
                      }
                      description
                        "Specify vendor-type";
                    }
                  }
                }
              }
            }
          }
        }
        container acct-session-id {
          description
            "Acct-Session-Id attribute(44)";
          container prepend-nas-port-id {
            presence "Indicates a prepend-nas-port-id node is configured.";
            description
              "Prepend Acct-Session-Id attribute with Nas-Port-Id";
          }
        }
        container acct-multi-session-id {
          description
            "Acct-Multi-Session-Id attribute(50)";
          container include-parent-session-id {
            presence "Indicates a include-parent-session-id node is configured.";
            description
              "Include Acct-Multi-Session-Id attribute with Acct-Parent-Session-Id";
          }
        }
        container filter-id-11 {
          description
            "Filter-Id attribute configuration";
          container default {
            description
              "Set the attribute defaults";
            leaf direction {
              type enumeration {
                enum "inbound" {
                  value 0;
                  description
                    "Filtering is applied to ingress(inbound) packets only";
                }
                enum "outbound" {
                  value 1;
                  description
                    "Filtering is applied to egress(outbound) packets only";
                }
              }
              description
                "Set the attribute default direction";
            }
          }
        }
      }
    }
    container radius {
      description
        "RADIUS configuration commands";
      container vrfs {
        description
          "VRF for this source interface configuration";
        list vrf {
          key "vrf-name";
          description
            "VRF for this source interface configuration";
          leaf vrf-name {
            type union {
              type string {
                pattern "default" {
                  description
                    "Default VRF";
                }
              }
              type xr:Cisco-ios-xr-string {
                length "1..1024" {
                  description
                    "Name of the VRF";
                }
              }
            }
            description
              "VRF for this source interface configuration";
          }
          leaf source-interface {
            type xr:Interface-name;
            mandatory true;
            description
              "Specify interface for source address in RADIUS packets";
          }
        }
      }
    }
  }
}
