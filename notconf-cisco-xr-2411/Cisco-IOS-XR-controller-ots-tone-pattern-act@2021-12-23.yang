module Cisco-IOS-XR-controller-ots-tone-pattern-act {
  namespace "http://cisco.com/ns/yang/Cisco-IOS-XR-controller-ots-tone-pattern-act";
  prefix controller-ots-tone-pattern-act;

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR tone pattern for controller-ots module.

     Copyright (c) 2018-2022 by Cisco Systems, Inc.
     All rights reserved.";

  revision 2021-12-23 {
    semver:module-version "1.0.0";
    description
      "Tone pattern action support for ots controllers";
  }
  revision 2021-02-04 {
    description
      "Added task-name to restrict user-access based on taskgroup";
  }

  rpc ots-controller-tonepattern {
    description
      "ots controller tone generation";

    input {
      leaf controller {
        type string;
        description
          "Controller name in R/S/I/P format";
      }
      leaf tonepatternstart {
        type empty;
        description
          "start tone pattern";
      }
      leaf tonepatternstop {
        type empty;
        description
          "stop tone pattern";
      }
      leaf tonepatternlaseron {
        type empty;
        description
          "laser on tone pattern";
      }
      leaf tonepatternlaseroff {
        type empty;
        description
          "laser off tone pattern";
      }
    }
  }
}
