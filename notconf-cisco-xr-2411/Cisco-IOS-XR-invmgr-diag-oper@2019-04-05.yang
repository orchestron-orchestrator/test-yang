module Cisco-IOS-XR-invmgr-diag-oper {
  namespace "http://cisco.com/ns/yang/Cisco-IOS-XR-invmgr-diag-oper";
  prefix invmgr-diag-oper;

  import Cisco-IOS-XR-types {
    prefix xr;
  }
  import cisco-semver {
    prefix semver;
  }

  include Cisco-IOS-XR-invmgr-diag-oper-sub1 {
    revision-date 2019-04-05;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR invmgr-diag package operational data.

     This module contains definitions
     for the following management objects:
       diag: Diag information

     Copyright (c) 2013-2019 by Cisco Systems, Inc.
     All rights reserved.";

  revision 2019-04-05 {
    semver:module-version "1.0.0";
    description
      "Establish semantic version baseline.";
  }
  revision 2015-11-09 {
    description
      "IOS XR 6.0 revision.";
  }

  grouping INSTANCE-TABLE {
    description
      "Common node of slot, fan-tray, power-shelf";
    container instances {
      description
        "Table of instances";
      list instance {
        key "name";
        description
          "instance number";
        leaf name {
          type xr:Cisco-ios-xr-string;
          description
            "Instance name";
        }
        uses DETAIL;
      }
    }
  }

  grouping DETAIL {
    description
      "Common node of instance, chassis";
    container detail {
      description
        "Detail information";
      uses INVMGR-DIAG-DETAIL-FORMAT;
    }
  }

  container diag {
    config false;
    description
      "Diag information";
    container racks {
      description
        "Table of racks";
      list rack {
        key "rack-name";
        description
          "Rack name";
        container power-shelfs {
          description
            "Table for rack power shelf ";
          list power-shelf {
            key "power-shelf-name";
            description
              "Power shelf name";
            leaf power-shelf-name {
              type xr:Cisco-ios-xr-string;
              description
                "Power Shelf name";
            }
            uses INSTANCE-TABLE;
          }
        }
        container fan-trays {
          description
            "Table for rack fan trays";
          list fan-tray {
            key "fan-tray-name";
            description
              "Fan tray name";
            leaf fan-tray-name {
              type xr:Cisco-ios-xr-string;
              description
                "Fan tray name";
            }
            uses INSTANCE-TABLE;
          }
        }
        container slots {
          description
            "Table of slots";
          list slot {
            key "slot-name";
            description
              "Slot name";
            leaf slot-name {
              type xr:Cisco-ios-xr-string;
              description
                "Slot name";
            }
            uses INSTANCE-TABLE;
          }
        }
        container chassis {
          description
            "Chassis information";
          uses DETAIL;
        }
        leaf rack-name {
          type xr:Cisco-ios-xr-string;
          description
            "Rack name";
        }
      }
    }
  }
}
