submodule Cisco-IOS-XR-fabric-fsdb-server-oper-sub1 {
  belongs-to Cisco-IOS-XR-fabric-fsdb-server-oper {
    prefix Cisco-IOS-XR-fabric-fsdb-server-oper;
  }

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR fabric-fsdb-server package operational data.

     Copyright (c) 2013-2020 by Cisco Systems, Inc.
     All rights reserved.";

  revision 2020-06-26 {
    semver:module-version "1.0.0";
    description
      "task-name field added.";
  }
  revision 2019-07-17 {
    description
      "Yang Schema fixed for fabric link port Information.";
  }
  revision 2019-04-05 {
    description
      "Establish semantic version baseline.";
  }
  revision 2015-11-09 {
    description
      "IOS XR 6.0 revision.";
  }

  grouping FSDB-SERVER-EDM-PLA-FAB {
    description
      "FSDB SERVER EDM PLA FAB";
    leaf rack-num-str {
      type string {
        length "0..128";
      }
      description
        "rack num str";
    }
    leaf stage-name {
      type string {
        length "0..128";
      }
      description
        "stage name";
    }
    leaf fabid-address {
      type string {
        length "0..128";
      }
      description
        "fabid address";
    }
    leaf fabid-status {
      type string;
      description
        "fabid status";
    }
    leaf num-planes {
      type int32;
      description
        "num planes";
    }
    leaf plane-0-mask {
      type string {
        length "0..128";
      }
      description
        "plane 0 mask";
    }
    leaf plane-1-mask {
      type string {
        length "0..128";
      }
      description
        "plane 1 mask";
    }
    leaf plane-2-mask {
      type string {
        length "0..128";
      }
      description
        "plane 2 mask";
    }
    leaf plane-3-mask {
      type string {
        length "0..128";
      }
      description
        "plane 3 mask";
    }
    leaf plane-4-mask {
      type string {
        length "0..128";
      }
      description
        "plane 4 mask";
    }
    leaf plane-5-mask {
      type string {
        length "0..128";
      }
      description
        "plane 5 mask";
    }
    leaf plane-6-mask {
      type string {
        length "0..128";
      }
      description
        "plane 6 mask";
    }
    leaf plane-7-mask {
      type string {
        length "0..128";
      }
      description
        "plane 7 mask";
    }
    leaf total-links {
      type int32;
      description
        "total links";
    }
    leaf total-up-links {
      type int32;
      description
        "total up links";
    }
    leaf min-links-per-asic {
      type int32;
      description
        "min links per asic";
    }
    leaf max-links-per-asic {
      type int32;
      description
        "max links per asic";
    }
    leaf min-up-links-per-asic {
      type int32;
      description
        "min up links per asic";
    }
    leaf max-up-links-per-asic {
      type int32;
      description
        "max up links per asic";
    }
  }

  grouping FSDB-LINK-HIST {
    description
      "FSDB LINK HIST";
    leaf timestamp-str {
      type string {
        length "0..128";
      }
      description
        "timestamp str";
    }
    leaf admin-state {
      type string;
      description
        "admin state";
    }
    leaf oper-state {
      type string;
      description
        "oper state";
    }
    leaf error-state {
      type string;
      description
        "error state";
    }
  }

  grouping FSDB-SERVER-EDM-LPORT {
    description
      "FSDB SERVER EDM LPORT";
    leaf link-str {
      type string {
        length "0..128";
      }
      description
        "link str";
    }
    leaf neib-link-str {
      type string {
        length "0..128";
      }
      description
        "neib link str";
    }
    leaf admin-state {
      type string;
      description
        "admin state";
    }
    leaf oper-state {
      type string;
      description
        "oper state";
    }
    leaf retimer-rx-str {
      type string {
        length "0..128";
      }
      description
        "retimer rx str";
    }
    leaf retimer-tx-str {
      type string {
        length "0..128";
      }
      description
        "retimer tx str";
    }
    leaf mux-rx-str {
      type string {
        length "0..128";
      }
      description
        "mux rx str";
    }
    leaf mux-tx-str {
      type string {
        length "0..128";
      }
      description
        "mux tx str";
    }
    list history {
      max-elements 5;
      description
        "history";
      uses FSDB-LINK-HIST;
    }
  }
}
