module Cisco-IOS-XR-pmengine-gl-cfg {
  namespace "http://cisco.com/ns/yang/Cisco-IOS-XR-pmengine-gl-cfg";
  prefix pmengine-gl-cfg;

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR pmengine-gl package configuration.

     This module contains definitions
     for the following management objects:
       performance-monitor: Configure flex-bin interval

     Copyright (c) 2013-2020 by Cisco Systems, Inc.
     All rights reserved.";

  revision 2020-08-20 {
    semver:module-version "1.0.0";
    description
      "Added new global config for flexbin interval.";
  }
  revision 2019-04-05 {
    description
      "Establish semantic version baseline.";
  }
  revision 2015-11-09 {
    description
      "IOS XR 6.0 revision.";
  }

  container performance-monitor {
    description
      "Configure flex-bin interval";
    container flex-bin {
      description
        "Configure flex-bin interval";
      leaf interval {
        type uint32 {
          range "1..10";
        }
        units "second";
        description
          "Configure the flex-bin interval in seconds <1
           ,10>";
      }
    }
  }
}
