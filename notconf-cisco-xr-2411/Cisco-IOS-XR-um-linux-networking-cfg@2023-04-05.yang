module Cisco-IOS-XR-um-linux-networking-cfg {
  namespace "http://cisco.com/ns/yang/Cisco-IOS-XR-um-linux-networking-cfg";
  prefix um-linux-networking-cfg;

  import Cisco-IOS-XR-types {
    prefix xr;
  }
  import ietf-inet-types {
    prefix inet;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR linux-networking package configuration.

     This YANG module augments the
     modules with configuration data.

     Copyright (c) 2020-2023 by Cisco Systems, Inc.
     All rights reserved.";

  revision 2023-04-05 {
    semver:module-version "1.1.0";
    description
      "New config option for Linux-owned VRF mapping
       2022-11-11
         New CLI options following migration of XLNC to eXR
       2022-07-06
         Updated stats sync options";
  }
  revision 2020-10-28 {
    semver:module-version "1.0.0";
    description
      "Initial release";
  }

  container linux {
    description
      "Configure Linux functionality";
    container networking {
      description
        "Configure Linux networking";
      container statistics-synchronization {
        description
          "Configure synchronization of interface statistics between IOS-XR and Linux";
        container from-xr {
          presence "Indicates a from-xr node is configured.";
          description
            "Set Linux interface statistics using values from IOS-XR";
          container every {
            description
              "Configure the how often the Linux interface statistics are updated with values from IOS-XR";
            container thirty-seconds {
              must
                "not(../sixty-seconds or ../twom
                 or ../threem or ../fourm
                 or ../fivem or ../sixm
                 or ../sevenm or ../eightm
                 or ../ninem or ../ten-m)";
              presence "Indicates a thirty-seconds node is configured.";
              description
                "Sync every thirty seconds";
            }
            container sixty-seconds {
              must
                "not(../thirty-seconds or ../twom
                 or ../threem or ../fourm
                 or ../fivem or ../sixm
                 or ../sevenm or ../eightm
                 or ../ninem or ../ten-m)";
              presence "Indicates a sixty-seconds node is configured.";
              description
                "Sync every sixty seconds";
            }
            container twom {
              must
                "not(../thirty-seconds or ../sixty-seconds
                 or ../threem or ../fourm
                 or ../fivem or ../sixm
                 or ../sevenm or ../eightm
                 or ../ninem or ../ten-m)";
              presence "Indicates a twom node is configured.";
              description
                "Sync every 2 minutes";
            }
            container threem {
              must
                "not(../thirty-seconds or ../sixty-seconds
                 or ../twom or ../fourm
                 or ../fivem or ../sixm
                 or ../sevenm or ../eightm
                 or ../ninem or ../ten-m)";
              presence "Indicates a threem node is configured.";
              description
                "Sync every 3 minutes";
            }
            container fourm {
              must
                "not(../thirty-seconds or ../sixty-seconds
                 or ../twom or ../threem
                 or ../fivem or ../sixm
                 or ../sevenm or ../eightm
                 or ../ninem or ../ten-m)";
              presence "Indicates a fourm node is configured.";
              description
                "Sync every 4 minutes";
            }
            container fivem {
              must
                "not(../thirty-seconds or ../sixty-seconds
                 or ../twom or ../threem
                 or ../fourm or ../sixm
                 or ../sevenm or ../eightm
                 or ../ninem or ../ten-m)";
              presence "Indicates a fivem node is configured.";
              description
                "Sync every 5 minutes";
            }
            container sixm {
              must
                "not(../thirty-seconds or ../sixty-seconds
                 or ../twom or ../threem
                 or ../fourm or ../fivem
                 or ../sevenm or ../eightm
                 or ../ninem or ../ten-m)";
              presence "Indicates a sixm node is configured.";
              description
                "Sync every 6 minutes";
            }
            container sevenm {
              must
                "not(../thirty-seconds or ../sixty-seconds
                 or ../twom or ../threem
                 or ../fourm or ../fivem
                 or ../sixm or ../eightm
                 or ../ninem or ../ten-m)";
              presence "Indicates a sevenm node is configured.";
              description
                "Sync every 7 minutes";
            }
            container eightm {
              must
                "not(../thirty-seconds or ../sixty-seconds
                 or ../twom or ../threem
                 or ../fourm or ../fivem
                 or ../sixm or ../sevenm
                 or ../ninem or ../ten-m)";
              presence "Indicates a eightm node is configured.";
              description
                "Sync every 8 minutes";
            }
            container ninem {
              must
                "not(../thirty-seconds or ../sixty-seconds
                 or ../twom or ../threem
                 or ../fourm or ../fivem
                 or ../sixm or ../sevenm
                 or ../eightm or ../ten-m)";
              presence "Indicates a ninem node is configured.";
              description
                "Sync every 9 minutes";
            }
            container ten-m {
              must
                "not(../thirty-seconds or ../sixty-seconds
                 or ../twom or ../threem
                 or ../fourm or ../fivem
                 or ../sixm or ../sevenm
                 or ../eightm or ../ninem)";
              presence "Indicates a ten-m node is configured.";
              description
                "Sync every 10 minutes";
            }
          }
        }
      }
      leaf linux-owned-vrf {
        type xr:Cisco-ios-xr-string {
          length "1..32" {
            description
              "VRF name";
          }
        }
        description
          "Configure a VRF as Linux-owned, to be mapped to the default Linux network namespace";
      }
      container exposed-interfaces {
        description
          "Configure an Exposed XR Interface (EXI)";
        container interfaces {
          description
            "Specify an IOS-XR interface to expose to Linux";
          list interface {
            key "interface-name";
            description
              "Specify an IOS-XR interface to expose to Linux";
            leaf interface-name {
              type xr:Interface-name;
              description
                "Specify an IOS-XR interface to expose to Linux";
            }
            leaf linux-managed {
              type enumeration {
                enum "enable" {
                  value 1;
                  description
                    "Enable properties of this interface are controlled by linux, not IOS-XR";
                }
                enum "disable" {
                  value 0;
                  description
                    "Disable properties of this interface are controlled by linux, not IOS-XR";
                }
              }
              mandatory true;
              description
                "Properties of this interface are controlled by linux, not IOS-XR";
            }
            container statistics-synchronization {
              description
                "Configure synchronization of interface statistics between IOS-XR and Linux";
              container from-xr {
                presence "Indicates a from-xr node is configured.";
                description
                  "Set Linux interface statistics using values from IOS-XR";
                container every {
                  description
                    "Configure the how often the Linux interface statistics are updated with values from IOS-XR";
                  container five-seconds {
                    must
                      "not(../ten-seconds or ../thirty-seconds
                       or ../sixty-seconds)";
                    presence "Indicates a five-seconds node is configured.";
                    description
                      "Sync every five seconds";
                  }
                  container ten-seconds {
                    must
                      "not(../five-seconds or ../thirty-seconds
                       or ../sixty-seconds)";
                    presence "Indicates a ten-seconds node is configured.";
                    description
                      "Sync every ten seconds";
                  }
                  container thirty-seconds {
                    must
                      "not(../five-seconds or ../ten-seconds
                       or ../sixty-seconds)";
                    presence "Indicates a thirty-seconds node is configured.";
                    description
                      "Sync every thirty seconds";
                  }
                  container sixty-seconds {
                    must
                      "not(../five-seconds or ../ten-seconds
                       or ../thirty-seconds)";
                    presence "Indicates a sixty-seconds node is configured.";
                    description
                      "Sync every sixty seconds";
                  }
                }
              }
            }
          }
        }
      }
      container vrfs {
        description
          "Configuration for a particular VRF";
        list vrf {
          key "vrf-name";
          description
            "Configuration for a particular VRF";
          leaf vrf-name {
            type xr:Cisco-ios-xr-string {
              length "1..32" {
                description
                  "VRF name";
              }
            }
            description
              "Configuration for a particular VRF";
          }
          container east-wests {
            description
              "Configure an East West Interface for a VRF.";
            list east-west {
              key "east-west-name";
              description
                "Configure an East West Interface for a VRF.";
              leaf east-west-name {
                type xr:Interface-name;
                description
                  "Configure an East West Interface for a VRF.";
              }
            }
          }
          container disable {
            presence "Indicates a disable node is configured.";
            description
              "Disable synchronization of this VRF with Linux. Linux applications will not be able to communicate over interfaces in the VRF";
          }
          container address-family {
            description
              "Configuration for a particular IP address family";
            container ipv4 {
              description
                "IPv4 address family";
              container source-hint {
                description
                  "Source hint config";
                container default-route {
                  description
                    "Default route source hint config";
                  leaf interface {
                    type xr:Interface-name;
                    description
                      "Interface name for source hint";
                  }
                  container active-management {
                    presence "Indicates a active-management node is configured.";
                    description
                      "Use active RP management interface for source hint";
                  }
                }
                container management-route {
                  description
                    "Management route source hint config";
                  leaf interface {
                    type xr:Interface-name;
                    description
                      "Interface name for source hint";
                  }
                }
              }
              container default-route {
                description
                  "Configure behavior of the Linux default route";
                container software-forwarding {
                  presence "Indicates a software-forwarding node is configured.";
                  description
                    "Use software forwarding instead of hardware forwarding. This may be required to send Linux traffic via the default route over management ports";
                }
              }
              container protection {
                description
                  "Configure Traffic Protection for Linux networking";
                container protocol {
                  description
                    "L4 protocol to specify Traffic Protection rules for";
                  list protocol {
                    key "protocol-name";
                    description
                      "L4 protocol to specify Traffic Protection rules for";
                    leaf protocol-name {
                      type enumeration {
                        enum "tcp" {
                          value 104;
                          description
                            "Transmission Control Protocol, RFC 793";
                        }
                        enum "udp" {
                          value 105;
                          description
                            "User Datagram Protocol, RFC 768";
                        }
                      }
                      description
                        "L4 protocol";
                    }
                    container local-port {
                      description
                        "L4 port number to specify Traffic Protection rules for";
                      container ports {
                        description
                          "selected port number (1-65535)";
                        list port {
                          key "port-number";
                          description
                            "selected port number (1-65535)";
                          leaf port-number {
                            type uint32 {
                              range "1..65535" {
                                description
                                  "selected port number (1-65535)";
                              }
                            }
                            description
                              "selected port number (1-65535)";
                          }
                          container default-action {
                            description
                              "Default action to take for packets matching this Traffic Protection service";
                            container permit {
                              must "not(../deny)";
                              presence "Indicates a permit node is configured.";
                              description
                                "Permit packets to reach Linux applications for this service";
                            }
                            container deny {
                              must "not(../permit)";
                              presence "Indicates a deny node is configured.";
                              description
                                "Drop packets for this service";
                            }
                          }
                          container remote-addresses {
                            description
                              "Remote address to filter against";
                            list remote-address {
                              must "permit or deny";
                              key "address length";
                              description
                                "Remote address to filter against";
                              leaf address {
                                type inet:ipv4-address-no-zone;
                                description
                                  "Remote address to filter against";
                              }
                              leaf length {
                                type uint32 {
                                  range "0..32";
                                }
                                description
                                  "Remote address to filter against";
                              }
                              container permit {
                                must "not(../deny) and ../../../default-action/deny";
                                presence "Indicates a permit node is configured.";
                                description
                                  "Add exception rule to permit packets to reach Linux applications (only valid when default-action is deny)";
                              }
                              container deny {
                                must "not(../permit) and ../../../default-action/permit";
                                presence "Indicates a deny node is configured.";
                                description
                                  "Add exception rule to drop packets (only valid when default-action is permit)";
                              }
                            }
                          }
                          container local-addresses {
                            description
                              "Local address to filter against";
                            list local-address {
                              must "permit or deny";
                              key "address length";
                              description
                                "Local address to filter against";
                              leaf address {
                                type inet:ipv4-address-no-zone;
                                description
                                  "Local address to filter against";
                              }
                              leaf length {
                                type uint32 {
                                  range "0..32";
                                }
                                description
                                  "Local address to filter against";
                              }
                              container permit {
                                must "not(../deny) and ../../../default-action/deny";
                                presence "Indicates a permit node is configured.";
                                description
                                  "Add exception rule to permit packets to reach Linux applications (only valid when default-action is deny)";
                              }
                              container deny {
                                must "not(../permit) and ../../../default-action/permit";
                                presence "Indicates a deny node is configured.";
                                description
                                  "Add exception rule to drop packets (only valid when default-action is permit)";
                              }
                            }
                          }
                          container interfaces {
                            description
                              "Select an ingress interface to restrict traffic to";
                            list interface {
                              must "permit or deny";
                              key "interface-name";
                              description
                                "Select an ingress interface to restrict traffic to";
                              leaf interface-name {
                                type xr:Interface-name;
                                description
                                  "Select an ingress interface to restrict traffic to";
                              }
                              container permit {
                                must "not(../deny) and ../../../default-action/deny";
                                presence "Indicates a permit node is configured.";
                                description
                                  "Add exception rule to permit packets to reach Linux applications (only valid when default-action is deny)";
                              }
                              container deny {
                                must "not(../permit) and ../../../default-action/permit";
                                presence "Indicates a deny node is configured.";
                                description
                                  "Add exception rule to drop packets (only valid when default-action is permit)";
                              }
                            }
                          }
                          container remote-address-local-addresses {
                            description
                              "Remote address to filter against";
                            list remote-address-local-address {
                              must "permit or deny";
                              key "remote-address remote-length local-address local-length";
                              description
                                "Remote address to filter against";
                              leaf remote-address {
                                type inet:ipv4-address-no-zone;
                                description
                                  "Remote address to filter against";
                              }
                              leaf remote-length {
                                type uint32 {
                                  range "0..32";
                                }
                                description
                                  "Remote address to filter against";
                              }
                              leaf local-address {
                                type inet:ipv4-address-no-zone;
                                description
                                  "Local address to filter against";
                              }
                              leaf local-length {
                                type uint32 {
                                  range "0..32";
                                }
                                description
                                  "Local address to filter against";
                              }
                              container permit {
                                must "not(../deny) and ../../../default-action/deny";
                                presence "Indicates a permit node is configured.";
                                description
                                  "Add exception rule to permit packets to reach Linux applications (only valid when default-action is deny)";
                              }
                              container deny {
                                must "not(../permit) and ../../../default-action/permit";
                                presence "Indicates a deny node is configured.";
                                description
                                  "Add exception rule to drop packets (only valid when default-action is permit)";
                              }
                            }
                          }
                          container remote-address-interfaces {
                            description
                              "Remote address to filter against";
                            list remote-address-interface {
                              must "permit or deny";
                              key "address length interface-name";
                              description
                                "Remote address to filter against";
                              leaf address {
                                type inet:ipv4-address-no-zone;
                                description
                                  "Remote address to filter against";
                              }
                              leaf length {
                                type uint32 {
                                  range "0..32";
                                }
                                description
                                  "Remote address to filter against";
                              }
                              leaf interface-name {
                                type xr:Interface-name;
                                description
                                  "Select an ingress interface to restrict traffic to";
                              }
                              container permit {
                                must "not(../deny) and ../../../default-action/deny";
                                presence "Indicates a permit node is configured.";
                                description
                                  "Add exception rule to permit packets to reach Linux applications (only valid when default-action is deny)";
                              }
                              container deny {
                                must "not(../permit) and ../../../default-action/permit";
                                presence "Indicates a deny node is configured.";
                                description
                                  "Add exception rule to drop packets (only valid when default-action is permit)";
                              }
                            }
                          }
                          container local-address-interfaces {
                            description
                              "Local address to filter against";
                            list local-address-interface {
                              must "permit or deny";
                              key "address length interface-name";
                              description
                                "Local address to filter against";
                              leaf address {
                                type inet:ipv4-address-no-zone;
                                description
                                  "Local address to filter against";
                              }
                              leaf length {
                                type uint32 {
                                  range "0..32";
                                }
                                description
                                  "Local address to filter against";
                              }
                              leaf interface-name {
                                type xr:Interface-name;
                                description
                                  "Select an ingress interface to restrict traffic to";
                              }
                              container permit {
                                must "not(../deny) and ../../../default-action/deny";
                                presence "Indicates a permit node is configured.";
                                description
                                  "Add exception rule to permit packets to reach Linux applications (only valid when default-action is deny)";
                              }
                              container deny {
                                must "not(../permit) and ../../../default-action/permit";
                                presence "Indicates a deny node is configured.";
                                description
                                  "Add exception rule to drop packets (only valid when default-action is permit)";
                              }
                            }
                          }
                          container remote-address-local-address-interfaces {
                            description
                              "Remote address to filter against";
                            list remote-address-local-address-interface {
                              must "permit or deny";
                              key "remote-address remote-length local-address local-length interface-name";
                              description
                                "Remote address to filter against";
                              leaf remote-address {
                                type inet:ipv4-address-no-zone;
                                description
                                  "Remote address to filter against";
                              }
                              leaf remote-length {
                                type uint32 {
                                  range "0..32";
                                }
                                description
                                  "Remote address to filter against";
                              }
                              leaf local-address {
                                type inet:ipv4-address-no-zone;
                                description
                                  "Local address to filter against";
                              }
                              leaf local-length {
                                type uint32 {
                                  range "0..32";
                                }
                                description
                                  "Local address to filter against";
                              }
                              leaf interface-name {
                                type xr:Interface-name;
                                description
                                  "Select an ingress interface to restrict traffic to";
                              }
                              container permit {
                                must "not(../deny) and ../../../default-action/deny";
                                presence "Indicates a permit node is configured.";
                                description
                                  "Add exception rule to permit packets to reach Linux applications (only valid when default-action is deny)";
                              }
                              container deny {
                                must "not(../permit) and ../../../default-action/permit";
                                presence "Indicates a deny node is configured.";
                                description
                                  "Add exception rule to drop packets (only valid when default-action is permit)";
                              }
                            }
                          }
                        }
                      }
                      container all {
                        description
                          "all ports";
                        container default-action {
                          description
                            "Default action to take for packets matching this Traffic Protection service";
                          container permit {
                            must "not(../deny)";
                            presence "Indicates a permit node is configured.";
                            description
                              "Permit packets to reach Linux applications for this service";
                          }
                          container deny {
                            must "not(../permit)";
                            presence "Indicates a deny node is configured.";
                            description
                              "Drop packets for this service";
                          }
                        }
                        container remote-addresses {
                          description
                            "Remote address to filter against";
                          list remote-address {
                            must "permit or deny";
                            key "address length";
                            description
                              "Remote address to filter against";
                            leaf address {
                              type inet:ipv4-address-no-zone;
                              description
                                "Remote address to filter against";
                            }
                            leaf length {
                              type uint32 {
                                range "0..32";
                              }
                              description
                                "Remote address to filter against";
                            }
                            container permit {
                              must "not(../deny) and ../../../default-action/deny";
                              presence "Indicates a permit node is configured.";
                              description
                                "Add exception rule to permit packets to reach Linux applications (only valid when default-action is deny)";
                            }
                            container deny {
                              must "not(../permit) and ../../../default-action/permit";
                              presence "Indicates a deny node is configured.";
                              description
                                "Add exception rule to drop packets (only valid when default-action is permit)";
                            }
                          }
                        }
                        container local-addresses {
                          description
                            "Local address to filter against";
                          list local-address {
                            must "permit or deny";
                            key "address length";
                            description
                              "Local address to filter against";
                            leaf address {
                              type inet:ipv4-address-no-zone;
                              description
                                "Local address to filter against";
                            }
                            leaf length {
                              type uint32 {
                                range "0..32";
                              }
                              description
                                "Local address to filter against";
                            }
                            container permit {
                              must "not(../deny) and ../../../default-action/deny";
                              presence "Indicates a permit node is configured.";
                              description
                                "Add exception rule to permit packets to reach Linux applications (only valid when default-action is deny)";
                            }
                            container deny {
                              must "not(../permit) and ../../../default-action/permit";
                              presence "Indicates a deny node is configured.";
                              description
                                "Add exception rule to drop packets (only valid when default-action is permit)";
                            }
                          }
                        }
                        container interfaces {
                          description
                            "Select an ingress interface to restrict traffic to";
                          list interface {
                            must "permit or deny";
                            key "interface-name";
                            description
                              "Select an ingress interface to restrict traffic to";
                            leaf interface-name {
                              type xr:Interface-name;
                              description
                                "Select an ingress interface to restrict traffic to";
                            }
                            container permit {
                              must "not(../deny) and ../../../default-action/deny";
                              presence "Indicates a permit node is configured.";
                              description
                                "Add exception rule to permit packets to reach Linux applications (only valid when default-action is deny)";
                            }
                            container deny {
                              must "not(../permit) and ../../../default-action/permit";
                              presence "Indicates a deny node is configured.";
                              description
                                "Add exception rule to drop packets (only valid when default-action is permit)";
                            }
                          }
                        }
                        container remote-address-local-addresses {
                          description
                            "Remote address to filter against";
                          list remote-address-local-address {
                            must "permit or deny";
                            key "remote-address remote-length local-address local-length";
                            description
                              "Remote address to filter against";
                            leaf remote-address {
                              type inet:ipv4-address-no-zone;
                              description
                                "Remote address to filter against";
                            }
                            leaf remote-length {
                              type uint32 {
                                range "0..32";
                              }
                              description
                                "Remote address to filter against";
                            }
                            leaf local-address {
                              type inet:ipv4-address-no-zone;
                              description
                                "Local address to filter against";
                            }
                            leaf local-length {
                              type uint32 {
                                range "0..32";
                              }
                              description
                                "Local address to filter against";
                            }
                            container permit {
                              must "not(../deny) and ../../../default-action/deny";
                              presence "Indicates a permit node is configured.";
                              description
                                "Add exception rule to permit packets to reach Linux applications (only valid when default-action is deny)";
                            }
                            container deny {
                              must "not(../permit) and ../../../default-action/permit";
                              presence "Indicates a deny node is configured.";
                              description
                                "Add exception rule to drop packets (only valid when default-action is permit)";
                            }
                          }
                        }
                        container remote-address-interfaces {
                          description
                            "Remote address to filter against";
                          list remote-address-interface {
                            must "permit or deny";
                            key "address length interface-name";
                            description
                              "Remote address to filter against";
                            leaf address {
                              type inet:ipv4-address-no-zone;
                              description
                                "Remote address to filter against";
                            }
                            leaf length {
                              type uint32 {
                                range "0..32";
                              }
                              description
                                "Remote address to filter against";
                            }
                            leaf interface-name {
                              type xr:Interface-name;
                              description
                                "Select an ingress interface to restrict traffic to";
                            }
                            container permit {
                              must "not(../deny) and ../../../default-action/deny";
                              presence "Indicates a permit node is configured.";
                              description
                                "Add exception rule to permit packets to reach Linux applications (only valid when default-action is deny)";
                            }
                            container deny {
                              must "not(../permit) and ../../../default-action/permit";
                              presence "Indicates a deny node is configured.";
                              description
                                "Add exception rule to drop packets (only valid when default-action is permit)";
                            }
                          }
                        }
                        container local-address-interfaces {
                          description
                            "Local address to filter against";
                          list local-address-interface {
                            must "permit or deny";
                            key "address length interface-name";
                            description
                              "Local address to filter against";
                            leaf address {
                              type inet:ipv4-address-no-zone;
                              description
                                "Local address to filter against";
                            }
                            leaf length {
                              type uint32 {
                                range "0..32";
                              }
                              description
                                "Local address to filter against";
                            }
                            leaf interface-name {
                              type xr:Interface-name;
                              description
                                "Select an ingress interface to restrict traffic to";
                            }
                            container permit {
                              must "not(../deny) and ../../../default-action/deny";
                              presence "Indicates a permit node is configured.";
                              description
                                "Add exception rule to permit packets to reach Linux applications (only valid when default-action is deny)";
                            }
                            container deny {
                              must "not(../permit) and ../../../default-action/permit";
                              presence "Indicates a deny node is configured.";
                              description
                                "Add exception rule to drop packets (only valid when default-action is permit)";
                            }
                          }
                        }
                        container remote-address-local-address-interfaces {
                          description
                            "Remote address to filter against";
                          list remote-address-local-address-interface {
                            must "permit or deny";
                            key "remote-address remote-length local-address local-length interface-name";
                            description
                              "Remote address to filter against";
                            leaf remote-address {
                              type inet:ipv4-address-no-zone;
                              description
                                "Remote address to filter against";
                            }
                            leaf remote-length {
                              type uint32 {
                                range "0..32";
                              }
                              description
                                "Remote address to filter against";
                            }
                            leaf local-address {
                              type inet:ipv4-address-no-zone;
                              description
                                "Local address to filter against";
                            }
                            leaf local-length {
                              type uint32 {
                                range "0..32";
                              }
                              description
                                "Local address to filter against";
                            }
                            leaf interface-name {
                              type xr:Interface-name;
                              description
                                "Select an ingress interface to restrict traffic to";
                            }
                            container permit {
                              must "not(../deny) and ../../../default-action/deny";
                              presence "Indicates a permit node is configured.";
                              description
                                "Add exception rule to permit packets to reach Linux applications (only valid when default-action is deny)";
                            }
                            container deny {
                              must "not(../permit) and ../../../default-action/permit";
                              presence "Indicates a deny node is configured.";
                              description
                                "Add exception rule to drop packets (only valid when default-action is permit)";
                            }
                          }
                        }
                      }
                    }
                  }
                }
              }
            }
            container ipv6 {
              description
                "IPv6 address family";
              container source-hint {
                description
                  "Source hint config";
                container default-route {
                  description
                    "Default route source hint config";
                  leaf interface {
                    type xr:Interface-name;
                    description
                      "Interface name for source hint";
                  }
                  container active-management {
                    presence "Indicates a active-management node is configured.";
                    description
                      "Use active RP management interface for source hint";
                  }
                }
                container management-route {
                  description
                    "Management route source hint config";
                  leaf interface {
                    type xr:Interface-name;
                    description
                      "Interface name for source hint";
                  }
                }
              }
              container default-route {
                description
                  "Configure behavior of the Linux default route";
                container software-forwarding {
                  presence "Indicates a software-forwarding node is configured.";
                  description
                    "Use software forwarding instead of hardware forwarding. This may be required to send Linux traffic via the default route over management ports";
                }
              }
              container protection {
                description
                  "Configure Traffic Protection for Linux networking";
                container protocol {
                  description
                    "L4 protocol to specify Traffic Protection rules for";
                  list protocol {
                    key "protocol-name";
                    description
                      "L4 protocol to specify Traffic Protection rules for";
                    leaf protocol-name {
                      type enumeration {
                        enum "tcp" {
                          value 104;
                          description
                            "Transmission Control Protocol, RFC 793";
                        }
                        enum "udp" {
                          value 105;
                          description
                            "User Datagram Protocol, RFC 768";
                        }
                      }
                      description
                        "L4 protocol";
                    }
                    container local-port {
                      description
                        "L4 port number to specify Traffic Protection rules for";
                      container ports {
                        description
                          "selected port number (1-65535)";
                        list port {
                          key "port-number";
                          description
                            "selected port number (1-65535)";
                          leaf port-number {
                            type uint32 {
                              range "1..65535" {
                                description
                                  "selected port number (1-65535)";
                              }
                            }
                            description
                              "selected port number (1-65535)";
                          }
                          container default-action {
                            description
                              "Default action to take for packets matching this Traffic Protection service";
                            container permit {
                              must "not(../deny)";
                              presence "Indicates a permit node is configured.";
                              description
                                "Permit packets to reach Linux applications for this service";
                            }
                            container deny {
                              must "not(../permit)";
                              presence "Indicates a deny node is configured.";
                              description
                                "Drop packets for this service";
                            }
                          }
                          container remote-addresses {
                            description
                              "Remote address to filter against";
                            list remote-address {
                              must "permit or deny";
                              key "address length";
                              description
                                "Remote address to filter against";
                              leaf address {
                                type inet:ipv6-address-no-zone;
                                description
                                  "Remote address to filter against";
                              }
                              leaf length {
                                type uint32 {
                                  range "0..128";
                                }
                                description
                                  "Remote address to filter against";
                              }
                              container permit {
                                must "not(../deny) and ../../../default-action/deny";
                                presence "Indicates a permit node is configured.";
                                description
                                  "Add exception rule to permit packets to reach Linux applications (only valid when default-action is deny)";
                              }
                              container deny {
                                must "not(../permit) and ../../../default-action/permit";
                                presence "Indicates a deny node is configured.";
                                description
                                  "Add exception rule to drop packets (only valid when default-action is permit)";
                              }
                            }
                          }
                          container local-addresses {
                            description
                              "Local address to filter against";
                            list local-address {
                              must "permit or deny";
                              key "address length";
                              description
                                "Local address to filter against";
                              leaf address {
                                type inet:ipv6-address-no-zone;
                                description
                                  "Local address to filter against";
                              }
                              leaf length {
                                type uint32 {
                                  range "0..128";
                                }
                                description
                                  "Local address to filter against";
                              }
                              container permit {
                                must "not(../deny) and ../../../default-action/deny";
                                presence "Indicates a permit node is configured.";
                                description
                                  "Add exception rule to permit packets to reach Linux applications (only valid when default-action is deny)";
                              }
                              container deny {
                                must "not(../permit) and ../../../default-action/permit";
                                presence "Indicates a deny node is configured.";
                                description
                                  "Add exception rule to drop packets (only valid when default-action is permit)";
                              }
                            }
                          }
                          container interfaces {
                            description
                              "Select an ingress interface to restrict traffic to";
                            list interface {
                              must "permit or deny";
                              key "interface-name";
                              description
                                "Select an ingress interface to restrict traffic to";
                              leaf interface-name {
                                type xr:Interface-name;
                                description
                                  "Select an ingress interface to restrict traffic to";
                              }
                              container permit {
                                must "not(../deny) and ../../../default-action/deny";
                                presence "Indicates a permit node is configured.";
                                description
                                  "Add exception rule to permit packets to reach Linux applications (only valid when default-action is deny)";
                              }
                              container deny {
                                must "not(../permit) and ../../../default-action/permit";
                                presence "Indicates a deny node is configured.";
                                description
                                  "Add exception rule to drop packets (only valid when default-action is permit)";
                              }
                            }
                          }
                          container remote-address-local-addresses {
                            description
                              "Remote address to filter against";
                            list remote-address-local-address {
                              must "permit or deny";
                              key "remote-address remote-length local-address local-length";
                              description
                                "Remote address to filter against";
                              leaf remote-address {
                                type inet:ipv6-address-no-zone;
                                description
                                  "Remote address to filter against";
                              }
                              leaf remote-length {
                                type uint32 {
                                  range "0..128";
                                }
                                description
                                  "Remote address to filter against";
                              }
                              leaf local-address {
                                type inet:ipv6-address-no-zone;
                                description
                                  "Local address to filter against";
                              }
                              leaf local-length {
                                type uint32 {
                                  range "0..128";
                                }
                                description
                                  "Local address to filter against";
                              }
                              container permit {
                                must "not(../deny) and ../../../default-action/deny";
                                presence "Indicates a permit node is configured.";
                                description
                                  "Add exception rule to permit packets to reach Linux applications (only valid when default-action is deny)";
                              }
                              container deny {
                                must "not(../permit) and ../../../default-action/permit";
                                presence "Indicates a deny node is configured.";
                                description
                                  "Add exception rule to drop packets (only valid when default-action is permit)";
                              }
                            }
                          }
                          container remote-address-interfaces {
                            description
                              "Remote address to filter against";
                            list remote-address-interface {
                              must "permit or deny";
                              key "address length interface-name";
                              description
                                "Remote address to filter against";
                              leaf address {
                                type inet:ipv6-address-no-zone;
                                description
                                  "Remote address to filter against";
                              }
                              leaf length {
                                type uint32 {
                                  range "0..128";
                                }
                                description
                                  "Remote address to filter against";
                              }
                              leaf interface-name {
                                type xr:Interface-name;
                                description
                                  "Select an ingress interface to restrict traffic to";
                              }
                              container permit {
                                must "not(../deny) and ../../../default-action/deny";
                                presence "Indicates a permit node is configured.";
                                description
                                  "Add exception rule to permit packets to reach Linux applications (only valid when default-action is deny)";
                              }
                              container deny {
                                must "not(../permit) and ../../../default-action/permit";
                                presence "Indicates a deny node is configured.";
                                description
                                  "Add exception rule to drop packets (only valid when default-action is permit)";
                              }
                            }
                          }
                          container local-address-interfaces {
                            description
                              "Local address to filter against";
                            list local-address-interface {
                              must "permit or deny";
                              key "address length interface-name";
                              description
                                "Local address to filter against";
                              leaf address {
                                type inet:ipv6-address-no-zone;
                                description
                                  "Local address to filter against";
                              }
                              leaf length {
                                type uint32 {
                                  range "0..128";
                                }
                                description
                                  "Local address to filter against";
                              }
                              leaf interface-name {
                                type xr:Interface-name;
                                description
                                  "Select an ingress interface to restrict traffic to";
                              }
                              container permit {
                                must "not(../deny) and ../../../default-action/deny";
                                presence "Indicates a permit node is configured.";
                                description
                                  "Add exception rule to permit packets to reach Linux applications (only valid when default-action is deny)";
                              }
                              container deny {
                                must "not(../permit) and ../../../default-action/permit";
                                presence "Indicates a deny node is configured.";
                                description
                                  "Add exception rule to drop packets (only valid when default-action is permit)";
                              }
                            }
                          }
                          container remote-address-local-address-interfaces {
                            description
                              "Remote address to filter against";
                            list remote-address-local-address-interface {
                              must "permit or deny";
                              key "remote-address remote-length local-address local-length interface-name";
                              description
                                "Remote address to filter against";
                              leaf remote-address {
                                type inet:ipv6-address-no-zone;
                                description
                                  "Remote address to filter against";
                              }
                              leaf remote-length {
                                type uint32 {
                                  range "0..128";
                                }
                                description
                                  "Remote address to filter against";
                              }
                              leaf local-address {
                                type inet:ipv6-address-no-zone;
                                description
                                  "Local address to filter against";
                              }
                              leaf local-length {
                                type uint32 {
                                  range "0..128";
                                }
                                description
                                  "Local address to filter against";
                              }
                              leaf interface-name {
                                type xr:Interface-name;
                                description
                                  "Select an ingress interface to restrict traffic to";
                              }
                              container permit {
                                must "not(../deny) and ../../../default-action/deny";
                                presence "Indicates a permit node is configured.";
                                description
                                  "Add exception rule to permit packets to reach Linux applications (only valid when default-action is deny)";
                              }
                              container deny {
                                must "not(../permit) and ../../../default-action/permit";
                                presence "Indicates a deny node is configured.";
                                description
                                  "Add exception rule to drop packets (only valid when default-action is permit)";
                              }
                            }
                          }
                        }
                      }
                      container all {
                        description
                          "all ports";
                        container default-action {
                          description
                            "Default action to take for packets matching this Traffic Protection service";
                          container permit {
                            must "not(../deny)";
                            presence "Indicates a permit node is configured.";
                            description
                              "Permit packets to reach Linux applications for this service";
                          }
                          container deny {
                            must "not(../permit)";
                            presence "Indicates a deny node is configured.";
                            description
                              "Drop packets for this service";
                          }
                        }
                        container remote-addresses {
                          description
                            "Remote address to filter against";
                          list remote-address {
                            must "permit or deny";
                            key "address length";
                            description
                              "Remote address to filter against";
                            leaf address {
                              type inet:ipv6-address-no-zone;
                              description
                                "Remote address to filter against";
                            }
                            leaf length {
                              type uint32 {
                                range "0..128";
                              }
                              description
                                "Remote address to filter against";
                            }
                            container permit {
                              must "not(../deny) and ../../../default-action/deny";
                              presence "Indicates a permit node is configured.";
                              description
                                "Add exception rule to permit packets to reach Linux applications (only valid when default-action is deny)";
                            }
                            container deny {
                              must "not(../permit) and ../../../default-action/permit";
                              presence "Indicates a deny node is configured.";
                              description
                                "Add exception rule to drop packets (only valid when default-action is permit)";
                            }
                          }
                        }
                        container local-addresses {
                          description
                            "Local address to filter against";
                          list local-address {
                            must "permit or deny";
                            key "address length";
                            description
                              "Local address to filter against";
                            leaf address {
                              type inet:ipv6-address-no-zone;
                              description
                                "Local address to filter against";
                            }
                            leaf length {
                              type uint32 {
                                range "0..128";
                              }
                              description
                                "Local address to filter against";
                            }
                            container permit {
                              must "not(../deny) and ../../../default-action/deny";
                              presence "Indicates a permit node is configured.";
                              description
                                "Add exception rule to permit packets to reach Linux applications (only valid when default-action is deny)";
                            }
                            container deny {
                              must "not(../permit) and ../../../default-action/permit";
                              presence "Indicates a deny node is configured.";
                              description
                                "Add exception rule to drop packets (only valid when default-action is permit)";
                            }
                          }
                        }
                        container interfaces {
                          description
                            "Select an ingress interface to restrict traffic to";
                          list interface {
                            must "permit or deny";
                            key "interface-name";
                            description
                              "Select an ingress interface to restrict traffic to";
                            leaf interface-name {
                              type xr:Interface-name;
                              description
                                "Select an ingress interface to restrict traffic to";
                            }
                            container permit {
                              must "not(../deny) and ../../../default-action/deny";
                              presence "Indicates a permit node is configured.";
                              description
                                "Add exception rule to permit packets to reach Linux applications (only valid when default-action is deny)";
                            }
                            container deny {
                              must "not(../permit) and ../../../default-action/permit";
                              presence "Indicates a deny node is configured.";
                              description
                                "Add exception rule to drop packets (only valid when default-action is permit)";
                            }
                          }
                        }
                        container remote-address-local-addresses {
                          description
                            "Remote address to filter against";
                          list remote-address-local-address {
                            must "permit or deny";
                            key "remote-address remote-length local-address local-length";
                            description
                              "Remote address to filter against";
                            leaf remote-address {
                              type inet:ipv6-address-no-zone;
                              description
                                "Remote address to filter against";
                            }
                            leaf remote-length {
                              type uint32 {
                                range "0..128";
                              }
                              description
                                "Remote address to filter against";
                            }
                            leaf local-address {
                              type inet:ipv6-address-no-zone;
                              description
                                "Local address to filter against";
                            }
                            leaf local-length {
                              type uint32 {
                                range "0..128";
                              }
                              description
                                "Local address to filter against";
                            }
                            container permit {
                              must "not(../deny) and ../../../default-action/deny";
                              presence "Indicates a permit node is configured.";
                              description
                                "Add exception rule to permit packets to reach Linux applications (only valid when default-action is deny)";
                            }
                            container deny {
                              must "not(../permit) and ../../../default-action/permit";
                              presence "Indicates a deny node is configured.";
                              description
                                "Add exception rule to drop packets (only valid when default-action is permit)";
                            }
                          }
                        }
                        container remote-address-interfaces {
                          description
                            "Remote address to filter against";
                          list remote-address-interface {
                            must "permit or deny";
                            key "address length interface-name";
                            description
                              "Remote address to filter against";
                            leaf address {
                              type inet:ipv6-address-no-zone;
                              description
                                "Remote address to filter against";
                            }
                            leaf length {
                              type uint32 {
                                range "0..128";
                              }
                              description
                                "Remote address to filter against";
                            }
                            leaf interface-name {
                              type xr:Interface-name;
                              description
                                "Select an ingress interface to restrict traffic to";
                            }
                            container permit {
                              must "not(../deny) and ../../../default-action/deny";
                              presence "Indicates a permit node is configured.";
                              description
                                "Add exception rule to permit packets to reach Linux applications (only valid when default-action is deny)";
                            }
                            container deny {
                              must "not(../permit) and ../../../default-action/permit";
                              presence "Indicates a deny node is configured.";
                              description
                                "Add exception rule to drop packets (only valid when default-action is permit)";
                            }
                          }
                        }
                        container local-address-interfaces {
                          description
                            "Local address to filter against";
                          list local-address-interface {
                            must "permit or deny";
                            key "address length interface-name";
                            description
                              "Local address to filter against";
                            leaf address {
                              type inet:ipv6-address-no-zone;
                              description
                                "Local address to filter against";
                            }
                            leaf length {
                              type uint32 {
                                range "0..128";
                              }
                              description
                                "Local address to filter against";
                            }
                            leaf interface-name {
                              type xr:Interface-name;
                              description
                                "Select an ingress interface to restrict traffic to";
                            }
                            container permit {
                              must "not(../deny) and ../../../default-action/deny";
                              presence "Indicates a permit node is configured.";
                              description
                                "Add exception rule to permit packets to reach Linux applications (only valid when default-action is deny)";
                            }
                            container deny {
                              must "not(../permit) and ../../../default-action/permit";
                              presence "Indicates a deny node is configured.";
                              description
                                "Add exception rule to drop packets (only valid when default-action is permit)";
                            }
                          }
                        }
                        container remote-address-local-address-interfaces {
                          description
                            "Remote address to filter against";
                          list remote-address-local-address-interface {
                            must "permit or deny";
                            key "remote-address remote-length local-address local-length interface-name";
                            description
                              "Remote address to filter against";
                            leaf remote-address {
                              type inet:ipv6-address-no-zone;
                              description
                                "Remote address to filter against";
                            }
                            leaf remote-length {
                              type uint32 {
                                range "0..128";
                              }
                              description
                                "Remote address to filter against";
                            }
                            leaf local-address {
                              type inet:ipv6-address-no-zone;
                              description
                                "Local address to filter against";
                            }
                            leaf local-length {
                              type uint32 {
                                range "0..128";
                              }
                              description
                                "Local address to filter against";
                            }
                            leaf interface-name {
                              type xr:Interface-name;
                              description
                                "Select an ingress interface to restrict traffic to";
                            }
                            container permit {
                              must "not(../deny) and ../../../default-action/deny";
                              presence "Indicates a permit node is configured.";
                              description
                                "Add exception rule to permit packets to reach Linux applications (only valid when default-action is deny)";
                            }
                            container deny {
                              must "not(../permit) and ../../../default-action/permit";
                              presence "Indicates a deny node is configured.";
                              description
                                "Add exception rule to drop packets (only valid when default-action is permit)";
                            }
                          }
                        }
                      }
                    }
                  }
                }
              }
            }
          }
        }
      }
    }
  }
}
