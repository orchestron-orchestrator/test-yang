module Cisco-IOS-XR-spio-oper {
  namespace "http://cisco.com/ns/yang/Cisco-IOS-XR-spio-oper";
  prefix spio-oper;

  import Cisco-IOS-XR-types {
    prefix xr;
  }
  import cisco-semver {
    prefix semver;
  }

  include Cisco-IOS-XR-spio-oper-sub1 {
    revision-date 2022-08-25;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR spio package operational data.

     This module contains definitions
     for the following management objects:
       spio: SPIO operational data

     Copyright (c) 2013-2022 by Cisco Systems, Inc.
     All rights reserved.";

  revision 2022-08-25 {
    semver:module-version "1.0.0";
    description
      "Introduced yang support for spio";
  }
  revision 2019-04-05 {
    description
      "Establish semantic version baseline.";
  }
  revision 2015-11-09 {
    description
      "IOS XR 6.0 revision.";
  }

  typedef Spio-protocol-id {
    type enumeration {
      enum "cfm" {
        value 1;
        description
          "CFM";
      }
      enum "stp" {
        value 2;
        description
          "STP";
      }
      enum "stp-(provider-bridge)" {
        value 3;
        description
          "STP (Provider Bridge)";
      }
      enum "arp" {
        value 28;
        description
          "ARP";
      }
      enum "udld" {
        value 36;
        description
          "UDLD";
      }
    }
    description
      "Spio protocol id";
  }

  container spio {
    config false;
    description
      "SPIO operational data";
    container nodes {
      description
        "Per node SPIO operational data";
      list node {
        key "node-name";
        description
          "SPIO operational data for particular node. The
           data for the node relates to clients using
           interfaces whose control plane resides on the
           node.";
        container interfaces {
          description
            "SPIO attached interface operational data for
             the client";
          list interface {
            description
              "SPIO operational data for a particular
               interface";
            leaf protocol-id {
              type Spio-protocol-id;
              description
                "The protocol ID for the client";
            }
            leaf node-name {
              type xr:Node-id;
              description
                "The node that the client is running on";
            }
            leaf interface-name {
              type xr:Interface-name;
              description
                "The interface name";
            }
            uses SPIO-INTERFACE-INFO;
          }
        }
        container clients {
          description
            "Per client SPIO operational data";
          list client {
            description
              "SPIO operational data for a particular client";
            leaf protocol-id {
              type Spio-protocol-id;
              description
                "The protocol ID for the client";
            }
            leaf node-name {
              type xr:Node-id;
              description
                "The node that the client is running on";
            }
            uses SPIO-CLIENT-INFO;
          }
        }
        container offload-interfaces {
          description
            "SPIO interfaces with offload sessions for the
             client";
          list offload-interface {
            description
              "SPIO offload operational data for a
               particular interface";
            container sessions {
              description
                "SPIO offload sessions operational data for
                 an interface";
              list session {
                key "key";
                description
                  "SPIO operational data for a particular
                   session";
                leaf key {
                  type xr:Cisco-ios-xr-string;
                  description
                    "The key for the session, in hex format";
                }
                uses SPIO-SESSION-INFO;
              }
            }
            leaf protocol-id {
              type Spio-protocol-id;
              description
                "The protocol ID for the client";
            }
            leaf node-name {
              type xr:Node-id;
              description
                "The node that the client is running on";
            }
            leaf interface-name {
              type xr:Interface-name;
              description
                "The interface name";
            }
          }
        }
        container vis {
          description
            "SPIO virtual interface operational data";
          list vi {
            key "interface-name";
            description
              "SPIO virtual interface operational data for
               an interface";
            leaf interface-name {
              type xr:Interface-name;
              description
                "The interface name";
            }
            uses SPIO-VI-INFO;
          }
        }
        leaf node-name {
          type xr:Node-id;
          description
            "The identifier for the node";
        }
      }
    }
  }
}
