submodule Cisco-IOS-XR-ofa-npu-qos-oper-sub1 {
  belongs-to Cisco-IOS-XR-ofa-npu-qos-oper {
    prefix Cisco-IOS-XR-ofa-npu-qos-oper;
  }

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR ofa-npu-qos package operational data.

     Copyright (c) 2013-2022 by Cisco Systems, Inc.
     All rights reserved.";

  revision 2022-10-10 {
    semver:module-version "1.0.0";
    description
      "Create the initial npu-qos oper yang model.";
  }
  revision 2019-04-05 {
    description
      "Establish semantic version baseline.";
  }
  revision 2015-11-09 {
    description
      "IOS XR 6.0 revision.";
  }

  typedef Ofa-npu-qos-show-hp-level {
    type enumeration {
      enum "priority-level1" {
        description
          "Priority queue level 1";
      }
      enum "priority-level2" {
        description
          "Priority queue level 2";
      }
      enum "priority-level3" {
        description
          "Priority queue level 3";
      }
      enum "priority-level4" {
        description
          "Priority queue level 4";
      }
      enum "priority-level5" {
        description
          "Priority queue level 5";
      }
      enum "priority-level6" {
        description
          "Priority queue level 6";
      }
      enum "priority-level7" {
        description
          "Priority queue level 7";
      }
      enum "priority-level8" {
        description
          "Priority queue level 8";
      }
      enum "unknown" {
        description
          "Unknown";
      }
    }
    description
      "Priority level";
  }

  grouping OFA-NPU-QOS-Q-INFO-ST {
    description
      "OFA NPU QOS Q INFO ST";
    leaf priority-level {
      type Ofa-npu-qos-show-hp-level;
      description
        "Priority level";
    }
    leaf config-max-rate {
      type uint32;
      units "kbit/s";
      description
        "Configured maximum rate kbps";
    }
  }

  grouping OFA-NPU-QOS-SHOW-ST {
    description
      "OFA NPU QOS SHOW ST";
    leaf npu-id {
      type uint32;
      description
        "NPU ID";
    }
    leaf voq-base-address {
      type uint32;
      description
        "VOQ base address";
    }
    list q-config {
      key "priority-level";
      max-elements 8;
      description
        "Port configuration";
      uses OFA-NPU-QOS-Q-INFO-ST;
    }
  }
}
