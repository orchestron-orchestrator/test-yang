module Cisco-IOS-XR-um-if-packets-cfg {
  namespace "http://cisco.com/ns/yang/Cisco-IOS-XR-um-if-packets-cfg";
  prefix um-if-packets-cfg;

  import Cisco-IOS-XR-um-interface-cfg {
    prefix a1;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR if-packets package configuration.

     This YANG module augments the
     modules with configuration data.

     Copyright (c) 2020-2022 by Cisco Systems, Inc.
     All rights reserved.";

  revision 2022-07-11 {
    semver:module-version "1.1.0";
    description
      "Added missing description statement to nodes";
  }
  revision 2021-06-02 {
    semver:module-version "1.0.0";
    description
      "Initial release";
  }

  grouping IF-BODY {
    description
      "Grouping for interface";
    container capture {
      description
        "capture interface packets (platform)";
      container software {
        description
          "capture software switched packets";
        container packets {
          presence "Indicates a packets node is configured.";
          description
            "turns on both ingress and egress (platform)";
        }
      }
    }
  }

  augment "/a1:interfaces/a1:interface" {
    description
      "This augment extends active nodes configuration";
    uses IF-BODY;
  }
  augment "/a1:interfaces/a1:interface-preconfigure" {
    description
      "This augment extends preconfigured nodes
       configuration";
    uses IF-BODY;
  }
}
