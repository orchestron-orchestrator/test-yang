module Cisco-IOS-XR-um-power-mgmt-cfg {
  namespace "http://cisco.com/ns/yang/Cisco-IOS-XR-um-power-mgmt-cfg";
  prefix um-power-mgmt-cfg;

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR power-mgmt package configuration.

     This YANG module augments the
     modules with configuration data.

     Copyright (c) 2022 by Cisco Systems, Inc.
     All rights reserved.";

  revision 2022-02-17 {
    semver:module-version "1.1.0";
    description
      "Added new container action under container power-mgmt";
  }
  revision 2020-12-04 {
    semver:module-version "1.0.0";
    description
      "Initial release";
  }

  container power-mgmt {
    description
      "global power management commands";
    container extended-temp {
      description
        "action for setting power budget for extended temp mode";
      container enable {
        presence "Indicates a enable node is configured.";
        description
          "enable extended temp mode";
      }
    }
    container action {
      description
        "action for controlling power budget to not exceed power capacity";
      container disable {
        presence "Indicates a disable node is configured.";
        description
          "disable power budgeting";
      }
    }
    container single-feed-mode {
      description
        "action for suppressing alarms for missing feed (only for dual feed) supplies";
      container enable {
        presence "Indicates a enable node is configured.";
        description
          "enable single feed";
      }
    }
    leaf redundancy-num-pms {
      type uint32 {
        range "0..23" {
          description
            "Number of redundant PEMS";
        }
      }
      description
        "disable power tray level redundancy and convert to power module redundancy";
    }
  }
}
