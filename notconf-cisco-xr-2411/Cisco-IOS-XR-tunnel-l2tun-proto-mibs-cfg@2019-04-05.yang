module Cisco-IOS-XR-tunnel-l2tun-proto-mibs-cfg {
  namespace "http://cisco.com/ns/yang/Cisco-IOS-XR-tunnel-l2tun-proto-mibs-cfg";
  prefix tunnel-l2tun-proto-mibs-cfg;

  import cisco-semver {
    prefix semver;
  }
  import Cisco-IOS-XR-snmp-agent-cfg {
    prefix a1;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR tunnel-l2tun-proto-mibs package configuration.

     This YANG module augments the
       Cisco-IOS-XR-snmp-agent-cfg
     module with configuration data.

     Copyright (c) 2013-2019 by Cisco Systems, Inc.
     All rights reserved.";

  revision 2019-04-05 {
    semver:module-version "1.0.1";
    description
      "Establish semantic version baseline.";
  }
  revision 2015-11-09 {
    description
      "IOS XR 6.0 revision.";
  }

  augment "/a1:snmp/a1:notification" {
    description
      "This augment extends the configuration data of
       'Cisco-IOS-XR-snmp-agent-cfg'";
    container l2tun {
      description
        "Enable SNMP l2tun traps";
      leaf tunnel-up {
        type boolean;
        description
          "Enable L2TUN tunnel UP traps";
      }
      leaf tunnel-down {
        type boolean;
        description
          "Enable L2TUN tunnel DOWN traps";
      }
      leaf pseudowire-status {
        type boolean;
        description
          "Enable traps for L2TPv3 PW status";
      }
      leaf sessions {
        type boolean;
        description
          "Enable L2TUN sessions traps";
      }
    }
  }
}
