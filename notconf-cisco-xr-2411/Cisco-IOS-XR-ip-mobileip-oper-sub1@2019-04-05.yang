submodule Cisco-IOS-XR-ip-mobileip-oper-sub1 {
  belongs-to Cisco-IOS-XR-ip-mobileip-oper {
    prefix Cisco-IOS-XR-ip-mobileip-oper;
  }

  import ietf-inet-types {
    prefix inet;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR ip-mobileip package operational data.

     Copyright (c) 2013-2019 by Cisco Systems, Inc.
     All rights reserved.";

  revision 2019-04-05 {
    semver:module-version "1.0.1";
    description
      "Establish semantic version baseline.";
  }
  revision 2016-03-10 {
    description
      "Initial version";
  }
  revision 2015-11-09 {
    description
      "IOS XR 6.0 revision.";
  }

  typedef Pmipv6-encap {
    type enumeration {
      enum "none" {
        description
          "None";
      }
      enum "ipv6" {
        description
          "IPV6 Tunnel";
      }
      enum "ipv6-ipv4" {
        description
          "IPV6 in IPV4 Tunnel";
      }
      enum "ipv6-udp" {
        description
          "IPV6 in IPV4 UDP Tunnel";
      }
      enum "gre-ipv4" {
        description
          "GRE IPV4 Tunnel";
      }
      enum "gre-ipv6" {
        description
          "GRE IPV6 Tunnel";
      }
      enum "gre" {
        description
          "GRE Tunnel";
      }
      enum "mgre-ipv4" {
        description
          "MGRE IPV4 Tunnel";
      }
      enum "mgre-ipv6" {
        description
          "MGRE IPV6 Tunnel";
      }
      enum "mip-udp" {
        description
          "MIP UDP Tunnel";
      }
      enum "mip-mudp" {
        description
          "MIP MUDP Tunnel";
      }
      enum "max" {
        description
          "MAX Encap Type";
      }
    }
    description
      "ENCAP Types";
  }

  typedef Pmipv6-addr {
    type enumeration {
      enum "none" {
        description
          "None";
      }
      enum "ipv4" {
        description
          "IPV4 Address";
      }
      enum "ipv6" {
        description
          "IPV6 Address";
      }
      enum "pmipv6-addr-ipv4-ipv6" {
        description
          "Both IPV4 and IPV6 Address";
      }
    }
    description
      "Address Types";
  }

  typedef Pmipv6-role {
    type enumeration {
      enum "wlan" {
        description
          "WLAN";
      }
      enum "gpp" {
        description
          "3GPP";
      }
      enum "lte" {
        description
          "LTE";
      }
      enum "wi-max" {
        description
          "WiMAX";
      }
      enum "gma" {
        description
          "3GMA";
      }
      enum "rmax" {
        description
          "MAX Role";
      }
    }
    description
      "PMIPV6 Role Types";
  }

  grouping PMIPV6-DOMAIN-CUST-BD {
    description
      "PMIPV6 Customer Configs";
    leaf cust {
      type boolean;
      description
        "Customer Present";
    }
    leaf vrf {
      type boolean;
      description
        "Customer VRF Present";
    }
    leaf t-vrf {
      type boolean;
      description
        "Transport VRF Present";
    }
    leaf auth-option {
      type boolean;
      description
        "Authentication Option";
    }
    leaf heart-beat {
      type boolean;
      description
        "HeartBeat Option";
    }
    leaf reg-time {
      type uint32;
      description
        "BCE Registration Lifetime";
    }
    leaf cust-name {
      type string;
      description
        "CUSTOMER Name";
    }
    leaf vrf-name {
      type string;
      description
        "VRF Name";
    }
    leaf t-vrf-name {
      type string;
      description
        "Transport VRF Name";
    }
  }

  grouping PMIPV6-SHOW-LMA-NW-BD {
    description
      "PMIPV6 LMA NW";
    leaf v4pool {
      type boolean;
      description
        "IPV4 pool Present";
    }
    leaf v6pool {
      type boolean;
      description
        "IPV6 pool Present";
    }
    leaf network {
      type string;
      description
        "Network Name";
    }
    leaf ipv4 {
      type inet:ipv4-address;
      description
        "IPv4 Address";
    }
    leaf ipv6 {
      type inet:ipv6-address;
      description
        "IPv6 Address";
    }
    leaf v4pfx-len {
      type uint8;
      description
        "v4 prefix len";
    }
    leaf v6pfx-len {
      type uint8;
      description
        "v6 prefix len";
    }
    leaf mrnet {
      type uint8;
      description
        "num of mrnet";
    }
  }

  grouping PMIPV6-DOMAIN-PARAM-PEER-BD {
    description
      "PMIPV6 Domain Param Peer";
    leaf peer {
      type string;
      description
        "Peer Name";
    }
    leaf vrf-name {
      type string;
      description
        "VRF Name";
    }
    leaf interface {
      type string;
      description
        "Peer static tunnel intf";
    }
    leaf encap {
      type Pmipv6-encap;
      description
        "Encapsulation Type";
    }
    leaf auth {
      type boolean;
      description
        "Authentication Option";
    }
    leaf vrf {
      type boolean;
      description
        "VRF Present";
    }
    leaf statictunnel {
      type boolean;
      description
        "Static tunnel Present";
    }
  }

  grouping PMIPV6-SHOW-MAG-INTERFACES-BD {
    description
      "PMIPV6 MAG Interface";
    leaf apn {
      type boolean;
      description
        "APN Present";
    }
    leaf interface {
      type string;
      description
        "Access Interface Name";
    }
    leaf apn-name {
      type string;
      description
        "APN Name";
    }
  }

  grouping PMIPV6-ENTITY-ID-BD {
    description
      "Entity ID";
    leaf entity {
      type string;
      description
        "Identifier of PMIP Node";
    }
    leaf addr-type {
      type Pmipv6-addr;
      description
        "IPV4 or IPV6 or Both";
    }
    leaf address {
      type inet:ipv6-address;
      description
        "IPV6 address of LMA/MAG";
    }
    leaf ipv4-address {
      type inet:ipv4-address;
      description
        "IPV4 addrress of LMA/MAG";
    }
  }

  grouping PMIPV6-DOMAIN-PARAM-BD {
    description
      "PMIPV6 Domain Param";
    container self-id {
      description
        "Self Identifier";
      uses PMIPV6-ENTITY-ID-BD;
    }
    leaf timestamp {
      type boolean;
      description
        "Timestamp method in use";
    }
    leaf window {
      type uint64;
      description
        "Timestamp Validity Window";
    }
    leaf auth-option {
      type boolean;
      description
        "Authentication Option";
    }
    leaf reg-time {
      type uint32;
      description
        "BCE Registration Lifetime";
    }
    leaf ref-time {
      type uint32;
      description
        "BCE Refresh Time";
    }
    leaf retx {
      type uint16;
      description
        "Refresh Retransmit Init";
    }
    leaf ret-max {
      type uint16;
      description
        "Refresh Retransmit Max";
    }
    leaf bri-init {
      type uint16;
      description
        "BRI Init Delay time";
    }
    leaf bri-retries {
      type uint16;
      description
        "BRI Max Retries";
    }
    leaf bri-max {
      type uint16;
      description
        "BRI Max Delay time";
    }
    leaf max-bindings {
      type uint32;
      description
        "Allowed Max. Bindings";
    }
    leaf hnp {
      type uint8;
      description
        "Allowed HNPs per MN Intf.";
    }
    leaf encap {
      type Pmipv6-encap;
      description
        "Encapsulation Type";
    }
    leaf delete-time {
      type uint16;
      description
        "BCE Delete Hold Timer";
    }
    leaf create-time {
      type uint16;
      description
        "BCE Create Wait Timer";
    }
    leaf up-grekey {
      type uint32;
      description
        "Upstream GRE Key";
    }
    leaf down-grekey {
      type uint32;
      description
        "Downstream GRE Key";
    }
  }

  grouping PMIPV6-SHOW-GLOBALS-BD {
    description
      "PMIPv6 Globals";
    container parameters {
      description
        "Domain Parameters";
      uses PMIPV6-DOMAIN-PARAM-BD;
    }
    container mll-service {
      description
        "MLL service parameters";
      uses PMIPV6-LMA-MLL-SERVICE-BD;
    }
    leaf domain {
      type string;
      description
        "Domain Name";
    }
    leaf selfid {
      type string;
      description
        "Self ID";
    }
    leaf apn-name {
      type string;
      description
        "APN Name";
    }
    leaf role {
      type Pmipv6-role;
      description
        "Role Type";
    }
    leaf count {
      type uint32;
      description
        "Number of Networks/Intf";
    }
    leaf peers {
      type uint32;
      description
        "Number of Peers";
    }
    leaf customers {
      type uint32;
      description
        "Number of Customers";
    }
    leaf num-network {
      type uint32;
      description
        "Number of Networks";
    }
    leaf discover-mn {
      type boolean;
      description
        "Discover MN Detachment";
    }
    leaf local-routing {
      type boolean;
      description
        "Local Routing";
    }
    leaf aaa-accounting {
      type boolean;
      description
        "AAA Accounting";
    }
    leaf default-mn {
      type boolean;
      description
        "Default MN Enabled";
    }
    leaf apn {
      type boolean;
      description
        "APN Present";
    }
    leaf learn-mag {
      type boolean;
      description
        "Learn MAG";
    }
    leaf session-mgr {
      type boolean;
      description
        "Session Manager";
    }
    leaf service {
      type uint8;
      description
        "Service";
    }
    leaf profile {
      type string;
      description
        "Default MN Profile Name";
    }
    leaf ddp {
      type uint32;
      description
        "Discover Detach Period";
    }
    leaf ddt {
      type uint32;
      description
        "Discover Detach Timeout";
    }
    leaf ddr {
      type uint8;
      description
        "Discover Detach Retries";
    }
    list intf {
      description
        "MAG Access List";
      uses PMIPV6-SHOW-MAG-INTERFACES-BD;
    }
    list peer {
      description
        "Peer Parameters";
      uses PMIPV6-DOMAIN-PARAM-PEER-BD;
    }
    list network {
      description
        "LMA Network Parameters";
      uses PMIPV6-SHOW-LMA-NW-BD;
    }
    list cust {
      description
        "Customer parameters";
      uses PMIPV6-DOMAIN-CUST-BD;
    }
  }

  grouping PMIPV6-LMA-MLL-SERVICE-BD {
    description
      "PMIPV6 Service";
    leaf ignore-hoa {
      type boolean;
      description
        "Ignore Home Address";
    }
    leaf mnp-ipv4-lmn-max {
      type uint16;
      description
        "Max IPv4 prefixes per LMN";
    }
    leaf mnp-ipv6-lmn-max {
      type uint16;
      description
        "Max IPv6 prefixes per LMN";
    }
    leaf mnp-lmn-max {
      type uint16;
      description
        "Max prefixes per LMN";
    }
    leaf mnp-ipv4-cust-max {
      type uint32;
      description
        "Max IPv4 prefixes per Customer";
    }
    leaf mnp-ipv6-cust-max {
      type uint32;
      description
        "Max IPv6 prefixes per Customer";
    }
    leaf mnp-cust-max {
      type uint32;
      description
        "Max prefixes per Customer";
    }
    leaf mnp-ipv4-cust-cur {
      type uint32;
      description
        "Current IPv4 prefixes per Customer";
    }
    leaf mnp-ipv6-cust-cur {
      type uint32;
      description
        "Current IPv6 prefixes per Customer";
    }
  }

  grouping PMIPV6-SHOW-CUST-GLOBALS-BD {
    description
      "PMIPV6 Customer Globals";
    container mll-service {
      description
        "MLL service parameters";
      uses PMIPV6-LMA-MLL-SERVICE-BD;
    }
    leaf cust-name {
      type string;
      description
        "Customer Name";
    }
    leaf vrf-name {
      type string;
      description
        "VRF Name";
    }
    leaf auth-option {
      type boolean;
      description
        "Authentication Option";
    }
  }

  grouping PMIPV6-SHOW-HB-PATH-BD {
    description
      "Heartbeat Path";
    leaf vrf {
      type string;
      description
        "VRF Name";
    }
    leaf customer-name {
      type string;
      description
        "Customer Name";
    }
    leaf source-port {
      type uint32;
      description
        "Source Port";
    }
    leaf destination-port {
      type uint32;
      description
        "Destination Port";
    }
    leaf source-ipv4-address {
      type inet:ipv4-address;
      description
        "Source IPv4 Address";
    }
    leaf destination-ipv4-address {
      type inet:ipv4-address;
      description
        "Destination IPv4 Address";
    }
    leaf source-ipv6-address {
      type inet:ipv6-address;
      description
        "Source IPv6 Address";
    }
    leaf destination-ipv6-address {
      type inet:ipv6-address;
      description
        "Destination IPv6 Address";
    }
    leaf status {
      type boolean;
      description
        "Path Status";
    }
    leaf ipv6-path {
      type boolean;
      description
        "IPv6 Path";
    }
  }

  grouping PMIPV6-V6-PREFIX-BD {
    description
      "IPv6 Prefix";
    leaf pfxlen {
      type uint8;
      description
        "IPv6 prefix length";
    }
    leaf prefix {
      type inet:ipv6-address;
      description
        "IPv6 prefix";
    }
  }

  grouping PMIPV6-V4-PREFIX-BD {
    description
      "IPv4 Prefix";
    leaf pfxlen {
      type uint8;
      description
        "IPv4 prefix length";
    }
    leaf prefix {
      type inet:ipv4-address;
      description
        "IPv4 prefix";
    }
  }

  grouping PMIPV6-SHOW-BINDING-COA-BD {
    description
      "COA entry";
    leaf llid {
      type string;
      description
        "Link Layer Identifier";
    }
    leaf peer-name {
      type string;
      description
        "Peer Name";
    }
    leaf tunnel {
      type string;
      description
        "Tunnel Interface";
    }
    leaf e-label {
      type string;
      description
        "Egress Label";
    }
    leaf color {
      type string;
      description
        "Label Color";
    }
    leaf roa-min-tf {
      type string;
      description
        "Roaming Intf";
    }
    leaf pstate {
      type string;
      description
        "COA STATE";
    }
    leaf msisdn {
      type string;
      description
        "MSISDN";
    }
    leaf imsi {
      type string;
      description
        "IMSI or IMSI NAI";
    }
    leaf cdma-nai {
      type string;
      description
        "CDMA NAI";
    }
    leaf pgw-apn {
      type string;
      description
        "Subscriber APN on PWG";
    }
    leaf pgw-trans-vrf {
      type string;
      description
        "Subscriber Transport VRF on PGW";
    }
    leaf att {
      type uint16;
      description
        "MN ATT";
    }
    leaf lifetime {
      type uint32;
      description
        "Life Time of coa";
    }
    leaf lifetime-remaining {
      type uint32;
      description
        "Life Time remain of coa";
    }
    leaf refresh {
      type uint32;
      description
        "refresh Time of coa";
    }
    leaf refresh-rem {
      type uint32;
      description
        "refresh Time remain of coa";
    }
    leaf dnkey {
      type uint32;
      description
        "down key for coa tunnel";
    }
    leaf upkey {
      type uint32;
      description
        "up key for coa tunnel";
    }
    leaf coa-v4 {
      type inet:ipv4-address;
      description
        "IPv4 CoA";
    }
    leaf coa-v6 {
      type inet:ipv6-address;
      description
        "IPv6 CoA";
    }
  }

  grouping PMIPV6-SHOW-BINDING-BD {
    description
      "PMIPV6 Binding";
    leaf mnnai {
      type string;
      description
        "Mobile Node Identifier";
    }
    leaf customer-name-xr {
      type string;
      description
        "Customer name";
    }
    leaf llid {
      type string;
      description
        "Link Layer Identifier";
    }
    leaf peer-id {
      type string;
      description
        "Peer Identifier";
    }
    leaf phyintf {
      type string;
      description
        "Access Interface";
    }
    leaf tunnel {
      type string;
      description
        "Tunnel Interface";
    }
    leaf state {
      type string;
      description
        "State Name";
    }
    leaf apn {
      type string;
      description
        "Access Point Network";
    }
    leaf att {
      type uint16;
      description
        "MN ATT";
    }
    leaf hoa {
      type inet:ipv4-address;
      description
        "MN HOA";
    }
    leaf dflt {
      type inet:ipv4-address;
      description
        "MN Default Router";
    }
    leaf lifetime {
      type uint32;
      description
        "Life Time of Binding";
    }
    leaf liferem {
      type uint32;
      description
        "Life Time Remaining";
    }
    leaf refresh {
      type uint32;
      description
        "Refresh Time of Binding";
    }
    leaf refresh-rem {
      type uint32;
      description
        "Refresh Time Remaining";
    }
    leaf prefix-len {
      type uint8;
      description
        "Prefix Length";
    }
    leaf num-hnps {
      type uint8;
      description
        "HNP count";
    }
    leaf num-coa {
      type uint8;
      description
        "COA count";
    }
    leaf num-dmnp-v4 {
      type uint8;
      description
        "IPv4 DMNP count";
    }
    leaf num-dmnp-v6 {
      type uint8;
      description
        "IPv6 DMNP count";
    }
    leaf hnps {
      type inet:ipv6-address;
      description
        "MN Home Network Prefixes";
    }
    leaf ignore-home-address {
      type boolean;
      description
        "Ignore HoA/HNP";
    }
    leaf up-stream-grekey {
      type uint32;
      description
        "Upstream GRE Key";
    }
    leaf down-stream-grekey {
      type uint32;
      description
        "DownStream GRE Key";
    }
    leaf vrfid {
      type uint32;
      description
        "VRF ID of Access Interface";
    }
    list coa {
      description
        "COA entries";
      uses PMIPV6-SHOW-BINDING-COA-BD;
    }
    list dmnp-v4 {
      description
        "IPv4 DMNP prefixes";
      uses PMIPV6-V4-PREFIX-BD;
    }
    list dmnp-v6 {
      description
        "IPv6 DMNP prefixes";
      uses PMIPV6-V6-PREFIX-BD;
    }
  }

  grouping PMIPV6-SHOW-LMA-PEER-STATS-BD {
    description
      "PMIPv6 LMA Peer Statistics";
    container protocol-statistics {
      description
        "LMA Protocol Statistics";
      uses PMIPV6-LMA-PROTO-STATS-BD;
    }
    leaf lma-identifier {
      type string;
      description
        "LMA Identifier";
    }
  }

  grouping PMIPV6-MM-PKT-STATS-BD {
    description
      "Packet Statistics";
    leaf checksum-errors {
      type uint64;
      description
        "Checksumm errors";
    }
    leaf send-drops {
      type uint64;
      description
        "Drop count of sent packets";
    }
    leaf receive-drops {
      type uint64;
      description
        "Drop count of received packets";
    }
    leaf packets-received {
      type uint64;
      description
        "Count of received packets";
    }
    leaf packets-sent {
      type uint64;
      description
        "Count of sent packets";
    }
    leaf send-drops-ipv6 {
      type uint64;
      description
        "Drop count of IPv6 sent packets";
    }
    leaf receive-drops-ipv6 {
      type uint64;
      description
        "Drop count of IPv6 received packets";
    }
    leaf packets-received-ipv6 {
      type uint64;
      description
        "Count of IPv6 received packets";
    }
    leaf packets-sent-ipv6 {
      type uint64;
      description
        "Count of IPv6 sent packets";
    }
  }

  grouping PMIPV6-SHOW-LMA-STATS-BD {
    description
      "PMIPv6 LMA Statistics";
    container packet-statistics {
      description
        "Packet Statistics";
      uses PMIPV6-MM-PKT-STATS-BD;
    }
    container protocol-statistics {
      description
        "LMA Protocol Statistics";
      uses PMIPV6-LMA-PROTO-STATS-BD;
    }
    container accounting-statistics {
      description
        "LMA Accounting Statistics";
      uses PMIPV6-ACCT-STATS-BD;
    }
    leaf lma-identifier {
      type string;
      description
        "LMA Identifier";
    }
    leaf bce-count {
      type uint32;
      description
        "Count of Bindings";
    }
    leaf handoff-count {
      type uint32;
      description
        "Count of Handoffs";
    }
    leaf single-tenant-count {
      type uint32;
      description
        "Count of Single Tenants";
    }
    leaf multi-tenant-count {
      type uint32;
      description
        "Count of Multi Tenants";
    }
  }

  grouping PMIPV6-SHOW-LMA-LICENSE-STATS-BD {
    description
      "PMIPv6 LMA License Statistics";
    leaf lma-identifier {
      type string;
      description
        "LMA Identifier";
    }
    leaf bce-count {
      type uint32;
      description
        "Instantaneous Count of Bindings";
    }
    leaf peak-bce-count {
      type uint32;
      description
        "Peak Count of Bindings";
    }
    leaf peak-bce-count-reset-timestamp {
      type uint32;
      description
        "Timestamp when the Peak Count of Bindings was
         reset";
    }
  }

  grouping PMIPV6-ACCT-STATS-BD {
    description
      "PMIPv6 Accounting Statistics";
    leaf accounting-start-sent-count {
      type uint64;
      description
        "Count of Accounting Start Records Sent";
    }
    leaf accounting-update-sent-count {
      type uint64;
      description
        "Count of Accounting Update Records Sent";
    }
    leaf accounting-stop-sent-count {
      type uint64;
      description
        "Count of Accounting Stop Records Sent";
    }
  }

  grouping PMIPV6-PBRA-STATS-BD {
    description
      "PMIPv6 PBRA Statistics";
    leaf pbra-count {
      type uint64;
      description
        "Count of PBRAs";
    }
    leaf pbra-drop-count {
      type uint32;
      description
        "Count of PBRAs dropped";
    }
    leaf success-count {
      type uint32;
      description
        "Count of Revoc Status - Success";
    }
    leaf partial-success-count {
      type uint32;
      description
        "Count of Revoc Status - Partial Success";
    }
    leaf no-binding-count {
      type uint32;
      description
        "Count of Revoc Status - Binding Does Not Exist";
    }
    leaf hoa-required-count {
      type uint32;
      description
        "Count of Revoc Status - IPv4 Home Address Option
         Required";
    }
    leaf no-author-for-global-revoc-count {
      type uint32;
      description
        "Count of Revoc Status - Global Revocation NOT
         Authorized";
    }
    leaf mn-identity-required-count {
      type uint32;
      description
        "Count of Revoc Status - Revoked Mobile Node
         Identity Required";
    }
    leaf mn-attached-count {
      type uint32;
      description
        "Count of Revoc Status - Revocation Failed - MN
         is Attached";
    }
    leaf unknown-revoc-trigger-count {
      type uint32;
      description
        "Count of Revoc Status - Revocation Trigger NOT
         supported";
    }
    leaf revoc-function-not-supported-count {
      type uint32;
      description
        "Count of Revoc Status - Revocation Function NOT
         Supported";
    }
    leaf pbr-not-supported-count {
      type uint32;
      description
        "Count of Revoc Status - Proxy Binding Revocation
         NOT Supported";
    }
  }

  grouping PMIPV6-PBRI-STATS-BD {
    description
      "PMIPv6 PBRI Statistics";
    leaf pbri-count {
      type uint64;
      description
        "Count of PBRIs";
    }
    leaf pbri-drop-count {
      type uint32;
      description
        "Count of PBRIs dropped";
    }
    leaf unspecified-count {
      type uint32;
      description
        "Count of Revoc Trigger - Unspecified";
    }
    leaf admin-reason-count {
      type uint32;
      description
        "Count of Revoc Trigger - Administrative Reason";
    }
    leaf mag-handover-same-att-count {
      type uint32;
      description
        "Count of Revoc Trigger - Inter MAG Handover Same
         ATT";
    }
    leaf mag-handover-different-att-count {
      type uint32;
      description
        "Count of Revoc Trigger - Inter MAG Handover
         Different ATT";
    }
    leaf mag-handover-unknown-count {
      type uint32;
      description
        "Count of Revoc Trigger - Inter MAG Handover
         Unknown";
    }
    leaf user-session-termination-count {
      type uint32;
      description
        "Count of Revoc Trigger - User Init Session
         Terminatation";
    }
    leaf network-session-termination-count {
      type uint32;
      description
        "Count of Revoc Trigger - Access Network Session
         Termination";
    }
    leaf out-of-sync-bce-state-count {
      type uint32;
      description
        "Count of Revoc Trigger - Possible Out-of-Sync
         BCE State";
    }
    leaf per-peer-policy-count {
      type uint32;
      description
        "Count of Revoc Trigger - Per-Peer Policy";
    }
    leaf revoking-mn-local-policy-count {
      type uint32;
      description
        "Count of Revoc Trigger - Revoking Mobility Node
         Local Policy";
    }
  }

  grouping PMIPV6-PBA-STATS-BD {
    description
      "PMIPv6 PBA Statistics";
    leaf pba-count {
      type uint64;
      description
        "Count of PBAs";
    }
    leaf pba-drop-count {
      type uint32;
      description
        "Count of PBAs dropped";
    }
    leaf accepted-count {
      type uint32;
      description
        "Count of Status Code - Binding Update accepted";
    }
    leaf unknown-count {
      type uint32;
      description
        "Count of Status Code - Last BA status code sent.";
    }
    leaf unspecified-failure-count {
      type uint32;
      description
        "Count of Status Code - Reason unspecified";
    }
    leaf admin-failure-count {
      type uint32;
      description
        "Count of Status Code - Administratively
         prohibited";
    }
    leaf resource-failure-count {
      type uint32;
      description
        "Count of Status Code - Insufficient resources";
    }
    leaf home-reg-failure-count {
      type uint32;
      description
        "Count of Status Code - Home registration not
         supported";
    }
    leaf home-subnet-failure-count {
      type uint32;
      description
        "Count of Status Code - Not home subnet";
    }
    leaf bad-sequence-failure-count {
      type uint32;
      description
        "Count of Status Code - Sequence number out of
         window";
    }
    leaf reg-type-failure-count {
      type uint32;
      description
        "Count of Status Code - Registration type change";
    }
    leaf authen-failure-count {
      type uint32;
      description
        "Count of Status Code - Auth Fail";
    }
    leaf proxy-reg-not-enabled-count {
      type uint32;
      description
        "Count of Status Code - Proxy Registration not
         enabled";
    }
    leaf not-lma-for-this-mn-count {
      type uint32;
      description
        "Count of Status Code - Not LMA for this Mobile
         Node";
    }
    leaf no-author-for-proxy-reg-count {
      type uint32;
      description
        "Count of Status Code - MAG not auth.for proxyreg";
    }
    leaf no-author-for-hnp-count {
      type uint32;
      description
        "Count of Status Code - Not authorized for HNP";
    }
    leaf timestamp-mismatch-count {
      type uint32;
      description
        "Count of Status Code - Invalid timestamp value";
    }
    leaf timestamp-lower-than-previous-accepted-count {
      type uint32;
      description
        "Count of Status Code - Timestamp lower than
         previous accepted";
    }
    leaf missing-hnp-opt-count {
      type uint32;
      description
        "Count of Status Code - Missing Home Network
         Prefix option";
    }
    leaf received-hnps-do-not-match-bce-hnps-count {
      type uint32;
      description
        "Count of Status Code - Recevied HNPs do not
         match with BCE";
    }
    leaf missing-mn-id-opt-count {
      type uint32;
      description
        "Count of Status Code - Missing MN identifier
         option";
    }
    leaf missing-hi-opt-count {
      type uint32;
      description
        "Count of Status Code - Missing Handoff Indicator";
    }
    leaf missing-access-tech-type-opt-count {
      type uint32;
      description
        "Count of Status Code - Missing ATT option";
    }
    leaf no-author-for-ipv4-mobility-count {
      type uint32;
      description
        "Count of Status Code - Not authorized for IPv4
         mobility";
    }
    leaf no-author-for-ipv4-hoa-count {
      type uint32;
      description
        "Count of Status Code - Not authorized for IPv4
         HoA";
    }
    leaf no-author-for-ipv6-mobility-count {
      type uint32;
      description
        "Count of Status Code - Not authorized for IPv6
         mobility";
    }
    leaf multiple-ipv4-ho-a-not-supported-count {
      type uint32;
      description
        "Count of Status Code - Multiple IPv4 HoA not
         supported";
    }
    leaf gre-key-opt-required-count {
      type uint32;
      description
        "Count of Status Code - GRE Key option is
         required";
    }
  }

  grouping PMIPV6-PBU-STATS-BD {
    description
      "PMIPv6 PBU Statistics";
    leaf pbu-count {
      type uint64;
      description
        "Count of PBUs";
    }
    leaf pbu-drop-count {
      type uint32;
      description
        "Count of PBUs Dropped";
    }
  }

  grouping PMIPV6-LMA-PROTO-STATS-BD {
    description
      "PMIPv6 LMA Protocol Statistics";
    container pbu-receive-statistics {
      description
        "PBU Receive Statistics";
      uses PMIPV6-PBU-STATS-BD;
    }
    container pba-send-statistics {
      description
        "PBA Send Statistics";
      uses PMIPV6-PBA-STATS-BD;
    }
    container pbri-send-statistics {
      description
        "PBRI Send Statistics";
      uses PMIPV6-PBRI-STATS-BD;
    }
    container pbri-receive-statistics {
      description
        "PBRI Receive Statistics";
      uses PMIPV6-PBRI-STATS-BD;
    }
    container pbra-send-statistics {
      description
        "PBRA Send Statistics";
      uses PMIPV6-PBRA-STATS-BD;
    }
    container pbra-receive-statistics {
      description
        "PBRA Receive Statistics";
      uses PMIPV6-PBRA-STATS-BD;
    }
  }

  grouping PMIPV6-SHOW-LMA-CUST-STATS-BD {
    description
      "PMIPv6 LMA Customer Statistics";
    container protocol-statistics {
      description
        "LMA Protocol Statistics";
      uses PMIPV6-LMA-PROTO-STATS-BD;
    }
    container accounting-statistics {
      description
        "LMA Accounting Statistics";
      uses PMIPV6-ACCT-STATS-BD;
    }
    leaf lma-identifier {
      type string;
      description
        "LMA Identifier";
    }
    leaf bce-count {
      type uint32;
      description
        "Count of Bindings";
    }
    leaf handoff-count {
      type uint32;
      description
        "Count of Handoffs";
    }
    leaf ipv4-mnp-count {
      type uint32;
      description
        "Count of IPv4 Mobile Node Prefixes";
    }
    leaf ipv6-mnp-count {
      type uint32;
      description
        "Count of IPv6 Mobile Node Prefixes";
    }
  }
}
