module Cisco-IOS-XR-sysadmin-show-media {
  namespace "http://www.cisco.com/ns/yang/Cisco-IOS-XR-sysadmin-show-media";
  prefix mediasvrh;

  import cisco-semver {
    prefix semver;
  }

  organization
    "Cisco Systems Inc.";
  contact
    "Cisco Systems, Inc.
     Customer Service

     Postal: 170 West Tasman Drive
     San Jose, CA 95134

     Tel: +1 800 553-NETS

     E-mail: cs-yang@cisco.com";
  description
    "This module contains a collection of YANG
     definitions for Cisco IOS-XR SysAdmin to
     report back memory utilization in sysadmin.

     Copyright (c) 2018-2020 by Cisco Systems, Inc.
     All rights reserved.";

  revision 2020-06-04 {
    semver:module-version "2.0.0";
    description
      "Breaking output show_media_report into fields";
  }
  revision 2020-04-08 {
    semver:module-version "1.0.0";
    description
      "Suppressing raw output";
  }
  revision 2019-04-15 {
    semver:module-version "1.0.0";
    description
      "Establish semantic version baseline.";
  }
  revision 2019-02-06 {
    description
      "Initial revision";
  }

  container ShowMedia {
    config false;
    description
      "Show the memory usage in sysadmin";
    list all-locations {
      key "location";
      description
        "Media information for system";
      leaf location {
        type string;
        description
          "Media information for one node";
      }
      list partition {
        key "name";
        leaf name {
          type string;
          description
            "Media partition name";
        }
        leaf size {
          type string;
          description
            "Media partition size in T/G/M/K/B";
        }
        leaf used {
          type string;
          description
            "Media partition used space in T/G/M/K/B";
        }
        leaf percent {
          type string;
          description
            "Media partition used space percentage";
        }
        leaf avail {
          type string;
          description
            "Media partition available space in T/G/M/K/B";
        }
      }
    }
  }
}
