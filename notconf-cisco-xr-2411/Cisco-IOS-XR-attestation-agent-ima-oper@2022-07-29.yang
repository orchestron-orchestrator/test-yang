module Cisco-IOS-XR-attestation-agent-ima-oper {
  namespace "http://cisco.com/ns/yang/Cisco-IOS-XR-attestation-agent-ima-oper";
  prefix attestation-agent-ima-oper;

  import cisco-semver {
    prefix semver;
  }

  include Cisco-IOS-XR-attestation-agent-ima-oper-sub1 {
    revision-date 2022-07-29;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR attestation-agent-ima package operational data.

     This module contains definitions
     for the following management objects:
       attestation: Oper data for IMA cache and Cron job statistics

     Copyright (c) 2013-2022 by Cisco Systems, Inc.
     All rights reserved.";

  revision 2022-07-29 {
    semver:module-version "1.1.0";
    description
      "Changed a few entries in bag from character array to string.";
  }
  revision 2021-07-19 {
    semver:module-version "1.1.0";
    description
      "Added total_count under cron job stat bag.";
  }
  revision 2020-09-21 {
    semver:module-version "1.0.0";
    description
      "Fixed bag mismatch issue for dossier stat.";
  }
  revision 2020-09-15 {
    description
      "Added task for netconf support.";
  }
  revision 2019-04-05 {
    description
      "Establish semantic version baseline.";
  }
  revision 2015-11-09 {
    description
      "IOS XR 6.0 revision.";
  }

  container attestation {
    config false;
    description
      "Oper data for IMA cache and Cron job statistics ";
    container ima-cache {
      description
        "Oper data for IMA cache and Cron job statistics ";
      container ima-corrupt-stat {
        description
          "Cron job running stats";
        uses BLOCK-VALID-DET;
      }
      container dossier-stat {
        description
          "Dossier running stats";
        uses DOSSIER-STAT;
      }
      container cron-stat {
        description
          "Cron job running stats";
        uses CRON-DET;
      }
      container node-cache-summary {
        description
          "Cache summary for nodes running agent";
        uses CACHE-DET;
      }
      container node-block-summary {
        description
          "Block summary for nodes running agent";
        uses BLOCK-DET;
      }
    }
  }
}
