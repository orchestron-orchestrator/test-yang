module Cisco-IOS-XR-mirror-oper {
  namespace "http://cisco.com/ns/yang/Cisco-IOS-XR-mirror-oper";
  prefix mirror-oper;

  import cisco-semver {
    prefix semver;
  }

  include Cisco-IOS-XR-mirror-oper-sub1 {
    revision-date 2019-04-05;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR mirror package operational data.

     This module contains definitions
     for the following management objects:
       mirror-oper: Mirror operational data

     Copyright (c) 2013-2019 by Cisco Systems, Inc.
     All rights reserved.";

  revision 2019-04-05 {
    semver:module-version "1.0.0";
    description
      "Establish semantic version baseline.";
  }
  revision 2015-11-09 {
    description
      "IOS XR 6.0 revision.";
  }

  container mirror-oper {
    config false;
    description
      "Mirror operational data";
    container show-mirror-sync-entries {
      description
        "The list of dirs which are being synced";
      list show-mirror-sync-entry {
        key "directory";
        description
          "The dirs subject to syncing and if they are
           currently syncing";
        leaf directory {
          type string;
          description
            "Directory";
        }
        uses MIRROR-SYNC-ENTRY;
      }
    }
    container show-mirror-entries {
      description
        "Entries from show mirror";
      container show-mirror-mismatch-entries {
        description
          "Only entries which are not mirrored";
        list show-mirror-mismatch-entry {
          key "path";
          description
            "The individual path entries from show mirror";
          leaf path {
            type string;
            description
              "Path";
          }
          uses MIRROR-FILE-ENTRY;
        }
      }
      container show-mirror-entries {
        description
          "All file entries from show mirror";
        list show-mirror-entry {
          key "path";
          description
            "The individual path entries from show mirror";
          leaf path {
            type string;
            description
              "Path";
          }
          uses MIRROR-FILE-ENTRY;
        }
      }
    }
  }
}
