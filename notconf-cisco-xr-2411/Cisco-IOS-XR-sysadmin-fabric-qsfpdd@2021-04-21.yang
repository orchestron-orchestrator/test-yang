module Cisco-IOS-XR-sysadmin-fabric-qsfpdd {
  namespace "http://www.cisco.com/ns/yang/Cisco-IOS-XR-sysadmin-fabric-qsfpdd";
  prefix fabric_qsfpdd;

  import tailf-xsd-types {
    prefix xs;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains definitions
     for the Calvados model objects.

     Copyright (c) 2012-2020 by Cisco Systems, Inc.
     All rights reserved.";

  revision 2021-04-21 {
    semver:module-version "1.0.0";
    description
      "Removed unused imports";
  }

  grouping dom_output {
    list qsfpdd_port {
      key "qsfpdd_port_num";
      leaf show_port {
        type boolean;
        default "false";
      }
      leaf error_msg {
        type string;
      }
      leaf qsfpdd_port_num {
        type uint32;
        description
          "Front Port Num";
      }
      leaf optics_description {
        type string;
      }
      leaf vendorname {
        type string;
      }
      leaf vendor_rev_num {
        type string;
      }
      leaf vid {
        type string;
      }
      leaf pid {
        type string;
      }
      leaf qsfp_type {
        type uint32;
      }
      leaf is_cisco_supported {
        type boolean;
      }
      leaf vendor_pn {
        type string;
      }
      leaf vendor_sn {
        type string;
      }
      leaf ven_date_code {
        type string;
      }
      leaf vendor_oui {
        type string;
      }
      leaf temp_rd {
        type xs:double;
      }
      leaf volt_rd {
        type xs:double;
      }
      leaf wavelength {
        type xs:double;
      }
      leaf temp_hi_alarm_sts {
        type string;
      }
      leaf temp_lo_alarm_sts {
        type string;
      }
      leaf volt_hi_alarm_sts {
        type string;
      }
      leaf volt_lo_alarm_sts {
        type string;
      }
      leaf rx_power_dbm_0 {
        type xs:double;
      }
      leaf rx_power_dbm_1 {
        type xs:double;
      }
      leaf rx_power_dbm_2 {
        type xs:double;
      }
      leaf rx_power_dbm_3 {
        type xs:double;
      }
      leaf rx_power_dbm_4 {
        type xs:double;
      }
      leaf rx_power_dbm_5 {
        type xs:double;
      }
      leaf rx_power_dbm_6 {
        type xs:double;
      }
      leaf rx_power_dbm_7 {
        type xs:double;
      }
      leaf rx_los_0 {
        type string;
      }
      leaf rx_los_1 {
        type string;
      }
      leaf rx_los_2 {
        type string;
      }
      leaf rx_los_3 {
        type string;
      }
      leaf rx_los_4 {
        type string;
      }
      leaf rx_los_5 {
        type string;
      }
      leaf rx_los_6 {
        type string;
      }
      leaf rx_los_7 {
        type string;
      }
      leaf rx_cdr_lol_0 {
        type string;
      }
      leaf rx_cdr_lol_1 {
        type string;
      }
      leaf rx_cdr_lol_2 {
        type string;
      }
      leaf rx_cdr_lol_3 {
        type string;
      }
      leaf rx_cdr_lol_4 {
        type string;
      }
      leaf rx_cdr_lol_5 {
        type string;
      }
      leaf rx_cdr_lol_6 {
        type string;
      }
      leaf rx_cdr_lol_7 {
        type string;
      }
      leaf rx_hi_alarm_0 {
        type string;
      }
      leaf rx_hi_alarm_1 {
        type string;
      }
      leaf rx_hi_alarm_2 {
        type string;
      }
      leaf rx_hi_alarm_3 {
        type string;
      }
      leaf rx_hi_alarm_4 {
        type string;
      }
      leaf rx_hi_alarm_5 {
        type string;
      }
      leaf rx_hi_alarm_6 {
        type string;
      }
      leaf rx_hi_alarm_7 {
        type string;
      }
      leaf rx_lo_alarm_0 {
        type string;
      }
      leaf rx_lo_alarm_1 {
        type string;
      }
      leaf rx_lo_alarm_2 {
        type string;
      }
      leaf rx_lo_alarm_3 {
        type string;
      }
      leaf rx_lo_alarm_4 {
        type string;
      }
      leaf rx_lo_alarm_5 {
        type string;
      }
      leaf rx_lo_alarm_6 {
        type string;
      }
      leaf rx_lo_alarm_7 {
        type string;
      }
      leaf tx_power_dbm_0 {
        type xs:double;
      }
      leaf tx_power_dbm_1 {
        type xs:double;
      }
      leaf tx_power_dbm_2 {
        type xs:double;
      }
      leaf tx_power_dbm_3 {
        type xs:double;
      }
      leaf tx_power_dbm_4 {
        type xs:double;
      }
      leaf tx_power_dbm_5 {
        type xs:double;
      }
      leaf tx_power_dbm_6 {
        type xs:double;
      }
      leaf tx_power_dbm_7 {
        type xs:double;
      }
      leaf tx_bias_current_0 {
        type xs:double;
      }
      leaf tx_bias_current_1 {
        type xs:double;
      }
      leaf tx_bias_current_2 {
        type xs:double;
      }
      leaf tx_bias_current_3 {
        type xs:double;
      }
      leaf tx_bias_current_4 {
        type xs:double;
      }
      leaf tx_bias_current_5 {
        type xs:double;
      }
      leaf tx_bias_current_6 {
        type xs:double;
      }
      leaf tx_bias_current_7 {
        type xs:double;
      }
      leaf tx_laser_status_0 {
        type string;
      }
      leaf tx_laser_status_1 {
        type string;
      }
      leaf tx_laser_status_2 {
        type string;
      }
      leaf tx_laser_status_3 {
        type string;
      }
      leaf tx_laser_status_4 {
        type string;
      }
      leaf tx_laser_status_5 {
        type string;
      }
      leaf tx_laser_status_6 {
        type string;
      }
      leaf tx_laser_status_7 {
        type string;
      }
      leaf tx_los_status_0 {
        type string;
      }
      leaf tx_los_status_1 {
        type string;
      }
      leaf tx_los_status_2 {
        type string;
      }
      leaf tx_los_status_3 {
        type string;
      }
      leaf tx_los_status_4 {
        type string;
      }
      leaf tx_los_status_5 {
        type string;
      }
      leaf tx_los_status_6 {
        type string;
      }
      leaf tx_los_status_7 {
        type string;
      }
      leaf tx_fault_status_0 {
        type string;
      }
      leaf tx_fault_status_1 {
        type string;
      }
      leaf tx_fault_status_2 {
        type string;
      }
      leaf tx_fault_status_3 {
        type string;
      }
      leaf tx_fault_status_4 {
        type string;
      }
      leaf tx_fault_status_5 {
        type string;
      }
      leaf tx_fault_status_6 {
        type string;
      }
      leaf tx_fault_status_7 {
        type string;
      }
      leaf tx_cdr_lol_status_0 {
        type string;
      }
      leaf tx_cdr_lol_status_1 {
        type string;
      }
      leaf tx_cdr_lol_status_2 {
        type string;
      }
      leaf tx_cdr_lol_status_3 {
        type string;
      }
      leaf tx_cdr_lol_status_4 {
        type string;
      }
      leaf tx_cdr_lol_status_5 {
        type string;
      }
      leaf tx_cdr_lol_status_6 {
        type string;
      }
      leaf tx_cdr_lol_status_7 {
        type string;
      }
      leaf tx_power_high_alarm_status_0 {
        type string;
      }
      leaf tx_power_high_alarm_status_1 {
        type string;
      }
      leaf tx_power_high_alarm_status_2 {
        type string;
      }
      leaf tx_power_high_alarm_status_3 {
        type string;
      }
      leaf tx_power_high_alarm_status_4 {
        type string;
      }
      leaf tx_power_high_alarm_status_5 {
        type string;
      }
      leaf tx_power_high_alarm_status_6 {
        type string;
      }
      leaf tx_power_high_alarm_status_7 {
        type string;
      }
      leaf tx_power_low_alarm_status_0 {
        type string;
      }
      leaf tx_power_low_alarm_status_1 {
        type string;
      }
      leaf tx_power_low_alarm_status_2 {
        type string;
      }
      leaf tx_power_low_alarm_status_3 {
        type string;
      }
      leaf tx_power_low_alarm_status_4 {
        type string;
      }
      leaf tx_power_low_alarm_status_5 {
        type string;
      }
      leaf tx_power_low_alarm_status_6 {
        type string;
      }
      leaf tx_power_low_alarm_status_7 {
        type string;
      }
      leaf tx_laser_bias_high_alarm_status_0 {
        type string;
      }
      leaf tx_laser_bias_high_alarm_status_1 {
        type string;
      }
      leaf tx_laser_bias_high_alarm_status_2 {
        type string;
      }
      leaf tx_laser_bias_high_alarm_status_3 {
        type string;
      }
      leaf tx_laser_bias_high_alarm_status_4 {
        type string;
      }
      leaf tx_laser_bias_high_alarm_status_5 {
        type string;
      }
      leaf tx_laser_bias_high_alarm_status_6 {
        type string;
      }
      leaf tx_laser_bias_high_alarm_status_7 {
        type string;
      }
      leaf tx_laser_bias_low_alarm_status_0 {
        type string;
      }
      leaf tx_laser_bias_low_alarm_status_1 {
        type string;
      }
      leaf tx_laser_bias_low_alarm_status_2 {
        type string;
      }
      leaf tx_laser_bias_low_alarm_status_3 {
        type string;
      }
      leaf tx_laser_bias_low_alarm_status_4 {
        type string;
      }
      leaf tx_laser_bias_low_alarm_status_5 {
        type string;
      }
      leaf tx_laser_bias_low_alarm_status_6 {
        type string;
      }
      leaf tx_laser_bias_low_alarm_status_7 {
        type string;
      }
      leaf temp_high_alarm {
        type xs:double;
      }
      leaf temp_high_warn_alarm {
        type xs:double;
      }
      leaf temp_low_warn_alarm {
        type xs:double;
      }
      leaf temp_low_alarm {
        type xs:double;
      }
      leaf volt_high_alarm {
        type xs:double;
      }
      leaf volt_high_warn_alarm {
        type xs:double;
      }
      leaf volt_low_warn_alarm {
        type xs:double;
      }
      leaf volt_low_alarm {
        type xs:double;
      }
      leaf tx_cur_high_alarm {
        type xs:double;
      }
      leaf tx_cur_high_warn_alarm {
        type xs:double;
      }
      leaf tx_cur_low_warn_alarm {
        type xs:double;
      }
      leaf tx_cur_low_alarm {
        type xs:double;
      }
      leaf tx_pwr_high_alarm {
        type xs:double;
      }
      leaf tx_pwr_high_warn_alarm {
        type xs:double;
      }
      leaf tx_pwr_low_warn_alarm {
        type xs:double;
      }
      leaf tx_pwr_low_alarm {
        type xs:double;
      }
      leaf rx_pwr_high_alarm {
        type xs:double;
      }
      leaf rx_pwr_high_warn_alarm {
        type xs:double;
      }
      leaf rx_pwr_low_warn_alarm {
        type xs:double;
      }
      leaf rx_pwr_low_alarm {
        type xs:double;
      }
    }
  }

  grouping fc_qsfpdd {
    container qsfpdd {
      container dom {
        list location {
          key "loc_str";
          leaf loc_str {
            type string;
          }
          leaf description {
            type string;
            default "location (R/S)";
          }
          uses dom_output;
        }
      }
      container summary {
        list rack {
          key "rack_str";
          config false;
          leaf rack_str {
            type string;
          }
          leaf description {
            type string;
            default "Rack No.";
          }
          list qsfpdd_rack_summary_data {
            leaf qsfpdd_rack_data {
              type string;
            }
          }
        }
      }
    }
  }
}
