module Cisco-IOS-XR-asic-error-oper {
  namespace "http://cisco.com/ns/yang/Cisco-IOS-XR-asic-error-oper";
  prefix asic-error-oper;

  import Cisco-IOS-XR-types {
    prefix xr;
  }
  import cisco-semver {
    prefix semver;
  }

  include Cisco-IOS-XR-asic-error-oper-sub2 {
    revision-date 2023-06-08;
  }
  include Cisco-IOS-XR-asic-error-oper-sub1 {
    revision-date 2023-06-08;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR asic-error package operational data.

     This module contains definitions
     for the following management objects:
       asic-errors: Error summary of all asics

     Copyright (c) 2013-2023 by Cisco Systems, Inc.
     All rights reserved.";

  revision 2023-06-08 {
    semver:module-version "1.1.0";
    description
      "Datatype change from hex to string for Asic Information.";
  }
  revision 2021-02-10 {
    semver:module-version "1.1.0";
    description
      "Introduced working oper model for asic-errors.";
  }
  revision 2019-09-27 {
    semver:module-version "1.0.0";
    description
      "Introduced working oper model for asic-errors.";
  }
  revision 2019-09-24 {
    semver:module-version "1.0.0";
    description
      "Introduced working oper model for asic-errors.";
  }
  revision 2019-04-05 {
    description
      "Establish semantic version baseline.";
  }
  revision 2015-11-09 {
    description
      "IOS XR 6.0 revision.";
  }

  container asic-errors {
    config false;
    description
      "Error summary of all asics";
    container nodes {
      description
        "Asic errors for each available nodes";
      list node {
        key "node-name";
        description
          "Asic error for a particular node";
        leaf node-name {
          type xr:Node-id;
          description
            "Node ID";
        }
        list asic-information {
          key "asic";
          description
            "Asic on the node";
          container instances {
            description
              "All asic errors  on the node";
            list instance {
              key "asic-instance";
              description
                "Particular asic instance on the node";
              container categories {
                description
                  "Error path of the instances";
                list category {
                  key "category";
                  description
                    "Error category soft/hard";
                  leaf category {
                    type xr:Cisco-ios-xr-string;
                    description
                      "Error Category soft/hard";
                  }
                  list error-class {
                    key "class";
                    description
                      "Error Classes - supported by asic type";
                    container error-info-indexes {
                      description
                        "Asic ErrorClass Info";
                      list error-info-index {
                        key "error-info-index";
                        description
                          "Asic Error List Per Class";
                        container error-counter {
                          description
                            "Asic Error data Per Index Per class";
                          uses ASIC-ERROR-INST-BG;
                        }
                        leaf error-info-index {
                          type uint32;
                          description
                            "Indexed Counter Key";
                        }
                      }
                    }
                    container asic-error-info {
                      description
                        "Asic Error Info";
                      uses SCHEMA-DATA-BG;
                    }
                    leaf class {
                      type xr:Cisco-ios-xr-string;
                      description
                        "Error Class";
                    }
                  }
                }
              }
              container instance-summary {
                description
                  "Summary for a specific instance";
                uses SUMMARY-DATA-BG;
              }
              leaf asic-instance {
                type uint32 {
                  range "0..256";
                }
                description
                  "asic instance";
              }
            }
          }
          container all-instances {
            description
              "All asic instance on the node";
            container all-error-path {
              description
                "Error path of all instances";
              container summary {
                description
                  "Summary of all instances errors";
                uses ASIC-SUMMARY-BG;
              }
            }
          }
          leaf asic {
            type xr:Cisco-ios-xr-string;
            description
              "Asic string";
          }
        }
      }
    }
  }
}
