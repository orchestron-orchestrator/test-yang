submodule Cisco-IOS-XR-acl-hw-oper-sub1 {
  belongs-to Cisco-IOS-XR-acl-hw-oper {
    prefix Cisco-IOS-XR-acl-hw-oper;
  }

  import ietf-inet-types {
    prefix inet;
  }
  import ietf-yang-types {
    prefix yang;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR acl-hw package operational data.

     Copyright (c) 2013-2023 by Cisco Systems, Inc.
     All rights reserved.";

  revision 2023-11-09 {
    semver:module-version "1.0.0";
    description
      "Removal of enum qos-ea in schema, CSCwh91588";
  }
  revision 2023-02-21 {
    description
      "Fixed the Traceback error CSCwe41742";
  }
  revision 2023-02-03 {
    description
      "Adding support for ACL HW schema";
  }
  revision 2019-04-05 {
    description
      "Establish semantic version baseline.";
  }
  revision 2015-11-09 {
    description
      "IOS XR 6.0 revision.";
  }

  typedef Dpa-fm-client-sh-compr-port {
    type uint32;
    description
      "Dpa fm client sh compr port";
  }

  typedef Dpa-fm-client-sh-compr-addr {
    type uint32;
    description
      "Dpa fm client sh compr addr";
  }

  typedef Dpa-fm-client-sh-ipv6-address {
    type inet:ipv6-address;
    description
      "Dpa fm client sh ipv6 address";
  }

  typedef Dpa-fm-client-sh-ipv4-address {
    type inet:ipv4-address;
    description
      "Dpa fm client sh ipv4 address";
  }

  typedef Dpa-fm-client-ipv4-addr {
    type uint32;
    description
      "Dpa fm client ipv4 addr";
  }

  typedef Dpa-fm-client-ipv6-addr-type-new {
    type inet:ipv6-address;
    description
      "Dpa fm client ipv6 addr type new";
  }

  typedef Dpa-fm-client-ipv4-addr-type-new {
    type inet:ipv4-address;
    description
      "Dpa fm client ipv4 addr type new";
  }

  typedef Dpa-fm-client-sh-addr {
    type enumeration {
      enum "ipv4" {
        description
          "IPv4";
      }
      enum "ipv6" {
        description
          "IPv6";
      }
      enum "mac" {
        description
          "Mac";
      }
    }
    description
      "Address types";
  }

  typedef Dpa-fm-grant {
    type enumeration {
      enum "permit" {
        value 1;
        description
          "Grant permit";
      }
      enum "deny" {
        value 2;
        description
          "Grant deny";
      }
    }
    description
      "ACL grant";
  }

  typedef Dpa-fm-client-sh-compr {
    type enumeration {
      enum "source-ip-prefix" {
        description
          "SRC_IP Prefix Compression";
      }
      enum "destination-ip-prefix" {
        description
          "DEST_IP prefix Compression";
      }
      enum "source-port" {
        description
          "SRC port Compression";
      }
      enum "not-applicable" {
        description
          "MAX Compression Field type";
      }
    }
    description
      "Compress Field types";
  }

  typedef Dpa-fm-client-sh-vrfy-result {
    type enumeration {
      enum "successful" {
        description
          "Successful verification";
      }
      enum "failed" {
        description
          "Failed verification";
      }
      enum "not-applicable" {
        description
          "Not applicable";
      }
    }
    description
      "Verification result";
  }

  typedef Dpa-fm-client-sh-lkup {
    type enumeration {
      enum "ipv4" {
        description
          "IPv4 Lookup";
      }
      enum "ipv6" {
        description
          "IPv6 Lookup";
      }
      enum "l2mac" {
        description
          "Layer 2 MAC Lookup";
      }
    }
    description
      "Lookup type";
  }

  grouping DPA-FM-CLIENT-SH-ENTRY-INFO {
    description
      "DPA FM CLIENT SH ENTRY INFO";
    container best-nh {
      description
        "best nh";
      uses DPA-FM-CLIENT-SH-ADDR;
    }
    leaf hits {
      type uint64;
      description
        "hits";
    }
    leaf police-accepted {
      type uint64;
      description
        "police accepted";
    }
    leaf police-dropped {
      type uint64;
      description
        "police dropped";
    }
    leaf byte-hits {
      type uint64;
      description
        "byte hits";
    }
    leaf byte-police-accepted {
      type uint64;
      description
        "byte police accepted";
    }
    leaf byte-police-dropped {
      type uint64;
      description
        "byte police dropped";
    }
    leaf has-abf {
      type boolean;
      description
        "has abf";
    }
    leaf vrf-name {
      type string {
        length "0..32";
      }
      description
        "vrf name";
    }
  }

  grouping DPA-FM-CLIENT-SH-ADDRESS {
    description
      "DPA FM CLIENT SH ADDRESS";
    leaf address-type {
      type Dpa-fm-client-sh-addr;
      description
        "AddressType";
    }
    leaf ipv4-address {
      when "../address-type = 'ipv4'" {
        description
          "../AddressType = 'IPv4'";
      }
      type Dpa-fm-client-sh-ipv4-address;
      description
        "IPv4 address type";
    }
    leaf ipv6-address {
      when "../address-type = 'ipv6'" {
        description
          "../AddressType = 'IPv6'";
      }
      type Dpa-fm-client-sh-ipv6-address;
      description
        "IPv6 address type";
    }
  }

  grouping DPA-FM-CLIENT-SH-TCAM-DATA {
    description
      "TCAM entry information";
    container tcam-common-key-field-value {
      description
        "TCAM common key field values";
      uses DPA-FM-CLIENT-SH-PARAMS;
    }
    container tcam-common-key-mask {
      description
        "TCAM common key field masks";
      uses DPA-FM-CLIENT-SH-PARAMS;
    }
    container source-ip-address {
      description
        "Source IP address";
      uses DPA-FM-CLIENT-SH-ADDRESS;
    }
    container destination-ip-address {
      description
        "Destination IP address";
      uses DPA-FM-CLIENT-SH-ADDRESS;
    }
    container source-ip-address-mask {
      description
        "Source IP address mask";
      uses DPA-FM-CLIENT-SH-ADDRESS;
    }
    container destination-ip-address-mask {
      description
        "Destination IP address mask";
      uses DPA-FM-CLIENT-SH-ADDRESS;
    }
    leaf entry-index {
      type uint32;
      description
        "Entry index for current entry";
    }
    leaf tcam-entry-id {
      type uint32;
      description
        "TCAM entry ID";
    }
    leaf tcam-entry-hw-priority {
      type uint32;
      description
        "TCAM HW priority";
    }
    leaf source-port-range-set {
      type boolean;
      description
        "ASIC range ID used for L4 source port range";
    }
    leaf destination-port-range-set {
      type boolean;
      description
        "ASIC range ID used for L4 destination port range";
    }
    leaf src-port-end {
      type uint16;
      description
        "End of range for L4 source port range";
    }
    leaf dest-port-end {
      type uint16;
      description
        "End of range for L4 destination port range";
    }
    leaf acl-compressed {
      type boolean;
      description
        "ACL compression  applied or not";
    }
    leaf compressed-src-ip-ace-encoding {
      type Dpa-fm-client-sh-compr-addr;
      description
        "Source IP ACE compression encoding ";
    }
    leaf compressed-src-ip-ace-encoding-mask {
      type Dpa-fm-client-sh-compr-addr;
      description
        "Source IP ACE compression encoding mask";
    }
    leaf compressed-dst-ip-ace-encoding {
      type Dpa-fm-client-sh-compr-addr;
      description
        "Destination IP ACE compression encoding ";
    }
    leaf compressed-dst-ip-ace-encoding-mask {
      type Dpa-fm-client-sh-compr-addr;
      description
        "Destination IP ACE compression encoding mask";
    }
    leaf compressed-src-port-ace-encoding {
      type Dpa-fm-client-sh-compr-port;
      description
        "Source port ACE compression encoding";
    }
    leaf compressed-src-port-ace-encoding-mask {
      type Dpa-fm-client-sh-compr-port;
      description
        "Source port ACE compression encoding mask";
    }
    leaf compressed-dst-port-ace-encoding {
      type Dpa-fm-client-sh-compr-addr;
      description
        "Destination port ACE compression encoding";
    }
    leaf compressed-dst-port-ace-encoding-mask {
      type Dpa-fm-client-sh-compr-addr;
      description
        "Destination port ACE compression encoding mask";
    }
    list udf-entry {
      key "udf-name";
      description
        "UDFEntry";
      uses DPA-FM-CLIENT-SH-UDF;
    }
  }

  grouping DPA-FM-CLIENT-SH-ACE-RESULT {
    description
      "Pfilter ACE hardware result";
    leaf acl-id {
      type uint32;
      description
        "ACL ID";
    }
    leaf grant {
      type Dpa-fm-grant;
      description
        "Either permit or deny";
    }
    leaf next-hop-enabled {
      type uint32;
      description
        "Next hop enabled/disabled";
    }
    leaf next-hop-fec-id {
      type uint32;
      description
        "Next hop FEC ID";
    }
    leaf next-hop-vrf-id {
      type uint32;
      description
        "Next hop VRF ID";
    }
    leaf hits {
      type uint64;
      description
        "Number of TCAM hits";
    }
    leaf police-accepted {
      type uint64;
      description
        "Number of Policer accepted pkts";
    }
    leaf police-dropped {
      type uint64;
      description
        "Number of Policer dropped pkts";
    }
    leaf bytes-hits {
      type uint64;
      units "byte";
      description
        "Number of TCAM hit bytes";
    }
    leaf bytes-police-accepted {
      type uint64;
      units "byte";
      description
        "Number of Policer accepted bytes";
    }
    leaf bytes-police-dropped {
      type uint64;
      units "byte";
      description
        "Number of Policer dropped bytes";
    }
    leaf logging-enabled {
      type boolean;
      description
        "Logging enable or disabled";
    }
    leaf police-acl {
      type boolean;
      description
        "Police enable or disabled";
    }
  }

  grouping DPA-FM-CLIENT-SH-ENTRY-BRIEF {
    description
      "Pfilter ACE hardware brief";
    container ace-result {
      description
        "ACE result data";
      uses DPA-FM-CLIENT-SH-ACE-RESULT;
    }
    leaf sequence {
      type uint32;
      description
        "ACE sequence number";
    }
    leaf ace-total-tcam-entries {
      type uint32;
      description
        "ACE total number of TCAM entries";
    }
  }

  grouping DPA-FM-CLIENT-SH-ENTRY-DETAIL {
    description
      "Pfilter ACE hardware detail";
    container ace-brief {
      description
        "ACE brief information";
      uses DPA-FM-CLIENT-SH-ENTRY-BRIEF;
    }
    list tcam-entry {
      key "entry-index tcam-entry-id";
      description
        "ACE TCAM detail information";
      uses DPA-FM-CLIENT-SH-TCAM-DATA;
    }
  }

  grouping DPA-FM-CLIENT-SH-ENTRY-DETAIL-PER-NPU-ARRAY {
    description
      "Pfilter ACL ACE details per NPU";
    leaf npu-id {
      type uint32;
      description
        "NPU ID";
    }
    list npu-ace-detail {
      description
        "ACE breif information array";
      uses DPA-FM-CLIENT-SH-ENTRY-DETAIL;
    }
  }

  grouping DPA-FM-CLIENT-SH-ENTRY-DETAIL-ARRAY {
    description
      "Pfilter ACL ACE details across all NPUs";
    list ace-detail {
      key "npu-id";
      description
        "ACE breif information array";
      uses DPA-FM-CLIENT-SH-ENTRY-DETAIL-PER-NPU-ARRAY;
    }
  }

  grouping DPA-FM-CLIENT-SH-ENTRY-IMPLICIT-DETAIL-ARRAY {
    description
      "Pfilter ACL implicit details across all NPUs";
    list acl-implicit {
      description
        "ACL implicit entries";
      uses DPA-FM-CLIENT-SH-ENTRY-DETAIL-ARRAY;
    }
  }

  grouping DPA-FM-CLIENT-SH-UDF {
    description
      "DPA FM CLIENT SH UDF";
    leaf udf-name {
      type string {
        length "0..17";
      }
      description
        "UDF Name";
    }
    leaf udf-value {
      type uint32;
      description
        "UDF Value";
    }
    leaf udf-mask {
      type uint32;
      description
        "UDF MASK";
    }
  }

  grouping DPA-FM-CLIENT-IPV6-ADDR-TYPE {
    description
      "DPA FM CLIENT IPV6 ADDR TYPE";
    leaf addr {
      type yang:hex-string;
      description
        "addr";
    }
  }

  grouping DPA-FM-CLIENT-SH-ADDR {
    description
      "DPA FM CLIENT SH ADDR";
    container addr6 {
      when "../address-type = 'ipv6'" {
        description
          "../AddressType = 'IPv6'";
      }
      description
        "IPv6 address";
      uses DPA-FM-CLIENT-IPV6-ADDR-TYPE;
    }
    container mac {
      when "../address-type = 'mac'" {
        description
          "../AddressType = 'Mac'";
      }
      description
        "MAC address";
      uses DPA-FM-CLIENT-MAC-ADDR-TYPE;
    }
    leaf address-type {
      type Dpa-fm-client-sh-addr;
      description
        "AddressType";
    }
    leaf addr {
      when "../address-type = 'ipv4'" {
        description
          "../AddressType = 'IPv4'";
      }
      type Dpa-fm-client-ipv4-addr;
      description
        "IPv4 address";
    }
  }

  grouping DPA-FM-CLIENT-SH-PARAMS {
    description
      "Parameters included in dpa entry";
    leaf tcp-flags {
      type uint8;
      description
        "tcp flags";
    }
    leaf proto {
      type uint8;
      description
        "proto";
    }
    leaf dscp {
      type uint8;
      description
        "dscp";
    }
    leaf exp {
      type uint8;
      description
        "exp";
    }
    leaf ttl-match {
      type uint8;
      description
        "ttl match";
    }
    leaf src-port {
      type uint16;
      description
        "src port";
    }
    leaf dst-port {
      type uint16;
      description
        "dst port";
    }
    leaf is-frag {
      type uint8;
      description
        "is frag";
    }
  }

  grouping DPA-FM-CLIENT-SH-ENTRY-DATA {
    description
      "DPA FM CLIENT SH ENTRY DATA";
    container params {
      description
        "params";
      uses DPA-FM-CLIENT-SH-PARAMS;
    }
    container params-mask {
      description
        "params mask";
      uses DPA-FM-CLIENT-SH-PARAMS;
    }
    container src-addr {
      description
        "src addr";
      uses DPA-FM-CLIENT-SH-ADDR;
    }
    container dst-addr {
      description
        "dst addr";
      uses DPA-FM-CLIENT-SH-ADDR;
    }
    container src-addr-mask {
      description
        "src addr mask";
      uses DPA-FM-CLIENT-SH-ADDR;
    }
    container dst-addr-mask {
      description
        "dst addr mask";
      uses DPA-FM-CLIENT-SH-ADDR;
    }
    leaf entry-index {
      type uint32;
      description
        "entry index";
    }
    leaf dpa-handle {
      type uint32;
      description
        "dpa handle";
    }
    leaf src-port-range-set {
      type boolean;
      description
        "src port range set";
    }
    leaf dst-port-range-set {
      type boolean;
      description
        "dst port range set";
    }
    leaf src-port-end {
      type uint16;
      description
        "src port end";
    }
    leaf dst-port-end {
      type uint16;
      description
        "dst port end";
    }
    leaf vlan {
      type uint16;
      description
        "vlan";
    }
    leaf vlan-mask {
      type uint16;
      description
        "vlan mask";
    }
    leaf cos {
      type uint8;
      description
        "cos";
    }
    leaf dei {
      type uint8;
      description
        "dei";
    }
    leaf ethertype {
      type uint16;
      description
        "ethertype";
    }
    leaf ethertype-mask {
      type uint16;
      description
        "ethertype mask";
    }
    leaf udf-count {
      type uint8;
      description
        "udf count";
    }
    list udf-entry {
      key "udf-name";
      max-elements 8;
      description
        "UDFEntry";
      uses DPA-FM-CLIENT-SH-UDF;
    }
  }

  grouping DPA-FM-CLIENT-SH-QOS-RESULT {
    description
      "DPA FM CLIENT SH QOS RESULT";
    leaf valid-bits {
      type uint8;
      description
        "valid bits";
    }
    leaf class-index {
      type uint8;
      description
        "class index";
    }
    leaf qos-group {
      type uint8;
      description
        "qos group";
    }
    leaf discard-class {
      type uint8;
      description
        "discard class";
    }
    leaf dscp {
      type uint8;
      description
        "dscp";
    }
    leaf exp {
      type uint8;
      description
        "exp";
    }
    leaf exp-imp {
      type uint8;
      description
        "exp imp";
    }
    leaf inner-cos {
      type uint8;
      description
        "inner cos";
    }
    leaf outer-cos {
      type uint8;
      description
        "outer cos";
    }
    leaf dei {
      type uint8;
      description
        "dei";
    }
  }

  grouping DPA-FM-CLIENT-MAC-ADDR-TYPE {
    description
      "DPA FM CLIENT MAC ADDR TYPE";
    leaf addr {
      type yang:hex-string;
      description
        "addr";
    }
  }

  grouping DPA-FM-CLIENT-SH-ADDR-NEW {
    description
      "DPA FM CLIENT SH ADDR NEW";
    container mac {
      when "../address-type = 'mac'" {
        description
          "../AddressType = 'Mac'";
      }
      description
        "MAC address";
      uses DPA-FM-CLIENT-MAC-ADDR-TYPE;
    }
    leaf address-type {
      type Dpa-fm-client-sh-addr;
      description
        "AddressType";
    }
    leaf addr4 {
      when "../address-type = 'ipv4'" {
        description
          "../AddressType = 'IPv4'";
      }
      type Dpa-fm-client-ipv4-addr-type-new;
      description
        "IPv4 address";
    }
    leaf addr6 {
      when "../address-type = 'ipv6'" {
        description
          "../AddressType = 'IPv6'";
      }
      type Dpa-fm-client-ipv6-addr-type-new;
      description
        "IPv6 address";
    }
  }

  grouping DPA-FM-CLIENT-SH-PFILTER-ENTRY {
    description
      "DPA FM CLIENT SH PFILTER ENTRY";
    container abf-best-nh {
      description
        "abf best nh";
      uses DPA-FM-CLIENT-SH-ADDR-NEW;
    }
    leaf acl-id {
      type uint32;
      description
        "acl id";
    }
    leaf police-acl {
      type boolean;
      description
        "police acl";
    }
    leaf ace-action {
      type Dpa-fm-grant;
      description
        "ace action";
    }
    leaf abf-action {
      type uint32;
      description
        "abf action";
    }
    leaf abf-fec-id {
      type uint32;
      description
        "abf fec id";
    }
    leaf abf-vrf-id {
      type uint32;
      description
        "abf vrf id";
    }
    leaf abf-vrf-name {
      type string {
        length "0..32";
      }
      description
        "abf vrf name";
    }
    leaf hits {
      type uint64;
      description
        "hits";
    }
    leaf byte-hits {
      type uint64;
      description
        "byte hits";
    }
    leaf policer-rate {
      type uint32;
      description
        "policer rate";
    }
    leaf hw-policer-rate {
      type uint32;
      description
        "hw policer rate";
    }
    leaf police-accepted {
      type uint64;
      description
        "police accepted";
    }
    leaf police-dropped {
      type uint64;
      description
        "police dropped";
    }
    leaf byte-police-accepted {
      type uint64;
      description
        "byte police accepted";
    }
    leaf byte-police-dropped {
      type uint64;
      description
        "byte police dropped";
    }
    leaf stats-valid {
      type boolean;
      description
        "stats valid";
    }
    leaf log-enabled {
      type boolean;
      description
        "log enabled";
    }
    leaf ttl-set {
      type uint16;
      description
        "ttl set";
    }
  }

  grouping DPA-FM-CLIENT-SH-ENTRY {
    description
      "DPA FM CLIENT SH ENTRY";
    container acl-result {
      description
        "acl result";
      uses DPA-FM-CLIENT-SH-PFILTER-ENTRY;
    }
    container qos-result {
      description
        "qos result";
      uses DPA-FM-CLIENT-SH-QOS-RESULT;
    }
    leaf npu-id {
      type uint8;
      description
        "npu id";
    }
    leaf sequence {
      type uint32;
      description
        "sequence";
    }
    leaf num-dpa-entries {
      type uint32;
      description
        "num dpa entries";
    }
    list dpa-entry {
      key "entry-index";
      description
        "dpa entry";
      uses DPA-FM-CLIENT-SH-ENTRY-DATA;
    }
  }

  grouping DPA-FM-CLIENT-SH-ENTRY-ARRAY {
    description
      "DPA FM CLIENT SH ENTRY ARRAY";
    list ace-array {
      key "npu-id sequence";
      description
        "ace array";
      uses DPA-FM-CLIENT-SH-ENTRY;
    }
  }

  grouping DPA-FM-VERIFY-REGION-PREFIX-DATA {
    description
      "Verification prefix encoding summary  information";
    leaf compression-field-type {
      type Dpa-fm-client-sh-compr;
      description
        "Compressed encoding field type";
    }
    leaf entries-verified {
      type uint32;
      description
        "Total number of entries verified";
    }
    leaf total-tcam-entries {
      type uint32;
      description
        "Total numver TCAM entries to verify";
    }
    leaf rc {
      type uint32;
      description
        "Verification return code";
    }
    leaf verification-result {
      type Dpa-fm-client-sh-vrfy-result;
      description
        "Verification Success/Failure";
    }
  }

  grouping DPA-FM-VERIFY-REGION-ACE-DATA {
    description
      "Verification summary  information";
    leaf entries-verified {
      type uint32;
      description
        "Total number of entries verified";
    }
    leaf total-tcam-entries {
      type uint32;
      description
        "Total numver TCAM entries to verify";
    }
    leaf current-seq-number-verified {
      type uint32;
      description
        "Current ACE sequence number verified";
    }
    leaf current-ace-index {
      type uint32;
      description
        "Current TCAM index of ACE verified";
    }
    leaf rc {
      type uint32;
      description
        "Verification return code";
    }
    leaf verification-result {
      type Dpa-fm-client-sh-vrfy-result;
      description
        "Verification Success/Failure";
    }
  }

  grouping DPA-FM-VERIFY-INTF-DATA {
    description
      "Interface information of ACL attachment";
    leaf inferface-handle {
      type uint32;
      description
        "Interface Handle";
    }
    leaf interface-name {
      type string {
        length "0..80";
      }
      description
        "Interface Name";
    }
  }

  grouping DPA-FM-CLIENT-VERIFY-DATA {
    description
      "TCAM verification information for an ACL";
    container ace-data {
      description
        "Verified ACE Infomration";
      uses DPA-FM-VERIFY-REGION-ACE-DATA;
    }
    leaf npu-id {
      type uint8;
      description
        "NPU ID for ACL TCAM entries";
    }
    leaf acl-id {
      type uint32;
      description
        "ACL ID for ACL TCAM verification";
    }
    leaf number-of-intf-shared {
      type uint32;
      description
        "Number of INTFs for ACL attachment";
    }
    leaf total-aces {
      type uint32;
      description
        "Total number ACEs in ACL";
    }
    leaf compression-level {
      type uint32;
      description
        "ACL compression level";
    }
    leaf acl-compressed {
      type boolean;
      description
        "ACL compression  applied or not";
    }
    leaf look-up-type {
      type Dpa-fm-client-sh-lkup;
      description
        "ACL lookup type IPv4/IPv6/L2";
    }
    list interface-info {
      description
        "Interface Information";
      uses DPA-FM-VERIFY-INTF-DATA;
    }
    list prefix-compression-info {
      max-elements 3;
      description
        "Compression Information";
      uses DPA-FM-VERIFY-REGION-PREFIX-DATA;
    }
  }

  grouping DPA-FM-CLIENT-VERIFY-REGION-ARRAY {
    description
      "TCAM verification information per ACL attachment";
    list verify-data {
      key "npu-id acl-id";
      description
        "Verification Data per TCAM region";
      uses DPA-FM-CLIENT-VERIFY-DATA;
    }
  }

  grouping DPA-FM-CLIENT-VERIFY-NPU-ARRAY {
    description
      "TCAM verification information on all NPUs";
    list npu-verify-data {
      description
        "Verification Data per NPU";
      uses DPA-FM-CLIENT-VERIFY-REGION-ARRAY;
    }
  }
}
