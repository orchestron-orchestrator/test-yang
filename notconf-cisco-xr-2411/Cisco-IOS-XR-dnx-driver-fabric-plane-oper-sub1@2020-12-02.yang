submodule Cisco-IOS-XR-dnx-driver-fabric-plane-oper-sub1 {
  belongs-to Cisco-IOS-XR-dnx-driver-fabric-plane-oper {
    prefix Cisco-IOS-XR-dnx-driver-fabric-plane-oper;
  }

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR dnx-driver-fabric-plane package operational data.

     Copyright (c) 2013-2020 by Cisco Systems, Inc.
     All rights reserved.";

  revision 2020-12-02 {
    semver:module-version "1.1.0";
    description
      "added Ucast_lost_cells,Mcast_lost_cells and Asic_internal_drops for fsdb_plane_stats_info bag.";
  }
  revision 2019-04-05 {
    semver:module-version "1.0.1";
    description
      "Establish semantic version baseline.";
  }
  revision 2015-11-09 {
    description
      "IOS XR 6.0 revision.";
  }

  typedef Fsdb-plane-mode {
    type enumeration {
      enum "plane-mode-unknown" {
        value 0;
        description
          "plane mode unknown";
      }
      enum "plane-mode-sc" {
        value 1;
        description
          "plane mode sc";
      }
      enum "plane-mode-b2b" {
        value 2;
        description
          "plane mode b2b";
      }
      enum "plane-mode-mc" {
        value 3;
        description
          "plane mode mc";
      }
      enum "plane-mode-folded" {
        value 4;
        description
          "plane mode folded";
      }
    }
    description
      "FSDB plane mode enum";
  }

  typedef Fsdb-plane-admin-state {
    type enumeration {
      enum "plane-state-admin-up" {
        value 0;
        description
          "plane state admin up";
      }
      enum "plane-state-admin-down" {
        value 1;
        description
          "plane state admin down";
      }
    }
    description
      "FSDB Plane admin state enum";
  }

  typedef Fsdb-plane-oper-state {
    type enumeration {
      enum "plane-state-oper-up" {
        value 0;
        description
          "plane state oper up";
      }
      enum "plane-state-oper-down" {
        value 1;
        description
          "plane state oper down";
      }
      enum "plane-state-oper-mcast-down" {
        value 2;
        description
          "plane state oper mcast down";
      }
    }
    description
      "FSDB plane oper state enum";
  }

  grouping FABRIC-PLANE-INFO-DETAIL {
    description
      "Plane information in Detail";
    leaf plane-id {
      type uint32;
      description
        "Unique Identifier for Plane";
    }
    leaf plane-oper-status {
      type Fsdb-plane-oper-state;
      description
        "PlaneOperStatus";
    }
    leaf plane-admin-status {
      type Fsdb-plane-admin-state;
      description
        "PlaneAdminStatus";
    }
    leaf plane-mode {
      type Fsdb-plane-mode;
      description
        "Plane Mode Configuration";
    }
    leaf bundles {
      type uint16;
      description
        "Total number of bundles";
    }
    leaf down-bundles {
      type uint16;
      description
        "Total down bundles";
    }
    leaf plane-up-down-count {
      type uint32;
      description
        "counter of UP<->DOWN plane state transition";
    }
    leaf up-multicast-count {
      type uint32;
      description
        "counter of UP<->MCAST plane state transition";
    }
    leaf ppu-state {
      type string;
      description
        "Plane PPU State";
    }
  }

  grouping FSDBB-PLANE-INFO-XML {
    description
      "Fabric Plane Information for XML";
    list detail-plane-info {
      description
        "list of all elements in plane bag";
      uses FABRIC-PLANE-INFO-DETAIL;
    }
  }

  grouping FABRIC-PLANE-STATS-INFO {
    description
      "FABRIC PLANE STATS INFO";
    leaf plane-id {
      type uint32;
      description
        "Unique Identifier for Plane";
    }
    leaf rx-data-cells {
      type uint64;
      description
        "RxDataCells";
    }
    leaf tx-data-cells {
      type uint64;
      description
        "TxDataCells";
    }
    leaf rx-correctable-error-cells {
      type uint32;
      description
        "RxCorrectableErrorCells";
    }
    leaf rx-un-correctable-error-cells {
      type uint32;
      description
        "RxUnCorrectableErrorCells";
    }
    leaf rx-parity-error-cells {
      type uint32;
      description
        "RxParityErrorCells";
    }
    leaf ucast-lost-cells {
      type uint32;
      description
        "Ucast lost cells";
    }
    leaf mcast-lost-cells {
      type uint32;
      description
        "Mcast lost cells";
    }
    leaf asic-internal-drops {
      type uint32;
      description
        "Asic internal drops";
    }
  }

  grouping FSDBB-PLANE-STATS-INFO-XML {
    description
      "Fabric Plane Statistics Information for XML";
    list plane-stats-info {
      description
        "Statistics data of plane";
      uses FABRIC-PLANE-STATS-INFO;
    }
  }
}
