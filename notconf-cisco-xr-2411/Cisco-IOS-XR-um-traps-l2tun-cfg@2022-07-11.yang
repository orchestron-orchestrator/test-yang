module Cisco-IOS-XR-um-traps-l2tun-cfg {
  namespace "http://cisco.com/ns/yang/Cisco-IOS-XR-um-traps-l2tun-cfg";
  prefix um-traps-l2tun-cfg;

  import Cisco-IOS-XR-um-snmp-server-cfg {
    prefix a1;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR traps-l2tun package configuration.

     This YANG module augments the
     modules with configuration data.

     Copyright (c) 2020-2022 by Cisco Systems, Inc.
     All rights reserved.";

  revision 2022-07-11 {
    semver:module-version "1.0.0";
    description
      "Added missing description statement to nodes";
  }
  revision 2020-03-23 {
    semver:module-version "1.0.0";
    description
      "Initial release";
  }

  augment "/a1:snmp-server/a1:traps" {
    description
      "This augment extends snmp-server traps nodes
       configuration";
    container l2tun {
      description
        "Enable L2TUN traps";
      container sessions {
        presence "Indicates a sessions node is configured.";
        description
          "Enable L2TUN sessions traps";
      }
      container pseudowire {
        description
          "Enable L2TUN pseudowire status traps";
        container status {
          presence "Indicates a status node is configured.";
          description
            "Enable traps for L2TPv3 PW status";
        }
      }
      container tunnel-up {
        presence "Indicates a tunnel-up node is configured.";
        description
          "Enable L2TUN tunnel UP traps";
      }
      container tunnel-down {
        presence "Indicates a tunnel-down node is configured.";
        description
          "Enable L2TUN tunnel DOWN traps";
      }
    }
  }
}
