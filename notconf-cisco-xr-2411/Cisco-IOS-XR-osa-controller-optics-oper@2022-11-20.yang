module Cisco-IOS-XR-osa-controller-optics-oper {
  namespace "http://cisco.com/ns/yang/Cisco-IOS-XR-osa-controller-optics-oper";
  prefix osa-controller-optics-oper;

  import Cisco-IOS-XR-types {
    prefix xr;
  }
  import cisco-semver {
    prefix semver;
  }

  include Cisco-IOS-XR-osa-controller-optics-oper-sub1 {
    revision-date 2022-11-20;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR osa-controller-optics package operational data.

     This module contains definitions
     for the following management objects:
       osa-controller-operational-info: OSA controller Operational
         Information

     Copyright (c) 2013-2022 by Cisco Systems, Inc.
     All rights reserved.";

  revision 2022-11-20 {
    semver:module-version "1.2.0";
    description
      "Added new CLI-trunk-rates till 1200g";
  }
  revision 2020-05-18 {
    semver:module-version "1.1.0";
    description
      "Initial Revision.";
  }
  revision 2019-04-05 {
    semver:module-version "1.1.0";
    description
      "Establish semantic version baseline.";
  }
  revision 2019-02-16 {
    description
      "Initial Revision.";
  }
  revision 2015-11-09 {
    description
      "IOS XR 6.0 revision.";
  }

  container osa-controller-operational-info {
    config false;
    description
      "OSA controller Operational Information";
    container osa-optics-controller {
      description
        "Optics Controller";
      container controller-names {
        description
          "OSA optics controller Table";
        list controller-name {
          key "name";
          description
            "Controller Name";
          container bps-baud-rate-info {
            description
              "Fetch all BPS-GBD Capability Info";
            uses OSA-OPTICS-BPS-GBD-CAPAB-B;
          }
          leaf name {
            type xr:Interface-name;
            description
              "Controller name";
          }
        }
      }
    }
  }
}
