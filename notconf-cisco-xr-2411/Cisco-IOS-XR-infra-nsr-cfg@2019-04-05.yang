module Cisco-IOS-XR-infra-nsr-cfg {
  namespace "http://cisco.com/ns/yang/Cisco-IOS-XR-infra-nsr-cfg";
  prefix infra-nsr-cfg;

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR infra-nsr package configuration.

     This module contains definitions
     for the following management objects:
       nsr: NSR global configuration

     Copyright (c) 2013-2019 by Cisco Systems, Inc.
     All rights reserved.";

  revision 2019-04-05 {
    semver:module-version "1.0.1";
    description
      "Establish semantic version baseline.";
  }
  revision 2017-06-27 {
    description
      "IOS XR 6.4.1 revision.";
  }
  revision 2015-11-09 {
    description
      "IOS XR 6.0 revision.";
  }

  container nsr {
    description
      "NSR global configuration";
    container process-failure {
      description
        "Recovery action for process failures on active
         RP/DRP";
      leaf switchover {
        type empty;
        description
          "Enable RP/DRP switchover on process failures";
      }
    }
  }
}
