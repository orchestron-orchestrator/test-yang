module Cisco-IOS-XR-asr9k-fc-xbar-oper {
  namespace "http://cisco.com/ns/yang/Cisco-IOS-XR-asr9k-fc-xbar-oper";
  prefix asr9k-fc-xbar-oper;

  import Cisco-IOS-XR-types {
    prefix xr;
  }
  import cisco-semver {
    prefix semver;
  }

  include Cisco-IOS-XR-asr9k-fc-xbar-oper-sub3 {
    revision-date 2019-04-05;
  }
  include Cisco-IOS-XR-asr9k-fc-xbar-oper-sub2 {
    revision-date 2019-04-05;
  }
  include Cisco-IOS-XR-asr9k-fc-xbar-oper-sub1 {
    revision-date 2019-04-05;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR asr9k-fc-xbar package operational data.

     This module contains definitions
     for the following management objects:
       cross-bar-spine-stats: Crossbar stats operational data

     Copyright (c) 2013-2019 by Cisco Systems, Inc.
     All rights reserved.";

  revision 2019-04-05 {
    semver:module-version "1.0.0";
    description
      "Establish semantic version baseline.";
  }
  revision 2015-11-09 {
    description
      "IOS XR 6.0 revision.";
  }

  container cross-bar-spine-stats {
    config false;
    description
      "Crossbar stats operational data";
    list spine-table {
      key "spine-num";
      description
        "Table of stats information for FC cards";
      container bandwidth-utils-stats {
        description
          "Table of packet stats for Bandwidth Utils";
        list bandwidth-utils-stat {
          key "asic-id";
          description
            "Stats information for Bandwidth Utils Counter";
          leaf asic-id {
            type xr:Cisco-ios-xr-string;
            description
              "Asic ID";
          }
          uses XBAR-EDM-BANDWIDTH-UTILS;
        }
      }
      container skb-stats {
        description
          "Table of packet stats for SKB";
        list skb-stat {
          description
            "Stats information for a particular asic type
             and port";
          leaf asic-id {
            type xr:Cisco-ios-xr-string;
            description
              "Asic ID";
          }
          leaf port {
            type xr:Cisco-ios-xr-string;
            description
              "Port";
          }
          uses XBAR-EDM-SKB-PORT-STATS;
        }
      }
      container sm15-stats {
        description
          "Table of packet stats for SM15";
        list sm15-stat {
          description
            "Stats information for a particular asic type
             and port";
          leaf asic-id {
            type xr:Cisco-ios-xr-string;
            description
              "Asic ID";
          }
          leaf port {
            type xr:Cisco-ios-xr-string;
            description
              "Port";
          }
          uses XBAR-EDM-SM15-PORT-STATS;
        }
      }
      leaf spine-num {
        type xr:Cisco-ios-xr-string;
        description
          "Name of the Spine xbar_spX";
      }
    }
  }
}
