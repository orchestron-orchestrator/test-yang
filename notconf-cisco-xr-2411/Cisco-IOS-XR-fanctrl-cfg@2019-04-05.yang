module Cisco-IOS-XR-fanctrl-cfg {
  namespace "http://cisco.com/ns/yang/Cisco-IOS-XR-fanctrl-cfg";
  prefix fanctrl-cfg;

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR fanctrl package configuration.

     This module contains definitions
     for the following management objects:
       fan-control: EnvMon fan control logic options

     Copyright (c) 2013-2019 by Cisco Systems, Inc.
     All rights reserved.";

  revision 2019-04-05 {
    semver:module-version "1.0.0";
    description
      "Establish semantic version baseline.";
  }
  revision 2015-11-09 {
    description
      "IOS XR 6.0 revision.";
  }

  container fan-control {
    description
      "EnvMon fan control logic options";
    container fan-speed-set {
      description
        "Control fan speed setting";
      leaf disable {
        type boolean;
        default "false";
        description
          "Enable or disable fan speed setting";
      }
    }
  }
}
