module Cisco-IOS-XR-subscriber-accounting-cfg {
  namespace "http://cisco.com/ns/yang/Cisco-IOS-XR-subscriber-accounting-cfg";
  prefix subscriber-accounting-cfg;

  import Cisco-IOS-XR-types {
    prefix xr;
  }
  import cisco-semver {
    prefix semver;
  }
  import Cisco-IOS-XR-subscriber-infra-tmplmgr-cfg {
    prefix a1;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR subscriber-accounting package configuration.

     This module contains definitions
     for the following management objects:
       subscriber-accounting: Subscriber Configuration

     This YANG module augments the
       Cisco-IOS-XR-subscriber-infra-tmplmgr-cfg
     module with configuration data.

     Copyright (c) 2013-2019 by Cisco Systems, Inc.
     All rights reserved.";

  revision 2019-04-05 {
    semver:module-version "1.0.1";
    description
      "Establish semantic version baseline.";
  }
  revision 2017-09-07 {
    description
      "Fixed type translation error.";
  }
  revision 2015-11-09 {
    description
      "IOS XR 6.0 revision.";
  }

  grouping ACCOUNTING {
    description
      "Common node of subscriber-service, ip-subscriber";
    container accounting {
      description
        "Subscriber accounting dynamic-template commands";
      container service-accounting {
        description
          "Subscriber accounting service accounting";
        leaf method-list-name {
          type string;
          description
            "Service accounting method list name";
        }
        leaf accounting-interim-interval {
          type uint32;
          units "minute";
          description
            "Accounting interim interval in minutes";
        }
      }
      container session {
        description
          "Subscriber accounting session accounting";
        leaf method-list-name {
          type string;
          description
            "Session accounting method list name";
        }
        leaf periodic-interval {
          type uint32;
          units "minute";
          description
            "Interim accounting interval in minutes";
        }
        leaf dual-stack-delay {
          type uint32;
          units "second";
          description
            "Dual stack wait delay in seconds";
        }
        leaf hold-acct-start {
          type enumeration {
            enum "ipv6-prefix-delegation" {
              value 3;
              description
                "Based on ipv6 delegated prefix";
            }
          }
          description
            "Hold Accounting start based on IA_PD";
        }
      }
      container idle-timeout {
        description
          "Subscriber accounting idle timeout";
        leaf timeout-value {
          type uint32 {
            range "60..4320000";
          }
          units "second";
          description
            "Idle timeout value in seconds";
        }
        leaf threshold {
          type uint32 {
            range "1..10000";
          }
          description
            "Threshold in minute(s) per packet";
        }
        leaf direction {
          type string;
          description
            "Idle timeout traffic direction";
        }
      }
      leaf monitor-feature {
        type string;
        description
          "Subscriber monitor feature";
      }
      leaf prepaid-feature {
        type string;
        description
          "Subscriber accounting prepaid feature";
      }
    }
  }

  container subscriber-accounting {
    description
      "Subscriber Configuration";
    container prepaid-configurations {
      description
        "Subscriber Prepaid Feature Configuration";
      list prepaid-configuration {
        key "prepaid-config-name";
        description
          "Prepaid configuration name or default";
        leaf password {
          type string {
            length "1..64";
          }
          description
            "Password to be used when placing prepaid
             (re)authorization requests";
        }
        leaf volume-threshold {
          type uint32;
          description
            "Threshold at which to send prepaid volume
             quota request";
        }
        leaf accounting-method-list {
          type string {
            length "1..64";
          }
          description
            "Method list to be used when placing prepaid
             accounting requests";
        }
        leaf time-hold {
          type uint32;
          description
            "Idle Threshold for which prepaid quota is
             valid";
        }
        leaf author-method-list {
          type string {
            length "1..64";
          }
          description
            "Method list to be used when placing prepaid
             (re)authorization requests";
        }
        leaf traffic-direction {
          type string;
          description
            "Prepaid quota traffic direction";
        }
        leaf time-threshold {
          type uint32;
          description
            "Threshold at which to send prepaid time quota
             request";
        }
        leaf time-valid {
          type uint32;
          description
            "Threshold for which prepaid quota is valid";
        }
        leaf prepaid-config-name {
          type xr:Cisco-ios-xr-string {
            length "1..64";
          }
          description
            "Prepaid configuration name or default";
        }
      }
    }
  }

  augment "/a1:dynamic-template/a1:ppps/a1:ppp" {
    description
      "This augment extends the configuration data of
       'Cisco-IOS-XR-subscriber-infra-tmplmgr-cfg'";
    container accounting {
      description
        "Subscriber accounting dynamic-template commands";
      container idle-timeout {
        description
          "Subscriber accounting idle timeout";
        leaf timeout-value {
          type uint32 {
            range "60..4320000";
          }
          description
            "Idle timeout value in seconds";
        }
        leaf threshold {
          type uint32 {
            range "1..10000";
          }
          description
            "Threshold in minute(s) per packet";
        }
        leaf direction {
          type string;
          description
            "Idle timeout traffic direction";
        }
      }
      container session {
        description
          "Subscriber accounting session accounting";
        leaf method-list-name {
          type string;
          description
            "Session accounting method list name";
        }
        leaf periodic-interval {
          type uint32;
          description
            "Interim accounting interval in minutes";
        }
        leaf dual-stack-delay {
          type uint32;
          description
            "Dual stack wait delay in seconds";
        }
        leaf hold-acct-start {
          type enumeration {
            enum "ipv6-prefix-delegation" {
              value 3;
              description
                "Based on ipv6 delegated prefix";
            }
          }
          description
            "Hold Accounting start based on IA_PD";
        }
      }
      container service-accounting {
        description
          "Subscriber accounting service accounting";
        leaf method-list-name {
          type string;
          description
            "Service accounting method list name";
        }
        leaf accounting-interim-interval {
          type uint32;
          description
            "Accounting interim interval in minutes";
        }
      }
      leaf monitor-feature {
        type string;
        description
          "Subscriber monitor feature";
      }
      leaf prepaid-feature {
        type string;
        description
          "Subscriber accounting prepaid feature";
      }
    }
  }
  augment "/a1:dynamic-template/a1:ip-subscribers/a1:ip-subscriber" {
    description
      "This augment extends the configuration data of
       'Cisco-IOS-XR-subscriber-infra-tmplmgr-cfg'";
    uses ACCOUNTING;
  }
  augment "/a1:dynamic-template/a1:subscriber-services/a1:subscriber-service" {
    description
      "This augment extends the configuration data of
       'Cisco-IOS-XR-subscriber-infra-tmplmgr-cfg'";
    uses ACCOUNTING;
  }
}
