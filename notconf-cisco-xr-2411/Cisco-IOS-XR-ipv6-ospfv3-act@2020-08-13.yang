module Cisco-IOS-XR-ipv6-ospfv3-act {
  namespace "http://cisco.com/ns/yang/Cisco-IOS-XR-ipv6-ospfv3-act";
  prefix ospfv3-act;

  import cisco-semver {
    prefix semver;
  }
  import Cisco-IOS-XR-types {
    prefix xr;
  }
  import ietf-inet-types {
    prefix inet;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR IPv6 OSPFv3 action package configuration.

     Copyright (c) 2016-2020, 2022 by Cisco Systems, Inc.
     All rights reserved.";

  revision 2020-08-13 {
    semver:module-version "1.1.0";
    description
      "Added xr-task name ospf to restrict unlimited permission";
  }
  revision 2019-10-01 {
    semver:module-version "1.1.0";
    description
      "Made changes to be RFC6087 compliant";
  }
  revision 2019-04-05 {
    semver:module-version "1.0.0";
    description
      "Establish semantic version baseline.";
  }
  revision 2016-09-14 {
    description
      "IOS XR 6.2.1 revision.";
  }

  grouping OSPFv3-STAT-ATTRIBUTES {
    description
      "OSPFv3 Stat Attributes";
    leaf process {
      type empty;
      description
        "Reset OSPFv3 process";
    }
    leaf redistribution {
      type empty;
      description
        "Clear OSPFv3 route redistrbution";
    }
    leaf route {
      type empty;
      description
        "Clear OSPFv3 route table";
    }
    container stats {
      description
        "OSPFv3 counters and statistics";
      leaf spf {
        type empty;
        description
          "SPF statistics";
      }
      leaf prefix-priority {
        type empty;
        description
          "SPF Prefix Priority statistics";
      }
      container neighbor {
        description
          "Neighbor statistics per interface or neighbor id";
        leaf neighbor-id {
          type inet:ipv4-address;
          description
            "Neighbor ID";
        }
        container interface {
          description
            "Interface";
          leaf interface-name {
            type xr:Interface-name;
            description
              "OSPFv3 interface statistics";
          }
        }
      }
    }
  }

  rpc clear-ospfv3-routes {
    description
      "Clear OSPFv3 route table";

    input {
      container instance {
        description
          "Clear data from OSPFv3 instance";
        leaf instance-identifier {
          type string;
          description
            "OSPFv3 process instance identifier";
        }
      }
      leaf route {
        type empty;
        mandatory true;
        description
          "Clear OSPFv3 route table";
      }
    }
  }
  rpc clear-ospfv3-redistribution {
    description
      "Clear OSPFv3 route redistribution";

    input {
      container instance {
        description
          "Clear data from OSPFv3 instance";
        leaf instance-identifier {
          type string;
          description
            "OSPFv3 process instance identifier";
        }
      }
      leaf redistribution {
        type empty;
        mandatory true;
        description
          "Clear OSPFv3 route redistribution";
      }
    }
  }
  rpc clear-ospfv3-process {
    description
      "Clear (reset) OSPFv3 Process";

    input {
      container instance {
        description
          "Clear data from OSPFv3 instance";
        leaf instance-identifier {
          type string;
          description
            "OSPFv3 process instance identifier";
        }
      }
      leaf process {
        type empty;
        mandatory true;
        description
          "Reset OSPFv3 process";
      }
    }
  }
  rpc clear-ospfv3-statistics-neighbor {
    description
      "Clear OSPFv3 neighbor statistics per interface or neighbor id";

    input {
      container instance {
        description
          "Clear data from OSPFv3 instance";
        leaf instance-identifier {
          type string;
          description
            "OSPFv3 process instance identifier";
        }
      }
      container neighbor {
        description
          "Neighbor";
        leaf neighbor-id {
          type inet:ipv4-address;
          description
            "Neighbor ID";
        }
        leaf interface-name {
          type xr:Interface-name;
          description
            "Interface";
        }
      }
    }
  }
  rpc clear-ospfv3-statistics {
    description
      "Clear OSPFv3 counters and statistics";

    input {
      container instance {
        description
          "Clear data from OSPFv3 instance";
        leaf instance-identifier {
          type string;
          description
            "OSPFv3 process instance identifier";
        }
      }
      leaf prefix-priority {
        type empty;
        description
          "All OSPFv3 counters and statistics";
      }
      leaf spf {
        type empty;
        description
          "SPF statistics";
      }
      leaf neighbor {
        type empty;
        description
          "Neighbor statistics per neighbor id";
      }
    }
  }
  rpc clear-ospfv3-instance-vrf {
    description
      "Clear one or more non-default OSPFv3 VRFs in process";

    input {
      container instance {
        description
          "OSPFv3 instance name";
        leaf instance-identifier {
          type string;
          mandatory true;
          description
            "OSPFv3 process instance identifier";
        }
        container vrf {
          description
            "Clear one or more non-default OSPFv3 VRFs in process";
          leaf vrf-name {
            type string;
            mandatory true;
            description
              "OSPFv3 VRF name";
          }
          uses OSPFv3-STAT-ATTRIBUTES;
        }
        container all {
          description
            "Clear all non-default OSPFv3 VRFs";
          uses OSPFv3-STAT-ATTRIBUTES;
        }
        container all-inclusive {
          description
            "Clear all non-default and default OSPFv3 VRFs";
          uses OSPFv3-STAT-ATTRIBUTES;
        }
      }
    }
  }
}
