module Cisco-IOS-XR-fretta-dnx-lpts-oper {
  namespace "http://cisco.com/ns/yang/Cisco-IOS-XR-fretta-dnx-lpts-oper";
  prefix fretta-dnx-lpts-oper;

  import Cisco-IOS-XR-types {
    prefix xr;
  }
  import cisco-semver {
    prefix semver;
  }

  include Cisco-IOS-XR-fretta-dnx-lpts-oper-sub1 {
    revision-date 2019-04-05;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR fretta-dnx-lpts package operational data.

     This module contains definitions
     for the following management objects:
       platform-lptsp-ifib: Fretta platform ifib operational data

     Copyright (c) 2013-2019 by Cisco Systems, Inc.
     All rights reserved.";

  revision 2019-04-05 {
    semver:module-version "1.0.0";
    description
      "Establish semantic version baseline.";
  }
  revision 2015-11-09 {
    description
      "IOS XR 6.0 revision.";
  }

  container platform-lptsp-ifib {
    config false;
    description
      "Fretta platform ifib operational data ";
    container nodes {
      description
        "List of nodes with platform specific lpts
         operation data";
      list node {
        key "node-name";
        description
          "Node with platform specific lpts data";
        container entries {
          description
            "stats for LC";
          list entry {
            description
              "Data for single pre-ifib entry or all entries";
            leaf region {
              type uint32;
              description
                "Region";
            }
            leaf start-index {
              type uint32;
              description
                "Start Index";
            }
            leaf num-entries {
              type uint32;
              description
                "Number of entries";
            }
            leaf l4-protocol {
              type uint32;
              description
                "L4 Protocol";
            }
            leaf debug-option {
              type uint32;
              description
                "Debug option";
            }
            uses PL-PIFIB-SHOW-ENTRY;
          }
        }
        container polices {
          description
            "policer info for LC";
          list police {
            description
              "Data for single policer entry";
            leaf dm-index {
              type uint32;
              description
                "DM index";
            }
            leaf flow-type {
              type uint32;
              description
                "Flow type";
            }
            leaf npu-id {
              type uint32;
              description
                "NPU Identifier";
            }
            uses PL-PIFIB-POLICER-INFO;
          }
        }
        leaf node-name {
          type xr:Node-id;
          description
            "Node name";
        }
      }
    }
  }
}
