module Cisco-IOS-XR-um-yang-server-cfg {
  namespace "http://cisco.com/ns/yang/Cisco-IOS-XR-um-yang-server-cfg";
  prefix um-yang-server-cfg;

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR yang-server package configuration.

     This YANG module augments the
     modules with configuration data.

     Copyright (c) 2020-2022 by Cisco Systems, Inc.
     All rights reserved.";

  revision 2021-04-28 {
    semver:module-version "1.0.0";
    description
      "Initial release";
  }

  container yang-server {
    description
      "yang-server configuration commands";
    leaf module-set {
      type enumeration {
        enum "UM-preferred" {
          value 1;
          description
            "This set use as many unified native models as applicable";
        }
        enum "XR-only" {
          value 2;
          description
            "This set uses only old native models";
        }
      }
      description
        "Use only the yang modules listed in a module-set.";
    }
  }
}
