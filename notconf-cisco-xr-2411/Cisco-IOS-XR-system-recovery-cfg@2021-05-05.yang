module Cisco-IOS-XR-system-recovery-cfg {
  namespace "http://cisco.com/ns/yang/Cisco-IOS-XR-system-recovery-cfg";
  prefix system-recovery-cfg;

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR system-recovery package configuration.

     This module contains definitions
     for the following management objects:
       system-recovery: System Recovery configurations

     Copyright (c) 2013-2021 by Cisco Systems, Inc.
     All rights reserved.";

  revision 2021-05-05 {
    semver:module-version "1.0.0";
    description
      "Added support for system recovery";
  }
  revision 2019-04-05 {
    description
      "Establish semantic version baseline.";
  }
  revision 2015-11-09 {
    description
      "IOS XR 6.0 revision.";
  }

  container system-recovery {
    description
      "System Recovery configurations";
    leaf enable {
      type empty;
      description
        "Enable System Recovery";
    }
  }
}
