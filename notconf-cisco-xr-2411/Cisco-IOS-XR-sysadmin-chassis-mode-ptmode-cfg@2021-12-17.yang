module Cisco-IOS-XR-sysadmin-chassis-mode-ptmode-cfg {
  namespace "http://www.cisco.com/ns/yang/Cisco-IOS-XR-sysadmin-chassis-mode-ptmode-cfg";
  prefix chassis-mode;

  import cisco-semver {
    prefix semver;
  }

  organization
    "Cisco Systems Inc.";
  contact
    "Cisco Systems, Inc.
     Customer Service

     Postal: 170 West Tasman Drive
     San Jose, CA 95134

     Tel: +1 800 553-NETS

     E-mail: cs-yang@cisco.com";
  description
    "This module contains a YANG
     definitions for Cisco IOS-XR SysAdmin chassis-mode
     configuration.

     This module holds chassis PT-mode data.

     Copyright (c) 2021-2020 by Cisco Systems, Inc.
     All rights reserved.";

  revision 2021-12-17 {
    semver:module-version "1.0.0";
    description
      "Changing the cli option.";
  }
  revision 2021-10-29 {
    description
      "Initial revision.";
  }

  grouping mode {
    description
      "chassis mode";
    container config {
      description
        "chassis-mode config mode";
      uses global-chassis-config-group;
    }
  }

  grouping global-chassis-config-group {
    description
      "Enable/Disable 100G IM support on slot 6 & 8";
    leaf pass-through-mode {
      type enumeration {
        enum "disable";
        enum "enable";
      }
      default "disable";
      config true;
      description
        "Pass through mode; disabled by default";
    }
  }

  container chassis-mode {
    description
      "chassis-mode container";
    uses mode;
  }
}
