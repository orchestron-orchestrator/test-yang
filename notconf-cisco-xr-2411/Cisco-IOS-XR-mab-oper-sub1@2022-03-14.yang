submodule Cisco-IOS-XR-mab-oper-sub1 {
  belongs-to Cisco-IOS-XR-mab-oper {
    prefix Cisco-IOS-XR-mab-oper;
  }

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR mab package operational data.

     Copyright (c) 2013-2022 by Cisco Systems, Inc.
     All rights reserved.";

  revision 2022-03-14 {
    semver:module-version "1.0.0";
    description
      "Added fields to display AuthRetry Timeout and timer status";
  }
  revision 2021-11-23 {
    description
      "Added field to display Held Timeout and timer status";
  }
  revision 2021-10-11 {
    description
      "New Oper Model added to support MAC Authentication Bypass feature";
  }
  revision 2019-04-05 {
    description
      "Establish semantic version baseline.";
  }
  revision 2015-11-09 {
    description
      "IOS XR 6.0 revision.";
  }

  grouping MAB-CLIENT-INFO {
    description
      "MAB CLIENT INFO";
    leaf mac {
      type string;
      description
        "formatted MAC Address";
    }
    leaf mab-sm-state {
      type string;
      description
        "MAB SM State";
    }
    leaf time-to-next-reauth {
      type string;
      description
        "Remaining time for next reauthentication";
    }
    leaf auth-method {
      type string;
      description
        "Authentication method";
    }
    leaf reauth-timeout {
      type string;
      units "second";
      description
        "Reauth timeout in seconds";
    }
    leaf port-status {
      type string;
      description
        "Auth Client Port Status";
    }
    leaf last-authen-time {
      type string;
      description
        "Time of previous authentication";
    }
    leaf programming-status {
      type string;
      description
        "Programming Status";
    }
    leaf held-timeout {
      type string;
      units "second";
      description
        "Held timeout in seconds and Timer status";
    }
    leaf retry-timeout {
      type string;
      units "second";
      description
        "Auth Retry timeout in seconds and Timer status";
    }
    leaf time-to-next-auth-retry {
      type string;
      description
        "Remaining time for next authentication retry";
    }
  }

  grouping MAB-INTERFACE-DETAIL {
    description
      "MAB INTERFACE DETAIL";
    leaf interface-name {
      type string;
      description
        "Interface Display name ";
    }
    leaf interface-handle {
      type string;
      description
        "Interface handle";
    }
    leaf host-mode {
      type string;
      description
        "Host Mode";
    }
    leaf port-control {
      type string;
      description
        "Port Control";
    }
    leaf punt-state {
      type string;
      description
        "Punt State";
    }
    leaf punt-summary {
      type string;
      description
        "Punt Summary";
    }
    list client {
      description
        "MAB client list";
      uses MAB-CLIENT-INFO;
    }
  }

  grouping MAB-CLIENT-AUTH-STATS {
    description
      "MAB CLIENT AUTH STATS";
    leaf success-count {
      type uint32;
      description
        "Success count";
    }
    leaf fail-count {
      type uint32;
      description
        "Fail count";
    }
    leaf timeout-count {
      type uint32;
      description
        "Timeout count";
    }
    leaf aaa-unreach-count {
      type uint32;
      description
        "AAA Unreachable count";
    }
  }

  grouping MAB-CLIENT-STATS {
    description
      "MAB CLIENT STATS";
    container auth-stats {
      description
        "MAB Client authentication statistics";
      uses MAB-CLIENT-AUTH-STATS;
    }
    leaf mac-addr {
      type string;
      description
        "MAB Client MAC Address";
    }
  }

  grouping MAB-PC-STATS {
    description
      "MAB PC STATS";
    leaf enable-success {
      type uint32;
      description
        "EnableSuccess";
    }
    leaf enable-fail {
      type uint32;
      description
        "EnableFail";
    }
    leaf add-client-success {
      type uint32;
      description
        "Add Client Success";
    }
    leaf add-client-fail {
      type uint32;
      description
        "AddClientFail";
    }
    leaf remove-client-success {
      type uint32;
      description
        "Remove Client Success";
    }
    leaf remove-client-fail {
      type uint32;
      description
        "RemoveClientFail";
    }
    leaf update-success {
      type uint32;
      description
        "UpdateSuccess";
    }
    leaf update-fail {
      type uint32;
      description
        "UpdateFail";
    }
    leaf punt-start-success {
      type uint32;
      description
        "PuntStartSuccess";
    }
    leaf punt-start-fail {
      type uint32;
      description
        "PuntStartFail";
    }
    leaf punt-stop-success {
      type uint32;
      description
        "PuntStopSuccess";
    }
    leaf punt-stop-fail {
      type uint32;
      description
        "PuntStopFail";
    }
  }

  grouping MAB-ML-STATS {
    description
      "MAB ML STATS";
    leaf rx-total {
      type uint32;
      description
        "RxTotal";
    }
    leaf rx-no-src-mac {
      type uint32;
      description
        "RxNoSrcMac";
    }
    leaf rx-no-idb {
      type uint32;
      description
        "RxNoIdb";
    }
  }

  grouping MAB-IF-STATISTICS {
    description
      "MAB IF STATISTICS";
    container mac-learning-stats {
      description
        "MAC Learning Statistics";
      uses MAB-ML-STATS;
    }
    container port-control-stats {
      description
        "Port Control Statistics";
      uses MAB-PC-STATS;
    }
    leaf interface-name {
      type string;
      description
        "Interface Display name";
    }
    list client-stat {
      description
        "MAB Clients statistics";
      uses MAB-CLIENT-STATS;
    }
  }

  grouping MAB-NODE-STATISTICS {
    description
      "MAB NODE STATISTICS";
    leaf node-name {
      type string;
      description
        "Node Name";
    }
    leaf rx-total {
      type uint32;
      description
        "RxTotal";
    }
    leaf rx-no-src-mac {
      type uint32;
      description
        "RxNoSrcMac";
    }
    leaf rx-no-idb {
      type uint32;
      description
        "RxNoIdb";
    }
  }
}
