module Cisco-IOS-XR-controller-odg-oper {
  namespace "http://cisco.com/ns/yang/Cisco-IOS-XR-controller-odg-oper";
  prefix controller-odg-oper;

  import Cisco-IOS-XR-types {
    prefix xr;
  }
  import cisco-semver {
    prefix semver;
  }

  include Cisco-IOS-XR-controller-odg-oper-sub2 {
    revision-date 2019-04-05;
  }
  include Cisco-IOS-XR-controller-odg-oper-sub1 {
    revision-date 2019-04-05;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR controller-odg package operational data.

     This module contains definitions
     for the following management objects:
       odg: ODG operational data

     Copyright (c) 2013-2019 by Cisco Systems, Inc.
     All rights reserved.";

  revision 2019-04-05 {
    semver:module-version "1.0.0";
    description
      "Establish semantic version baseline.";
  }
  revision 2015-11-09 {
    description
      "IOS XR 6.0 revision.";
  }

  container odg {
    config false;
    description
      "ODG operational data";
    container controllers {
      description
        "All ODG Port operational data";
      list controller {
        key "odg-name";
        description
          "ODG Port operational data";
        container info {
          description
            "ODG port operational data";
          uses ODG-EDM-PORT-INFO;
        }
        container protection-info {
          description
            "ODG port Protection information";
          uses ODG-ODU-EDM-PORT-INFO;
        }
        leaf odg-name {
          type xr:Cisco-ios-xr-string;
          description
            "The name of the Odu-Group-MP name";
        }
      }
    }
  }
}
