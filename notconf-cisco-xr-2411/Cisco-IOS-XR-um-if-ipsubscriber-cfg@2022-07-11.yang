module Cisco-IOS-XR-um-if-ipsubscriber-cfg {
  namespace "http://cisco.com/ns/yang/Cisco-IOS-XR-um-if-ipsubscriber-cfg";
  prefix um-if-ipsubscriber-cfg;

  import Cisco-IOS-XR-um-interface-cfg {
    prefix a1;
  }
  import tailf-common {
    prefix tailf;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR if-ipsubscriber package configuration.

     This YANG module augments the
     modules with configuration data.

     Copyright (c) 2020-2022 by Cisco Systems, Inc.
     All rights reserved.";

  revision 2022-07-11 {
    semver:module-version "1.1.0";
    description
      "Added missing description statement to nodes";
  }
  revision 2020-03-23 {
    semver:module-version "1.0.0";
    description
      "Initial release";
  }

  grouping IF-BODY {
    description
      "Grouping for interface";
    container ipsubscriber {
      description
        "Configure IP Subscriber settings";
      container ipv4 {
        description
          "Enable IPv4 Subscriber";
        container l2-connected {
          description
            "Enable L2-connected IP Subscriber";
          container initiator {
            description
              "Configure IP Subscriber initiator";
            container dhcp {
              presence "Indicates a dhcp node is configured.";
              description
                "Configure DHCP as first-sign-of-life protocol for IPv4 subscriber";
            }
            container unclassified-source {
              presence "Indicates a unclassified-source node is configured.";
              description
                "Configure unclassified packets as first-sign-of-life for IPv4 subscriber";
              container address-unique {
                presence "Indicates a address-unique node is configured.";
                description
                  "Check for subscriber IP uniqueness during first-sign-of-life";
              }
            }
          }
        }
        container routed {
          description
            "Enable Routed IP Subscriber";
          container initiator {
            description
              "Configure IP Subscriber initiator";
            container dhcp {
              presence "Indicates a dhcp node is configured.";
              description
                "Configure DHCP as first-sign-of-life protocol for IPv4 subscriber";
            }
            container unclassified-ip {
              presence "Indicates a unclassified-ip node is configured.";
              description
                "Configure unclassified packets as first-sign-of-life for IPv4 subscriber";
            }
            container dhcp-snoop {
              presence "Indicates a dhcp-snoop node is configured.";
              description
                "Configure DHCP to pass the packets to server for IPv4 subscriber";
            }
          }
        }
      }
      container ipv6 {
        description
          "Enable IPv6 Subscriber";
        container l2-connected {
          description
            "Enable L2-connected IPv6 Subscriber";
          container initiator {
            description
              "Configure IPv6 Subscriber initiator";
            container dhcp {
              presence "Indicates a dhcp node is configured.";
              description
                "Configure DHCP as first-sign-of-life protocol for IPv6 subscriber";
            }
          }
        }
        container routed {
          description
            "Enable Routed IPv6 Subscriber";
          container initiator {
            description
              "Configure IPv6 Subscriber initiator";
            container unclassified-ip {
              presence "Indicates a unclassified-ip node is configured.";
              description
                "Configure unclassified packets as first-sign-of-life for IPv6 subscriber";
              leaf prefix-len {
                type uint32 {
                  range "1..127" {
                    description
                      "Configure Prefix Length of IPv6 Subscriber";
                  }
                }
                description
                  "Configure Prefix Length of IPv6 Subscriber";
              }
            }
            container dhcp {
              presence "Indicates a dhcp node is configured.";
              description
                "Configure DHCP as first-sign-of-life protocol for IPv6 subscriber";
              leaf prefix-len {
                type uint32 {
                  range "1..127" {
                    description
                      "Configure Prefix Length of IPv6 Subscriber";
                  }
                }
                description
                  "Configure Prefix Length of IPv6 Subscriber";
              }
            }
            container dhcp-snoop {
              presence "Indicates a dhcp-snoop node is configured.";
              description
                "Configure DHCP to pass the packets to server for IPv6 subscriber";
              leaf prefix-len {
                type uint32 {
                  range "1..127" {
                    description
                      "Configure Prefix Length of IPv6 Subscriber";
                  }
                }
                description
                  "Configure Prefix Length of IPv6 Subscriber";
              }
            }
          }
        }
      }
      leaf subscriber-templates {
        type uint32 {
          range "1..10" {
            description
              "Max templates on this access interface";
          }
        }
        description
          "Enable subscriber templates on this access interface";
      }
      container interface {
        presence "Indicates a interface node is configured.";
        description
          "Enable IP Static subscriber";
      }
      container session-limit {
        description
          "Limit number of IP subscriber sessions ";
        container unclassified-source {
          description
            "Limit IP subscribers for unclassified sources";
          leaf per-vlan {
            type uint32 {
              range "1..4294967295" {
                description
                  "Session limit";
              }
            }
            description
              "Limit the per VLAN subscribers created";
          }
        }
        container total {
          description
            "Limit IP subscribers for all sources";
          leaf per-vlan {
            type uint32 {
              range "1..4294967295" {
                description
                  "Session limit";
              }
            }
            description
              "Limit the per VLAN subscribers created";
          }
        }
      }
    }
  }

  augment "/a1:interfaces/a1:interface" {
    when "a1:interface-name[starts-with(text(),'PW-Ether')] or a1:interface-name[starts-with(text(),'GigabitEthernet')] or a1:interface-name[starts-with(text(),'TenGigE')] or a1:interface-name[starts-with(text(),'FortyGigE')] or a1:interface-name[starts-with(text(),'HundredGigE')] or a1:interface-name[starts-with(text(),'TwoHundredGigE')] or a1:interface-name[starts-with(text(),'FourHundredGigE')] or a1:interface-name[starts-with(text(),'EightHundredGigE')] or a1:interface-name[starts-with(text(),'TwentyFiveGigE')] or a1:interface-name[starts-with(text(),'FiftyGigE')] or a1:interface-name[starts-with(text(),'Bundle-Ether')]" {
      tailf:dependency "a1:interface-name";
    }
    description
      "This augment extends active nodes configuration";
    uses IF-BODY;
  }
  augment "/a1:interfaces/a1:interface-preconfigure" {
    when "a1:interface-name[starts-with(text(),'PW-Ether')] or a1:interface-name[starts-with(text(),'GigabitEthernet')] or a1:interface-name[starts-with(text(),'TenGigE')] or a1:interface-name[starts-with(text(),'FortyGigE')] or a1:interface-name[starts-with(text(),'HundredGigE')] or a1:interface-name[starts-with(text(),'TwoHundredGigE')] or a1:interface-name[starts-with(text(),'FourHundredGigE')] or a1:interface-name[starts-with(text(),'EightHundredGigE')] or a1:interface-name[starts-with(text(),'TwentyFiveGigE')] or a1:interface-name[starts-with(text(),'FiftyGigE')] or a1:interface-name[starts-with(text(),'Bundle-Ether')]" {
      tailf:dependency "a1:interface-name";
    }
    description
      "This augment extends preconfigured nodes
       configuration";
    uses IF-BODY;
  }
}
