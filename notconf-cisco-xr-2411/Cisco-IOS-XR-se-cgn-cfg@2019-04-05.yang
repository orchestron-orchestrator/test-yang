module Cisco-IOS-XR-se-cgn-cfg {
  namespace "http://cisco.com/ns/yang/Cisco-IOS-XR-se-cgn-cfg";
  prefix se-cgn-cfg;

  import Cisco-IOS-XR-types {
    prefix xr;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR se-cgn package configuration.

     This module contains definitions
     for the following management objects:
       cgns: Table of CGN
       cgv6s: Table of CGv6

     Copyright (c) 2013-2019 by Cisco Systems, Inc.
     All rights reserved.";

  revision 2019-04-05 {
    semver:module-version "1.0.0";
    description
      "Establish semantic version baseline.";
  }
  revision 2015-11-09 {
    description
      "IOS XR 6.0 revision.";
  }

  grouping SERVICE-INTF {
    description
      "Common node of cgn, cgv6";
    container service-intf {
      description
        "Interface on which service to be started";
      container active-intf-names {
        description
          "Table of ActiveIntfName";
        list active-intf-name {
          key "active-intf-name";
          description
            "Interface name";
          leaf active-intf-name {
            type xr:Interface-name;
            description
              "Interface through which CGN policy to be
               downloaded";
          }
        }
      }
    }
  }

  container cgns {
    description
      "Table of CGN";
    list cgn {
      key "cgn-name";
      description
        "CGN Configurations";
      container protocol {
        description
          "Select a protocol";
        container icmp {
          description
            "ICMP protocol";
          leaf rate-limit {
            type uint32 {
              range "0..65472";
            }
            description
              "ICMP rate limit per second.On CRS or C12k
               ,rate limit should be multiple of 64 and less
               than 65472.On ASR9k, rate limit should be
               multiple of 48 and less than 49104. ";
          }
        }
      }
      container service-node {
        presence "Indicates a service-node node is configured.";
        description
          "Location on which service to be started";
        leaf active-node-name {
          type xr:Node-id;
          mandatory true;
          description
            "Location on which active cgn to be
             instantiated";
        }
        leaf standby-node-name {
          type xr:Node-id;
          description
            "Location on which standby cgn to be
             instantiated";
        }
      }
      container service-type {
        description
          "Select a service to configure";
      }
      leaf cgn-name {
        type xr:Cisco-ios-xr-string {
          length "1..24";
        }
        description
          "Name of the CGN";
      }
      uses SERVICE-INTF;
    }
  }
  container cgv6s {
    description
      "Table of CGv6";
    list cgv6 {
      key "cgv6-name";
      description
        "CGv6 Configurations";
      container cgv6-service-type {
        description
          "Select a service to configure";
      }
      container service-node {
        presence "Indicates a service-node node is configured.";
        description
          "Location on which service to be started";
        leaf active-node-name {
          type xr:Node-id;
          mandatory true;
          description
            "Location on which active cgn to be
             instantiated";
        }
        leaf standby-node-name {
          type xr:Node-id;
          description
            "Location on which standby cgn to be
             instantiated";
        }
      }
      leaf cgv6-name {
        type xr:Cisco-ios-xr-string {
          length "1..24";
        }
        description
          "Name of the CGv6";
      }
      uses SERVICE-INTF;
    }
  }
}
