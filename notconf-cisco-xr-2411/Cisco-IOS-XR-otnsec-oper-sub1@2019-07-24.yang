submodule Cisco-IOS-XR-otnsec-oper-sub1 {
  belongs-to Cisco-IOS-XR-otnsec-oper {
    prefix Cisco-IOS-XR-otnsec-oper;
  }

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR otnsec package operational data.

     Copyright (c) 2013-2019 by Cisco Systems, Inc.
     All rights reserved.";

  revision 2019-07-24 {
    semver:module-version "1.1.0";
    description
      "Addition for leaf 'Time to Rekey' to display the key expiry time";
  }
  revision 2019-04-05 {
    semver:module-version "1.0.0";
    description
      "Establish semantic version baseline.";
  }
  revision 2018-11-10 {
    description
      "Initial Operational Schema Support";
  }
  revision 2015-11-09 {
    description
      "IOS XR 6.0 revision.";
  }

  typedef Security-policy {
    type enumeration {
      enum "should-secure" {
        value 0;
        description
          "Should Secure";
      }
      enum "must-secure" {
        value 1;
        description
          "Must Secure";
      }
    }
    description
      "security policy";
  }

  typedef Cipher-suite {
    type enumeration {
      enum "aes-gcm-256" {
        value 0;
        description
          "AES GCM 256";
      }
      enum "aes-gcm-128" {
        value 1;
        description
          "AES GCM 128";
      }
    }
    description
      "cipher suite";
  }

  typedef Session-state {
    type enumeration {
      enum "init" {
        value 0;
        description
          "INIT";
      }
      enum "pending" {
        value 1;
        description
          "PENDING";
      }
      enum "secured" {
        value 2;
        description
          "SECURED";
      }
      enum "rekeying" {
        value 3;
        description
          "REKEYING";
      }
    }
    description
      "session state";
  }

  grouping OTNSEC-EDM-SUMMARY {
    description
      "otnsec summary bag";
    leaf source-ip {
      type string;
      description
        "Source IP Address";
    }
    leaf destination-ip {
      type string;
      description
        "Destination IP Address";
    }
    leaf session-state {
      type Session-state;
      description
        "Session State";
    }
    leaf session-id {
      type uint16;
      description
        "Session ID";
    }
  }

  grouping OTNSEC-PROGRAM-STATUS {
    description
      "otnsec programming status";
    leaf valid {
      type boolean;
      description
        "valid";
    }
    leaf spi {
      type uint64;
      description
        "spi";
    }
    leaf bn {
      type uint64;
      description
        "bn";
    }
    leaf install-time {
      type string;
      description
        "install time";
    }
  }

  grouping OTNSEC-EDM-DETAIL {
    description
      "otnsec details bag";
    leaf source-ip {
      type string;
      description
        "Source IP Address";
    }
    leaf destination-ip {
      type string;
      description
        "Destination IP Address";
    }
    leaf session-state {
      type Session-state;
      description
        "Session State";
    }
    leaf session-id {
      type uint16;
      description
        "Session ID";
    }
    leaf ik-ev2-profile {
      type string;
      description
        "IKEv2 Profile";
    }
    leaf otnsec-policy {
      type string;
      description
        "IKEv2 Profile";
    }
    leaf rekey-interval {
      type uint32;
      description
        "Rekey Interval";
    }
    leaf cipher-suite {
      type Cipher-suite;
      description
        "cipher suite";
    }
    leaf security-policy {
      type Security-policy;
      description
        "security policy";
    }
    leaf rekey-time {
      type uint32;
      description
        "Rekey Time";
    }
    leaf key-exipry {
      type uint64;
      description
        "Time to key expiry";
    }
    list inbound-sa {
      max-elements 4;
      description
        "Inbound SA";
      uses OTNSEC-PROGRAM-STATUS;
    }
    list outbound-sa {
      max-elements 4;
      description
        "Outbound SA";
      uses OTNSEC-PROGRAM-STATUS;
    }
  }
}
