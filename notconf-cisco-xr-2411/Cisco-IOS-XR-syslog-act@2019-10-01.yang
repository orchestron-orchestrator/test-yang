module Cisco-IOS-XR-syslog-act {
  namespace "http://cisco.com/ns/yang/Cisco-IOS-XR-syslog-act";
  prefix syslog-act;

  import cisco-semver {
    prefix semver;
  }
  import ietf-syslog-types {
    prefix log;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR action package configuration.

     This module contains definitions
     for the following management objects:
     syslog: Global Syslog messaging data

     Copyright (c) 2016-2019, 2022 by Cisco Systems, Inc.
     All rights reserved.";

  revision 2019-10-01 {
    semver:module-version "1.1.0";
    description
      "Made changes to be RFC6087 compliant";
  }
  revision 2019-04-05 {
    semver:module-version "1.0.0";
    description
      "Establish semantic version baseline.";
  }
  revision 2016-04-17 {
    description
      "IOS XR 6.1.1 revision.";
  }

  rpc logmsg {
    description
      "Log message";

    input {
      leaf severity {
        type log:severity;
        mandatory true;
        description
          "Set serverity level";
      }
      leaf message {
        type string;
        mandatory true;
        description
          "Message body.";
      }
    }
  }
}
