module Cisco-IOS-XR-Ethernet-SPAN-oper {
  namespace "http://cisco.com/ns/yang/Cisco-IOS-XR-Ethernet-SPAN-oper";
  prefix ethernet-span-oper;

  import Cisco-IOS-XR-types {
    prefix xr;
  }
  import cisco-semver {
    prefix semver;
  }
  import Cisco-IOS-XR-Ethernet-SPAN-datatypes {
    prefix dt1;
  }

  include Cisco-IOS-XR-Ethernet-SPAN-oper-sub3 {
    revision-date 2023-09-12;
  }
  include Cisco-IOS-XR-Ethernet-SPAN-oper-sub2 {
    revision-date 2023-09-12;
  }
  include Cisco-IOS-XR-Ethernet-SPAN-oper-sub1 {
    revision-date 2023-09-12;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR Ethernet-SPAN package operational data.

     This module contains definitions
     for the following management objects:
       span-monitor-session: Monitor Session operational data

     Copyright (c) 2013-2023 by Cisco Systems, Inc.
     All rights reserved.";

  revision 2023-09-12 {
    semver:module-version "5.1.0";
    description
      "Support a single MPLS ACL under SPAN attachments
       2023-07-24
         Remove support for sflow destination
       2022-09-08
         Add rate-limiting support
       2022-09-05
         Operational data for GRE tunnel interfaces
       2022-08-19
         Add sflow destination
       2022-08-01
         Add per-session mirror interval
       2022-07-13
         Add MPLS IPv4 and MPLS IPv6 ACLs under SPAN attachments
       2022-06-29
         Change Buffer Drop references to Traffic Management
       2022-06-17
         Added support for ACL merge groups
       2022-05-27
         Added support for per-session statistics.
       2022-04-13
         Added support for mirroring dropped packets
       2021-09-15
         Added support for mirror first configured on sessions
       2021-08-20
         Added support for ERSPAN session ID under GRE destinations";
  }
  revision 2021-07-19 {
    semver:module-version "5.0.0";
    description
      "Added extended range of values to mirror interval sampling
       2021-06-02
          Added support for non-default VRFs and router-id";
  }
  revision 2020-12-03 {
    semver:module-version "4.0.0";
    description
      "Added support for multiple attachments per class on an interface
       2020-09-14
           Added support for mirror rx and tx traffic to separate destinations
       2020-04-03
           Added support for bundle destinations.";
  }
  revision 2020-01-30 {
    semver:module-version "3.0.0";
    description
      "Added support for L3 IPv4 and IPv6 ACLs on a L2 ethernet SPAN session
       2019-12-12
         Added support for file format and PCAP filter expressions under file
       2019-10-02
         Added support for UDP destinations and CloudSPAN.";
  }
  revision 2019-05-12 {
    semver:module-version "2.0.0";
    description
      "Added support for file destinations.";
  }
  revision 2019-04-05 {
    semver:module-version "1.0.0";
    description
      "Establish semantic version baseline.";
  }
  revision 2015-11-09 {
    description
      "IOS XR 6.0 revision.";
  }

  container span-monitor-session {
    config false;
    description
      "Monitor Session operational data";
    container global {
      description
        "Global operational data";
      container statistics {
        description
          "Table of statistics for source interfaces";
        list statistic {
          key "session interface";
          description
            "Statistics for a particular source interface";
          leaf session {
            type dt1:Span-session-name;
            description
              "Session Name";
          }
          leaf interface {
            type xr:Interface-name;
            description
              "Interface";
          }
          uses SPAN-MA-STATISTICS-BAG;
        }
      }
      container global-sessions {
        description
          "Global Monitor Sessions table";
        list global-session {
          key "session";
          description
            "Information about a globally-configured
             monitor session";
          leaf session {
            type dt1:Span-session-name;
            description
              "Session Name";
          }
          uses SPAN-MGR-SESSION-BAG;
        }
      }
      container session-statistics {
        description
          "Table of statistics for sessions";
        list session-statistic {
          key "session";
          description
            "Statistics for a particular session";
          leaf session {
            type dt1:Span-session-name;
            description
              "Session Name";
          }
          uses SPAN-MGR-STATISTICS-BAG;
        }
      }
    }
    container nodes {
      description
        "Node table for node-specific operational data";
      list node {
        key "node";
        description
          "Node-specific data for a particular node";
        container attachments {
          description
            "Table of source interfaces configured as
             attached to a session";
          list attachment {
            key "session interface";
            description
              "Information about a particular source
               interface configured as attached to monitor
               session";
            leaf session {
              type dt1:Span-session-name;
              description
                "Session Name";
            }
            leaf interface {
              type xr:Interface-name;
              description
                "Interface";
            }
            uses SPAN-MA-ATTACHMENT-BAG;
          }
        }
        container hardware-sessions {
          description
            "Table of sessions set up in the hardware.
             When all sessions are operating correctly the
             entries in this table should match those
             entries in GlobalSessionTable that have a
             destination configured";
          list hardware-session {
            description
              "Information about a particular session that
               is set up in the hardware";
            leaf session-class {
              type dt1:Span-session-class;
              description
                "Sesssion class";
            }
            leaf session-id {
              type dt1:Span-session-id;
              description
                "Session ID";
            }
            uses SPAN-EA-SESS-BAG;
          }
        }
        container interfaces {
          description
            "Table of source interfaces set up in the
             hardware.  The entries in this table should
             match the entries in AttachmentTable when all
             sessions are operating correctly";
          list interface {
            key "interface";
            description
              "Information about a particular interface that
               is set up in the hardware";
            leaf interface {
              type xr:Interface-name;
              description
                "Interface";
            }
            uses SPAN-EA-INTF-BAG;
          }
        }
        leaf node {
          type xr:Node-id;
          description
            "Node";
        }
      }
    }
  }
}
