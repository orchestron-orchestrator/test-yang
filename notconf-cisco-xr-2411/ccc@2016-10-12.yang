module ccc {
  namespace "http://cisco.com/calvados/ccc";
  prefix ccc;

  import tailf-common {
    prefix tailf;
  }
  import Cisco-IOS-XR-sysadmin-show-trace {
    prefix show_trace;
  }

  organization
    "Cisco Systems, Inc.";
  contact
    "Cisco Systems, Inc.
     Customer Service

     Postal: 170 West Tasman Drive
     San Jose, CA 95134

     Tel: +1 800 553-NETS

     E-mail: cs-yang@cisco.com";
  description
    "This module contains definitions
     for the Calvados model objects.

     Copyright (c) 2012-2020 by Cisco Systems, Inc.
     All rights reserved.";

  revision 2016-10-12 {
    description
      "Unhide commands and configs. Moved to advanced-grp";
  }

  typedef startHexOffset {
    type string;
  }

  typedef endHexOffset {
    type string;
  }

  typedef HexOffset {
    type string;
  }

  typedef cdrNumber {
    type uint32;
  }

  typedef laneMask {
    type string;
  }

  grouping ccc-grp {
    container ccc_driver {
      uses show_trace:traceable;
      uses show-ccc-cli-group-master;
      uses show-ccc-cli-group-slave;
      uses ccc-action-group;
    }
  }

  grouping show-ccc-cli-group-master {
    uses bootflash-group;
    uses inventory-group;
    uses power-group;
    uses reset-hist-group;
    uses register-group;
    uses ejector-group;
    uses i2c-dev-group;
    uses ethernet-group;
    uses tla-dump-group;
    uses master-event-hist-group;
    uses master-oir-hist-group;
    uses master-notif-hist-group;
  }

  grouping show-ccc-cli-group-slave {
    container slave {
      uses slave-event-hist-group;
      uses slave-notif-hist-group;
      uses slave-oir-hist-group;
    }
  }

  grouping bootflash-group {
    container bootflash {
      config false;
      container info {
        config false;
        list location {
          key "location";
          leaf location {
            type string;
          }
          container bf_info {
            leaf-list bf_info_values {
              type string;
            }
          }
        }
      }
      container status {
        config false;
        list location {
          key "location";
          leaf location {
            type string;
          }
          container bf_status {
            leaf-list bf_status_values {
              type string;
            }
          }
        }
      }
      container cre_status {
        config false;
        list location {
          key "location";
          leaf location {
            type string;
          }
          container bf_status {
            leaf-list bf_status_values {
              type string;
            }
          }
        }
      }
    }
  }

  grouping master-health-group {
    container health {
      config false;
      uses health-group;
    }
  }

  grouping slave-health-group {
    container health {
      config false;
      uses health-group;
    }
  }

  grouping health-group {
    list location {
      key "location";
      leaf location {
        type string;
      }
      container health_status {
        leaf-list health_status_values {
          type string;
        }
      }
    }
  }

  grouping inventory-group {
    container inventory {
      config false;
      uses inventory-summary-group;
      uses inventory-status-group;
      uses inventory-detail-group;
    }
  }

  grouping inventory-summary-group {
    container summary {
      config false;
      list ccc_inv_summary {
        key "location";
        leaf location {
          type string;
          mandatory true;
        }
        leaf ccc_inv_PID_string {
          type string;
        }
        leaf ccc_inv_slot_number {
          type uint32;
        }
        leaf ccc_inv_serial_number {
          type string;
        }
        leaf ccc_inv_hw_version {
          type string;
        }
        leaf ccc_inv_card_state {
          type string;
        }
      }
    }
    container version {
      config false;
      list ccc_inv_version {
        key "location";
        leaf location {
          type string;
          mandatory true;
        }
        leaf ccc_inv_PID_string {
          type string;
        }
        leaf ccc_inv_ccc_version {
          type string;
        }
        leaf ccc_inv_FPGA_version {
          type string;
        }
        leaf ccc_inv_pon_version {
          type string;
        }
        leaf ccc_inv_switch_version {
          type string;
        }
      }
    }
  }

  grouping inventory-status-group {
    container status {
      config false;
      list ccc_inv_status {
        key "location";
        leaf location {
          type string;
          mandatory true;
        }
        container ccc_inv_status_list {
          leaf-list ccc_inv_status_values {
            type string;
          }
        }
      }
    }
  }

  grouping inventory-detail-group {
    container detail {
      config false;
      list ccc_inv_detail {
        key "location";
        leaf location {
          type string;
        }
        container ccc_inv_detail_list {
          leaf-list ccc_inv_detail_values {
            type string;
          }
        }
      }
    }
  }

  grouping power-group {
    container power {
      config false;
      uses ccc-master-access-group;
    }
  }

  grouping ccc-master-access-group {
    container master-access {
      config false;
      uses ccc-power-summary-group;
      uses ccc-power-detail-group;
    }
  }

  grouping ccc-power-summary-group {
    container summary {
      config false;
      list power_summary {
        key "ccc_power_location";
        leaf ccc_power_location {
          type string;
          mandatory true;
        }
        leaf card_type {
          type string;
        }
        leaf power_state {
          type string;
        }
      }
    }
  }

  grouping ccc-power-detail-group {
    container detail {
      config false;
      list location {
        key "location";
        leaf location {
          type string;
        }
        container power_details {
          leaf-list power_details_values {
            type string;
          }
        }
      }
    }
  }

  grouping reset-hist-group {
    container reset-history {
      config false;
      uses reset-hist-chip-group;
      uses reset-hist-onboard-group;
    }
  }

  grouping reset-hist-chip-group {
    container onchip {
      config false;
      list location {
        key "loc";
        leaf loc {
          type string;
        }
        leaf ccc_reset_timeofday {
          type string;
        }
        leaf ccc_reset_uptime {
          type string;
        }
        leaf ccc_hw_reset_count {
          type uint32;
        }
        list ccc_reset_entry {
          key "ccc_reset_entry";
          leaf ccc_reset_entry {
            type int32;
          }
          leaf ccc_reset_pos {
            type uint32;
          }
          leaf ccc_reset_idx {
            type uint32;
          }
          leaf ccc_reset_word0 {
            type uint32;
          }
          leaf ccc_reset_pidx {
            type uint32;
          }
          leaf ccc_reset_sor {
            type uint32;
          }
          leaf ccc_reset_sor_string {
            type string;
          }
          leaf ccc_reset_cmd {
            type uint32;
          }
          leaf ccc_reset_cmd_string {
            type string;
          }
          leaf ccc_reset_hrm {
            type uint32;
          }
          leaf ccc_reset_srm {
            type uint32;
          }
          leaf ccc_reset_hr {
            type uint32;
          }
          leaf ccc_reset_sr {
            type uint32;
          }
          leaf ccc_reset_word1 {
            type uint32;
          }
          leaf ccc_reset_date {
            type string;
          }
        }
      }
    }
  }

  grouping reset-hist-onboard-group {
    container onboard {
      config false;
      list location {
        key "loc";
        leaf loc {
          type string;
        }
        leaf ccc_reset_scratch_sig {
          type string;
        }
        leaf ccc_reset_scratch_version {
          type uint32;
        }
        leaf ccc_reset_history_sig {
          type string;
        }
        leaf ccc_reset_history_count {
          type uint32;
        }
        leaf ccc_reset_history_disp {
          type uint32;
        }
        list ccc_reset_onboard_entry {
          key "ccc_reset_onboard_entry";
          leaf ccc_reset_onboard_entry {
            type int32;
          }
          leaf ccc_reset_pos {
            type uint32;
          }
          leaf ccc_reset_idx {
            type uint32;
          }
          leaf ccc_reset_word0 {
            type uint32;
          }
          leaf ccc_reset_pidx {
            type uint32;
          }
          leaf ccc_reset_sor {
            type uint32;
          }
          leaf ccc_reset_sor_string {
            type string;
          }
          leaf ccc_reset_cmd {
            type uint32;
          }
          leaf ccc_reset_cmd_string {
            type string;
          }
          leaf ccc_reset_hrm {
            type uint32;
          }
          leaf ccc_reset_srm {
            type uint32;
          }
          leaf ccc_reset_hr {
            type uint32;
          }
          leaf ccc_reset_sr {
            type uint32;
          }
          leaf ccc_reset_word1 {
            type uint32;
          }
          leaf ccc_reset_date {
            type string;
          }
        }
      }
    }
  }

  grouping register-group {
    container register {
      config false;
      list register_location {
        key "register_location";
        config false;
        leaf register_location {
          type string;
        }
        uses ccc-block-number-group;
        uses ccc-offset-group;
        uses ccc-address-group;
      }
    }
  }

  grouping ccc-block-number-group {
    list ccc_block_number {
      key "ccc_block_num";
      config false;
      leaf ccc_block_num {
        type uint32;
      }
      leaf block_location {
        type string;
      }
      leaf ccc_block_nm {
        type string;
      }
      list ccc_register_number {
        key "index";
        leaf index {
          type uint32;
        }
        leaf ccc_register_name {
          type string;
        }
        list ccc_data {
          leaf name {
            type string;
          }
          leaf offset {
            type uint32;
          }
          leaf value {
            type uint32;
          }
        }
      }
    }
  }

  grouping ccc-offset-group {
    list ccc_offset {
      key "hex_offset";
      config false;
      leaf hex_offset {
        type HexOffset;
      }
      list ccc_reg_offset_data {
        leaf ccc_reg_off_addr {
          type uint32;
        }
        leaf reg_off_value {
          type string;
        }
      }
    }
  }

  grouping ccc-address-group {
    list ccc_address {
      key "start_hex_addr end_hex_addr";
      config false;
      leaf start_hex_addr {
        type startHexOffset;
      }
      leaf end_hex_addr {
        type endHexOffset;
      }
      list ccc_reg_range_addr_list {
        key "ccc_reg_range_addr";
        leaf ccc_reg_range_addr {
          type uint32;
        }
        list ccc_reg_data {
          leaf ccc_reg_addr {
            type uint32;
          }
          leaf reg_value {
            type string;
          }
        }
      }
    }
  }

  grouping ejector-group {
    container ejector {
      config false;
      uses ejector-status-group;
    }
  }

  grouping ejector-status-group {
    container status {
      config false;
      list ccc_ejector_status {
        key "location";
        leaf location {
          type string;
        }
        leaf ccc_is_fc_card_type {
          type boolean;
          default "false";
        }
        leaf ccc_is_lc_card_type {
          type boolean;
          default "false";
        }
        leaf ccc_is_rp_sc_card_type {
          type boolean;
          default "false";
        }
        leaf ccc_ejc_card_type {
          type uint32;
        }
        leaf ccc_ejc_platform {
          type uint32;
        }
        leaf ccc_ejc_board_type {
          type string;
        }
        leaf ccc_ejc_card_slot {
          type uint32;
        }
        leaf ccc_ejc_card_version {
          type string;
        }
        leaf ccc_ejc_board_version {
          type string;
        }
        leaf ccc_ejc_hw_version {
          type string;
        }
        leaf ccc_ejc_core_version {
          type string;
        }
        leaf ccc_ejc_pon_version {
          type string;
        }
        leaf ccc_ejc_rp_supported {
          type string;
        }
        leaf ccc_ejc_enable {
          type string;
        }
        leaf ccc_ejc_status {
          type string;
        }
        leaf ccc_ejc_rp_pex_csr {
          type string;
        }
        leaf ccc_ejc_gp_live {
          type string;
        }
        leaf ccc_ejc_gp_status {
          type string;
        }
        leaf ccc_ejc_fc_pex_csr {
          type string;
        }
        leaf ccc_ejc_fc_ejector_support {
          type string;
        }
        leaf ccc_ejc_lc_pex_csr {
          type string;
        }
        leaf ccc_ejc_lc_ejector_support {
          type string;
        }
      }
    }
  }

  grouping master-event-hist-group {
    container event-history {
      config false;
      container brief {
        config false;
        uses event-hist-group-brief;
      }
      container detail {
        config false;
        uses event-hist-group-detail;
      }
    }
  }

  grouping slave-event-hist-group {
    container event-history {
      config false;
      container brief {
        config false;
        uses event-hist-group-brief;
      }
      container detail {
        config false;
        uses event-hist-group-detail;
      }
    }
  }

  grouping event-hist-group-brief {
    list location {
      key "location";
      leaf location {
        type string;
      }
      container card_event_hist_brief {
        leaf-list card_event_hist_brief_values {
          type string;
        }
      }
    }
  }

  grouping event-hist-group-detail {
    list location {
      key "location";
      leaf location {
        type string;
      }
      container card_event_hist_detail {
        leaf-list card_event_hist_detail_values {
          type string;
        }
      }
    }
  }

  grouping master-notif-hist-group {
    container notif-history {
      config false;
      container brief {
        config false;
        uses notif-hist-group-brief;
      }
      container detail {
        config false;
        uses notif-hist-group-detail;
      }
    }
  }

  grouping slave-notif-hist-group {
    container notif-history {
      config false;
      container brief {
        config false;
        uses notif-hist-group-brief;
      }
      container detail {
        config false;
        uses notif-hist-group-detail;
      }
    }
  }

  grouping notif-hist-group-brief {
    list location {
      key "location";
      leaf location {
        type string;
      }
      container card_notif_hist_brief {
        leaf-list card_notif_hist_brief_values {
          type string;
        }
      }
    }
  }

  grouping notif-hist-group-detail {
    list location {
      key "location";
      leaf location {
        type string;
      }
      container card_notif_hist_detail {
        leaf-list card_notif_hist_detail_values {
          type string;
        }
      }
    }
  }

  grouping i2c-dev-group {
    container i2c-dev {
      config false;
      uses cpu-complex-group;
      uses io-expander-group;
      uses cdr-group;
    }
  }

  grouping cpu-complex-group {
    container cpu-complex {
      config false;
      list location {
        key "location";
        leaf location {
          type string;
        }
        container cpu_complex_detail {
          leaf-list cpu_complex_values {
            type string;
          }
        }
      }
    }
  }

  grouping io-expander-group {
    container ioexpander {
      config false;
      list location {
        key "location";
        leaf location {
          type string;
        }
        container io_exp_val {
          leaf-list io_exp_details {
            type string;
          }
        }
      }
    }
  }

  grouping cdr-group {
    container cdr {
      config false;
      uses master-cdr-group;
      uses slave-cdr-group;
    }
  }

  grouping master-cdr-group {
    container master {
      config false;
      container summary {
        config false;
        uses summary-group;
      }
      container version {
        config false;
        uses version-group;
      }
      container si_dump {
        config false;
        uses si-dump-group;
      }
      container eye_scan {
        config false;
        uses eye-scan-group;
      }
    }
  }

  grouping slave-cdr-group {
    container slave {
      config false;
      container summary {
        config false;
        uses summary-group;
      }
      container version {
        config false;
        uses version-group;
      }
      container si_dump {
        config false;
        uses si-dump-group;
      }
      container eye_scan {
        config false;
        uses eye-scan-group;
      }
    }
  }

  grouping summary-group {
    list location {
      key "location";
      leaf location {
        type string;
      }
      container cdr_status {
        leaf-list cdr_summary_status {
          type string;
        }
      }
    }
  }

  grouping version-group {
    list location {
      key "location";
      config false;
      leaf location {
        type string;
      }
      uses cdr-number-group;
    }
  }

  grouping cdr-number-group {
    list cdr_number {
      key "cdr_num";
      config false;
      leaf cdr_num {
        type cdrNumber;
        description
          "CDR number";
      }
      list cdr_version_data {
        leaf version_data {
          type string;
        }
      }
    }
  }

  grouping si-dump-group {
    list location {
      key "location";
      config false;
      leaf location {
        type string;
      }
      uses si-group;
    }
  }

  grouping si-group {
    list cdr_number {
      key "cdr_num";
      config false;
      leaf cdr_num {
        type cdrNumber;
        description
          "CDR number";
      }
      list lane {
        key "lane_mask";
        config false;
        leaf lane_mask {
          type laneMask;
          description
            "Lane mask";
        }
        list cdr_si_dump_data {
          leaf si_dump_data {
            type string;
          }
        }
      }
    }
  }

  grouping eye-scan-group {
    list location {
      key "location";
      config false;
      leaf location {
        type string;
      }
      uses cdr-eye-scan-group;
    }
  }

  grouping cdr-eye-scan-group {
    list cdr_number {
      key "cdr_num";
      config false;
      leaf cdr_num {
        type cdrNumber;
        description
          "CDR number";
      }
      list lane {
        key "lane_mask";
        config false;
        leaf lane_mask {
          type laneMask;
          description
            "Lane mask";
        }
        list cdr_eye_scan_data {
          leaf eye_scan_data {
            type string;
          }
        }
      }
    }
  }

  grouping ccc-action-group {
    container action {
      config false;
      container register {
        config false;
        list location {
          tailf:action "write" {
            input {
              leaf reg-addr {
                type HexOffset;
                mandatory true;
              }
              leaf reg-val {
                type HexOffset;
                mandatory true;
              }
            }
            output {
              leaf result {
                type string;
              }
            }
          }
          key "location";
          config false;
          leaf location {
            type string;
          }
        }
      }
    }
  }

  grouping master-oir-hist-group {
    container oir-history {
      config false;
      uses oir-hist-group;
    }
  }

  grouping slave-oir-hist-group {
    container oir-history {
      config false;
      uses oir-hist-group;
    }
  }

  grouping oir-hist-group {
    list rack {
      key "rack";
      leaf rack {
        type string;
      }
      container card_oir_hist {
        leaf-list card_oir_events {
          type string;
        }
      }
    }
  }

  grouping ethernet-group {
    container ethernet {
      config false;
      uses ethernet-status;
      uses ethernet-counters;
    }
  }

  grouping ethernet-status {
    container ethernet_status {
      config false;
      list location {
        key "location";
        leaf location {
          type string;
        }
        container ethernet_status {
          leaf-list ethernet_status_values {
            type string;
          }
        }
      }
    }
  }

  grouping ethernet-counters {
    container ethernet_counters {
      config false;
      list location {
        key "location";
        leaf location {
          type string;
        }
        container ethernet_counters {
          leaf-list ethernet_counter_values {
            type string;
          }
        }
      }
    }
  }

  grouping tla-dump-group {
    container tla-dump {
      config false;
      list location {
        key "location";
        config false;
        leaf location {
          type string;
        }
        container tla-dump {
          leaf-list ccc_tla_register_dump {
            type string;
          }
        }
      }
    }
  }
}
