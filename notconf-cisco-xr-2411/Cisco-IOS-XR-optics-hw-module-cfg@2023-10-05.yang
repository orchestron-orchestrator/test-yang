module Cisco-IOS-XR-optics-hw-module-cfg {
  namespace "http://cisco.com/ns/yang/Cisco-IOS-XR-optics-hw-module-cfg";
  prefix optics-hw-module-cfg;

  import cisco-semver {
    prefix semver;
  }
  import Cisco-IOS-XR-config-mda-cfg {
    prefix a1;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR optics-hw-module package configuration.

     This YANG module augments the
       Cisco-IOS-XR-config-mda-cfg
     module with configuration data.

     Copyright (c) 2013-2023 by Cisco Systems, Inc.
     All rights reserved.";

  revision 2023-10-05 {
    semver:module-version "1.0.0";
    description
      "Initial revision";
  }
  revision 2019-04-05 {
    description
      "Establish semantic version baseline.";
  }
  revision 2015-11-09 {
    description
      "IOS XR 6.0 revision.";
  }

  grouping OPTICS {
    description
      "Common node of active-node, preconfigured-node";
    container optics {
      description
        "Fan speed control offset for all optics";
      container fan {
        description
          "Fan speed control offset for all optics";
        container control {
          description
            "Fan speed control offset for all optics";
          leaf offset {
            type uint32 {
              range "1..20";
            }
            description
              "This value will be decremented from maximum
               allowed temperature warning threshold in
               EEPROM";
          }
        }
      }
      leaf fw-init-recovery {
        type empty;
        description
          "Enablement of the failure recovery using
           firmware initialization";
      }
    }
  }

  augment "/a1:preconfigured-nodes/a1:preconfigured-node" {
    description
      "This augment extends the configuration data of
       'Cisco-IOS-XR-config-mda-cfg'";
    uses OPTICS;
  }
  augment "/a1:active-nodes/a1:active-node" {
    description
      "This augment extends the configuration data of
       'Cisco-IOS-XR-config-mda-cfg'";
    uses OPTICS;
  }
}
