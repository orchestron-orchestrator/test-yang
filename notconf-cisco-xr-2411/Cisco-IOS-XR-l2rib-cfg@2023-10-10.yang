module Cisco-IOS-XR-l2rib-cfg {
  namespace "http://cisco.com/ns/yang/Cisco-IOS-XR-l2rib-cfg";
  prefix l2rib-cfg;

  import cisco-semver {
    prefix semver;
  }
  import Cisco-IOS-XR-l2vpn-cfg {
    prefix a1;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR l2rib package configuration.

     This YANG module augments the
       Cisco-IOS-XR-l2vpn-cfg
     module with configuration data.

     Copyright (c) 2013-2023 by Cisco Systems, Inc.
     All rights reserved.";

  revision 2023-10-10 {
    semver:module-version "2.0.0";
    description
      "Adding a new NH service group(SGID) for EVPN Port Active support.";
  }
  revision 2019-09-09 {
    semver:module-version "2.0.0";
    description
      "New config parameter, reset-freeze-count-interval added.";
  }
  revision 2019-04-05 {
    semver:module-version "1.0.1";
    description
      "Establish semantic version baseline.";
  }
  revision 2018-09-26 {
    description
      "Duplicate detection parameters config moved from l2vpn to l2rib.";
  }
  revision 2015-11-09 {
    description
      "IOS XR 6.0 revision.";
  }

  typedef L2rib-retry-count {
    type union {
      type enumeration {
        enum "infinity" {
          value 1001;
          description
            "Infinite retry count";
        }
      }
      type uint32 {
        range "0..1001";
      }
    }
    description
      "L2rib retry count";
  }

  grouping DUPLICATE-DETECTION {
    description
      "Common node of mac, ipv4, ipv6";
    container duplicate-detection {
      description
        "EVPN HOST [MAC/IPv4/IPv6] DUP-DETECT
         Configuration";
      leaf move-count {
        type uint32 {
          range "1..1000";
        }
        default "5";
        description
          "Number of moves to occur within the
           MoveInterval before a MAC/IPv4/IPv6 address is
           marked as duplicate";
      }
      leaf retry-count {
        type L2rib-retry-count;
        description
          "Number of times to automatically clear the
           duplicate flag on a MAC/IPV4/IPV6 route before
           permanently freezing it";
      }
      leaf freeze-time {
        type uint32 {
          range "5..3600";
        }
        default "30";
        description
          "Length of time to lock the MAC/IPv4/IPv6 after
           a MAC/IPv4/IPv6 has been marked as duplicate";
      }
      leaf reset-freeze-count-interval {
        type uint32 {
          range "1..48";
        }
        default "24";
        description
          "Interval after which the count of duplicate
           detection events used to determine whether
           MAC/IPv4/IPv6 needs to be permanently frozen,
           is reset.";
      }
      leaf move-interval {
        type uint32 {
          range "5..3600";
        }
        default "180";
        description
          "Interval within which MoveCount number of moves
           need to happen before a MAC/IPv4/IPv6 route is
           marked as duplicate";
      }
      leaf disable {
        type empty;
        description
          "Set to disable duplicate detection";
      }
    }
  }

  augment "/a1:evpn/a1:evpn-tables" {
    description
      "This augment extends the configuration data of
       'Cisco-IOS-XR-l2vpn-cfg'";
    container host {
      description
        "EVPN HOST Configuration";
      container ipv6 {
        description
          "EVPN HOST IPV6-ADDR Configuration";
        uses DUPLICATE-DETECTION;
      }
      container ipv4 {
        description
          "EVPN HOST IPV4-ADDR Configuration";
        uses DUPLICATE-DETECTION;
      }
      container mac {
        description
          "EVPN HOST MAC-ADDR Configuration";
        uses DUPLICATE-DETECTION;
      }
    }
  }
}
