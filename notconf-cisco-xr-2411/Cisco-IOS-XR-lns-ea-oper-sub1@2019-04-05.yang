submodule Cisco-IOS-XR-lns-ea-oper-sub1 {
  belongs-to Cisco-IOS-XR-lns-ea-oper {
    prefix Cisco-IOS-XR-lns-ea-oper;
  }

  import ietf-inet-types {
    prefix inet;
  }
  import ietf-yang-types {
    prefix yang;
  }
  import Cisco-IOS-XR-types {
    prefix xr;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR lns-ea package operational data.

     Copyright (c) 2013-2019 by Cisco Systems, Inc.
     All rights reserved.";

  revision 2019-04-05 {
    semver:module-version "1.0.0";
    description
      "Establish semantic version baseline.";
  }
  revision 2015-11-09 {
    description
      "IOS XR 6.0 revision.";
  }

  grouping LNS-EA-PARENT-INTERFACE-INFO {
    description
      "LNS EA parent interface information";
    container srgv-mac {
      description
        "SRG VMac-address";
      uses ETHER-MACADDR-TYPE;
    }
    leaf interface {
      type xr:Interface-name;
      description
        "Interface";
    }
    leaf is-in-sync {
      type boolean;
      description
        "Is in sync";
    }
  }

  grouping ETHER-MACADDR-TYPE {
    description
      "ETHER MACADDR TYPE";
    leaf macaddr {
      type yang:hex-string;
      description
        "macaddr";
    }
  }

  grouping LNS-EA-INTERFACE-INFO {
    description
      "LNS EA interface information";
    container peer-mac {
      description
        "Peer Mac-address";
      uses ETHER-MACADDR-TYPE;
    }
    container local-mac {
      description
        "Local Mac-address";
      uses ETHER-MACADDR-TYPE;
    }
    leaf interface {
      type xr:Interface-name;
      description
        "Interface";
    }
    leaf session-id {
      type uint16;
      description
        "Session ID";
    }
    leaf tunnel-id {
      type uint16;
      description
        "Tunnel ID";
    }
    leaf remote-session-id {
      type uint16;
      description
        "Remote_Session ID";
    }
    leaf remote-tunnel-id {
      type uint16;
      description
        "Remote_Tunnel ID";
    }
    leaf tcp-mss-adjust {
      type uint16;
      description
        "tcp mss adjust";
    }
    leaf parent-interface {
      type xr:Interface-name;
      description
        "Parent Interface";
    }
    leaf set-df {
      type boolean;
      description
        "Set DF";
    }
    leaf reflect-df {
      type boolean;
      description
        "ReflectDF";
    }
    leaf set-tos {
      type uint8;
      description
        "Set tos";
    }
    leaf reflect-tos {
      type boolean;
      description
        "Reflecttos";
    }
    leaf local-endpt {
      type inet:ipv4-address;
      description
        "local endpt";
    }
    leaf remote-endpt {
      type inet:ipv4-address;
      description
        "remote endpt";
    }
    leaf table-id {
      type uint16;
      description
        "VrfTableID";
    }
    leaf is-in-sync {
      type boolean;
      description
        "Is in sync";
    }
    leaf is-platform-created {
      type boolean;
      description
        "Is Platform created";
    }
  }
}
