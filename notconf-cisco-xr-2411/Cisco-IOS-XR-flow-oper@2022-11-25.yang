module Cisco-IOS-XR-flow-oper {
  namespace "http://cisco.com/ns/yang/Cisco-IOS-XR-flow-oper";
  prefix flow-oper;

  import Cisco-IOS-XR-types {
    prefix xr;
  }
  import cisco-semver {
    prefix semver;
  }

  include Cisco-IOS-XR-flow-oper-sub2 {
    revision-date 2022-11-25;
  }
  include Cisco-IOS-XR-flow-oper-sub1 {
    revision-date 2022-11-25;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR flow package operational data.

     This module contains definitions
     for the following management objects:
       flow: Flow operational data

     Copyright (c) 2013-2022 by Cisco Systems, Inc.
     All rights reserved.";

  revision 2022-11-25 {
    semver:module-version "2.0.0";
    description
      "Added router-id related field in the exporter configuration information
       2022-09-25
         Added source-port related field in the exporter information
       2022-05-16
         Added more fields in the data template information
       2021-12-16
         Added new fields in collector node to indicate standby mode information.
       2021-08-16
         Added a new field for cache flow record size in cache information";
  }
  revision 2021-06-16 {
    semver:module-version "1.1.0";
    description
      "Added tunnel egress related options for sflow
       2021-04-23
          Added new node for data-template info";
  }
  revision 2019-04-05 {
    semver:module-version "1.0.0";
    description
      "Establish semantic version baseline.";
  }
  revision 2015-11-09 {
    description
      "IOS XR 6.0 revision.";
  }

  container flow {
    config false;
    description
      "Flow operational data";
    container nodes {
      description
        "Node table for node-specific operational data";
      list node {
        key "node-name";
        description
          "Node-specific data for a particular node";
        container flow-server {
          description
            "Flow server related";
          container exporter-map-names {
            description
              "Exporter-map related";
            list exporter-map-name {
              key "exporter-map-name";
              description
                "Exporter-map name";
              container operational-config {
                description
                  "Exporter-map operational configuration";
                uses NFSVR-EXPORT-SERVER-OPER-CONFIG;
              }
              container operational-data {
                description
                  "Exporter-map operational data";
                uses NFSVR-SHOW-FLOW-EXPORTER-RESP-STATS;
              }
              leaf exporter-map-name {
                type xr:Cisco-ios-xr-string;
                description
                  "The name of the exporter-map";
              }
            }
          }
          container monitor-map-names {
            description
              "Monitor-map related";
            list monitor-map-name {
              key "monitor-map-name";
              description
                "Monitor-map name";
              container operational-config {
                description
                  "Monitor-map operational configuration";
                uses NFSVR-SHOW-FLOW-MONITOR-BASIC;
              }
              container operational-data {
                description
                  "Monitor-map operational data";
                uses NFSVR-SHOW-FLOW-CACHE-RESP-SINGLE-MONITOR-MAP;
              }
              container data-template {
                description
                  "Monitor-map data template information";
                uses NFSVR-SHOW-FLOW-DATA-TEMPLATE;
              }
              leaf monitor-map-name {
                type xr:Cisco-ios-xr-string;
                description
                  "The name of the monitor-map";
              }
            }
          }
        }
        leaf node-name {
          type xr:Node-id;
          description
            "Node name";
        }
      }
    }
  }
}
