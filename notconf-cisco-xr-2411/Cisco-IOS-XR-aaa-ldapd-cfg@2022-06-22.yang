module Cisco-IOS-XR-aaa-ldapd-cfg {
  namespace "http://cisco.com/ns/yang/Cisco-IOS-XR-aaa-ldapd-cfg";
  prefix aaa-ldapd-cfg;

  import ietf-inet-types {
    prefix inet;
  }
  import Cisco-IOS-XR-types {
    prefix xr;
  }
  import cisco-semver {
    prefix semver;
  }
  import Cisco-IOS-XR-aaa-lib-cfg {
    prefix a1;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR aaa-ldapd package configuration.

     This YANG module augments the
       Cisco-IOS-XR-aaa-lib-cfg
     module with configuration data.

     Copyright (c) 2013-2022 by Cisco Systems, Inc.
     All rights reserved.";

  revision 2022-06-22 {
    semver:module-version "1.0.0";
    description
      "Dynamic NACM feature commit.";
  }
  revision 2022-05-20 {
    description
      "Dynamic NACM feature commit.";
  }
  revision 2019-04-05 {
    description
      "Establish semantic version baseline.";
  }
  revision 2015-11-09 {
    description
      "IOS XR 6.0 revision.";
  }

  typedef Aaa-ldap-timeout {
    type uint32 {
      range "1..1000";
    }
    description
      "Aaa ldap timeout";
  }

  typedef Aaaldap-bind-password {
    type enumeration {
      enum "type7" {
        value 7;
        description
          "Type 7 encryption";
      }
    }
    description
      "Aaaldap bind password";
  }

  typedef Aaa-ldap-port-range {
    type uint32 {
      range "1..65535";
    }
    description
      "Aaa ldap port range";
  }

  grouping BIND-DISTINGUISHED-NAME {
    description
      "Common node of aaa-ldap, host";
    leaf bind-distinguished-name {
      type string;
      description
        "Set AAA LDAP Bind Distinguished Name.";
    }
  }

  grouping BIND-PASSWORD {
    description
      "Common node of aaa-ldap, host";
    container bind-password {
      description
        "Set AAA LDAP Bind password";
      leaf encrypt-type {
        type Aaaldap-bind-password;
        description
          "Encryption Type";
      }
      leaf secret7 {
        when "../encrypt-type = 'type7'" {
          description
            "../EncryptType = Type7";
        }
        type xr:Proprietary-password;
        description
          "Type7 Encryption key";
      }
    }
  }

  grouping CONNECT-TIMEOUT {
    description
      "Common node of aaa-ldap, host";
    leaf connect-timeout {
      type Aaa-ldap-timeout;
      units "second";
      default "5";
      description
        "Time in seconds (range 1-1000 sec) to wait for
         AAA LDAP server to respond for connection
         request.";
    }
  }

  grouping SEARCH-TIMEOUT {
    description
      "Common node of aaa-ldap, host";
    leaf search-timeout {
      type Aaa-ldap-timeout;
      units "second";
      default "5";
      description
        "Time in seconds (range 1-1000 sec) to wait for
         AAA LDAP server to respond for search operation";
    }
  }

  grouping VRF {
    description
      "Common node of aaa-ldap, host";
    leaf vrf {
      type string;
      description
        "VRF name. Specify 'default' for default VRF";
    }
  }

  grouping BIND-TIMEOUT {
    description
      "Common node of aaa-ldap, host";
    leaf bind-timeout {
      type Aaa-ldap-timeout;
      units "second";
      default "5";
      description
        "Time in seconds (range 1-1000 sec) to wait for
         AAA LDAP to respond for bind request.";
    }
  }

  augment "/a1:aaa" {
    description
      "This augment extends the configuration data of
       'Cisco-IOS-XR-aaa-lib-cfg'";
    container aaa-ldap {
      description
        "Modify AAA LDAP query parameters";
      container hosts {
        description
          "Specify a AAA LDAP server";
        list host {
          key "ordering-index ip-address port-number";
          description
            "One of the AAA LDAP servers";
          leaf ordering-index {
            type uint32;
            description
              "This is used to sort the servers in the order
               of precedence";
          }
          leaf ip-address {
            type inet:ip-address-no-zone;
            description
              "IP address of AAA LDAP server";
          }
          leaf port-number {
            type Aaa-ldap-port-range;
            description
              "Port number (standard 389 or 636)";
          }
          uses BIND-PASSWORD;
          uses VRF;
          uses SEARCH-TIMEOUT;
          uses CONNECT-TIMEOUT;
          uses BIND-TIMEOUT;
          uses BIND-DISTINGUISHED-NAME;
        }
      }
      uses BIND-PASSWORD;
      uses VRF;
      uses SEARCH-TIMEOUT;
      uses CONNECT-TIMEOUT;
      uses BIND-TIMEOUT;
      uses BIND-DISTINGUISHED-NAME;
    }
  }
}
