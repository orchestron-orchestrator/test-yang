module Cisco-IOS-XR-um-lpts-punt-flow-trap-cfg {
  namespace "http://cisco.com/ns/yang/Cisco-IOS-XR-um-lpts-punt-flow-trap-cfg";
  prefix um-lpts-punt-flow-trap-cfg;

  import Cisco-IOS-XR-types {
    prefix xr;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR lpts-punt-flow-trap package configuration.

     This YANG module augments the
     modules with configuration data.

     Copyright (c) 2020, 2022 by Cisco Systems, Inc.
     All rights reserved.";

  revision 2020-08-31 {
    semver:module-version "1.0.0";
    description
      "Initial release";
  }

  container lpts {
    description
      "lpts configuration commands";
    container punt {
      description
        "punt configuration commands";
      container excessive-flow-trap {
        description
          "excessive punt flow trap configuration commands";
        container subscriber-interfaces {
          presence "Indicates a subscriber-interfaces node is configured.";
          description
            "Enable the trap on subscriber interfaces";
        }
        container non-subscriber-interfaces {
          presence "Indicates a non-subscriber-interfaces node is configured.";
          description
            "Enable the trap on non-subscriber interfaces";
          container mac {
            presence "Indicates a mac node is configured.";
            description
              "Enable trap based on source mac on non-subscriber interface";
          }
        }
        container penalty-rate {
          description
            "Configure penalty policing rate";
          leaf default {
            type uint32 {
              range "2..100" {
                description
                  "Penalty policer rate in packets-per-second";
              }
            }
            description
              "Configure default penalty policing rate for all protocols";
          }
          leaf arp {
            type uint32 {
              range "2..100" {
                description
                  "Penalty policer rate in packets-per-second";
              }
            }
            description
              "Configure penalty policing rate for arp";
          }
          leaf icmp {
            type uint32 {
              range "2..100" {
                description
                  "Penalty policer rate in packets-per-second";
              }
            }
            description
              "Configure penalty policing rate for icmp";
          }
          leaf dhcp {
            type uint32 {
              range "2..100" {
                description
                  "Penalty policer rate in packets-per-second";
              }
            }
            description
              "Configure penalty policing rate for dhcp";
          }
          leaf pppoe {
            type uint32 {
              range "2..100" {
                description
                  "Penalty policer rate in packets-per-second";
              }
            }
            description
              "Configure penalty policing rate for pppoe";
          }
          leaf ppp {
            type uint32 {
              range "2..100" {
                description
                  "Penalty policer rate in packets-per-second";
              }
            }
            description
              "Configure penalty policing rate for ppp";
          }
          leaf igmp {
            type uint32 {
              range "2..100" {
                description
                  "Penalty policer rate in packets-per-second";
              }
            }
            description
              "Configure penalty policing rate for igmp";
          }
          leaf ip {
            type uint32 {
              range "2..100" {
                description
                  "Penalty policer rate in packets-per-second";
              }
            }
            description
              "Configure penalty policing rate for ipv4/v6";
          }
          leaf l2tp {
            type uint32 {
              range "2..100" {
                description
                  "Penalty policer rate in packets-per-second";
              }
            }
            description
              "Configure penalty policing rate for l2tp";
          }
          leaf unclassified {
            type uint32 {
              range "2..100" {
                description
                  "Penalty policer rate in packets-per-second";
              }
            }
            description
              "Configure penalty policing rate for unclassified";
          }
        }
        container penalty-timeout {
          description
            "Configure penalty timeout value";
          leaf default {
            type uint32 {
              range "0..1000" {
                description
                  "Timeout value in minutes";
              }
            }
            description
              "Configure default penalty timeout for all protocols";
          }
          leaf arp {
            type uint32 {
              range "0..1000" {
                description
                  "Timeout value in minutes";
              }
            }
            description
              "Configure penalty timeout for arp";
          }
          leaf icmp {
            type uint32 {
              range "0..1000" {
                description
                  "Timeout value in minutes";
              }
            }
            description
              "Configure penalty timeout for icmp";
          }
          leaf dhcp {
            type uint32 {
              range "0..1000" {
                description
                  "Timeout value in minutes";
              }
            }
            description
              "Configure penalty timeout for dhcp";
          }
          leaf pppoe {
            type uint32 {
              range "0..1000" {
                description
                  "Timeout value in minutes";
              }
            }
            description
              "Configure penalty timeout for pppoe";
          }
          leaf ppp {
            type uint32 {
              range "0..1000" {
                description
                  "Timeout value in minutes";
              }
            }
            description
              "Configure penalty timeout for ppp";
          }
          leaf igmp {
            type uint32 {
              range "0..1000" {
                description
                  "Timeout value in minutes";
              }
            }
            description
              "Configure penalty timeout for igmp";
          }
          leaf ip {
            type uint32 {
              range "0..1000" {
                description
                  "Timeout value in minutes";
              }
            }
            description
              "Configure penalty timeout for ipv4/v6";
          }
          leaf l2tp {
            type uint32 {
              range "0..1000" {
                description
                  "Timeout value in minutes";
              }
            }
            description
              "Configure penalty timeout for l2tp";
          }
          leaf unclassifed {
            type uint32 {
              range "0..1000" {
                description
                  "Timeout value in minutes";
              }
            }
            description
              "Configure penalty timeout for unclassified";
          }
          leaf ospf {
            type uint32 {
              range "0..1000" {
                description
                  "Timeout value in minutes";
              }
            }
            description
              "Configure penalty timeout for ospf";
          }
          leaf bgp {
            type uint32 {
              range "0..1000" {
                description
                  "Timeout value in minutes";
              }
            }
            description
              "Configure penalty timeout for bgp";
          }
        }
        container exclude {
          description
            "Exclude an item from all traps";
          container interfaces {
            description
              "Exclude an interface from all traps";
            list interface {
              key "interface-name";
              description
                "Exclude an interface from all traps";
              leaf interface-name {
                type xr:Interface-name;
                description
                  "Exclude an interface from all traps";
              }
            }
          }
        }
        leaf trap-size {
          type uint32 {
            range "1|2|4|8|16|32|64|128" {
              description
                "Should be power of 2. Any one of 1,2,4,8,16,32,64,128";
            }
          }
          description
            "Flowtrap size";
        }
        leaf report-threshold {
          type uint32 {
            range "1..65535" {
              description
                "Threshold to cross for a flow to be considered as bad actor flow";
            }
          }
          description
            "Bad actor report threshold";
        }
        leaf eviction-threshold {
          type uint32 {
            range "1..65535" {
              description
                "Eviction threshold should be <= report-threshold(Default value of report-threshold = 5)";
            }
          }
          description
            "Threshold to evict a flow from trap";
        }
        leaf eviction-search-limit {
          type uint32 {
            range "1..128" {
              description
                "Eviction search limit should be less than or equal to trap-size";
            }
          }
          description
            "Search limit to evict a flow entry";
        }
        leaf max-flow-gap {
          type uint32 {
            range "1..60000" {
              description
                "Maximum flow gap in milliseconds";
            }
          }
          description
            "Max inter-packet-gap for BA flow";
        }
        leaf sample-prob {
          type xr:Cisco-ios-xr-string {
            length "1..32" {
              description
                "floating point value between 0 to 1";
            }
          }
          description
            "Probability of packets to be sampled";
        }
        leaf dampening {
          type uint32 {
            range "5000..60000" {
              description
                "Dampening period for a bad actor flow in milliseconds";
            }
          }
          description
            "Dampening bad actor notifications";
        }
        container interface-based-flow {
          presence "Indicates a interface-based-flow node is configured.";
          description
            "Identify flow based on interface and flowtype";
        }
        container routing-protocols-enable {
          presence "Indicates a routing-protocols-enable node is configured.";
          description
            "Allow routing protocol packets ospf bgp to pass through EPFT";
        }
      }
    }
  }
}
