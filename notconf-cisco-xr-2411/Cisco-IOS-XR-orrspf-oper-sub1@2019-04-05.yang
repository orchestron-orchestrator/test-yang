submodule Cisco-IOS-XR-orrspf-oper-sub1 {
  belongs-to Cisco-IOS-XR-orrspf-oper {
    prefix Cisco-IOS-XR-orrspf-oper;
  }

  import ietf-inet-types {
    prefix inet;
  }
  import ietf-yang-types {
    prefix yang;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR orrspf package operational data.

     Copyright (c) 2013-2019 by Cisco Systems, Inc.
     All rights reserved.";

  revision 2019-04-05 {
    semver:module-version "1.0.0";
    description
      "Establish semantic version baseline.";
  }
  revision 2015-11-09 {
    description
      "IOS XR 6.0 revision.";
  }

  typedef Orrspf-ipv6-addr {
    type inet:ipv6-address;
    description
      "Orrspf ipv6 addr";
  }

  typedef Orrspf-ipv4-addr {
    type inet:ipv4-address;
    description
      "Orrspf ipv4 addr";
  }

  typedef Orrspf-af-id {
    type enumeration {
      enum "ipv4" {
        value 1;
        description
          "IPv4";
      }
      enum "ipv6" {
        value 2;
        description
          "IPv6";
      }
    }
    description
      "Orrspf af id";
  }

  typedef Orrspf-sh-node-id {
    type yang:hex-string;
    description
      "Orrspf sh node id";
  }

  grouping ORRSPF-SH-TOPO {
    description
      "ORRSPF show topology bag";
    leaf spt-node {
      type Orrspf-sh-node-id;
      description
        "SPT node data";
    }
    leaf cost {
      type uint32;
      description
        "SPT node cost";
    }
    leaf next-hop {
      type Orrspf-sh-node-id;
      description
        "SPT node next hop";
    }
    leaf next-hop-valid {
      type boolean;
      description
        "SPT node next hop valid";
    }
  }

  grouping ORRSPF-SH-POLICY {
    description
      "ORRSPF show policy bag";
    container root-ip {
      description
        "Root IP Address";
      uses ORRSPF-IP-ADDR;
    }
    container primary-root-ip {
      description
        "Primary Root IP";
      uses ORRSPF-IP-ADDR;
    }
    container secondary-root-ip {
      description
        "Secondary Root IP";
      uses ORRSPF-IP-ADDR;
    }
    container tertiary-root-ip {
      description
        "Tertiary Root IP";
      uses ORRSPF-IP-ADDR;
    }
    leaf policy-name {
      type string {
        length "0..33";
      }
      description
        "Policy name";
    }
    leaf af-id {
      type uint8;
      description
        "Address family";
    }
    leaf protocol-id {
      type uint8;
      description
        "Protocol ID";
    }
    leaf fa-num {
      type uint8;
      description
        "Flex algo number";
    }
    leaf fad-valid {
      type boolean;
      description
        "Flex algo definition valid";
    }
    leaf table-id {
      type uint32;
      description
        "RIB Table ID";
    }
    leaf root-node {
      type Orrspf-sh-node-id;
      description
        "Root node ID";
    }
    leaf fad-node {
      type Orrspf-sh-node-id;
      description
        "Flex algo definition node ID";
    }
    leaf num-spt-nodes {
      type uint32;
      description
        "Number of nodes in SPT";
    }
    leaf num-spt-calc {
      type uint32;
      description
        "Number of SPT calculations";
    }
    leaf num-spt-reset {
      type uint32;
      description
        "Number of SPT reset";
    }
  }

  grouping ORRSPF-IPV6-PFX {
    description
      "IPv6 prefix";
    leaf prefix {
      type inet:ipv6-address;
      description
        "Prefix";
    }
    leaf prefix-length {
      type uint8;
      description
        "Prefix length";
    }
  }

  grouping ORRSPF-IPV4-PFX {
    description
      "IPv4 prefix";
    leaf prefix {
      type inet:ipv4-address;
      description
        "Prefix";
    }
    leaf prefix-length {
      type uint8;
      description
        "Prefix length";
    }
  }

  grouping ORRSPF-IP-PFX {
    description
      "ORRSPF IP PFX";
    container ipv4 {
      when "../af-id = 'ipv4'" {
        description
          "../AFId = 'IPv4'";
      }
      description
        "IPV4 prefix type";
      uses ORRSPF-IPV4-PFX;
    }
    container ipv6 {
      when "../af-id = 'ipv6'" {
        description
          "../AFId = 'IPv6'";
      }
      description
        "IPV6 prefix type";
      uses ORRSPF-IPV6-PFX;
    }
    leaf af-id {
      type Orrspf-af-id;
      description
        "AFId";
    }
  }

  grouping ORRSPF-SH-PFX {
    description
      "ORRSPF show prefix bag";
    container prefix {
      description
        "IP Prefix";
      uses ORRSPF-IP-PFX;
    }
    leaf cost {
      type uint32;
      description
        "Prefix cost";
    }
  }

  grouping ORRSPF-SH-FAD {
    description
      "ORRSPF show fad data";
    leaf fa-num {
      type uint8;
      description
        "Flex algo number";
    }
    leaf fad-unsupported {
      type boolean;
      description
        "Flex algo not supported";
    }
    leaf fad-node {
      type Orrspf-sh-node-id;
      description
        "Flex algo definition node ID";
    }
  }

  grouping ORRSPF-SH-CTX {
    description
      "ORRSPF show context bag";
    leaf vrf-id {
      type uint32;
      description
        "VRF ID";
    }
    leaf protocol-id {
      type uint8;
      description
        "Protocol ID";
    }
    leaf mt-id {
      type uint16;
      description
        "Multi-Topology ID";
    }
    leaf area-id {
      type uint32;
      description
        "Area ID";
    }
    list fad-data {
      description
        "Flex algo definition";
      uses ORRSPF-SH-FAD;
    }
  }

  grouping ORRSPF-SH-LINK {
    description
      "ORRSPF show link data";
    leaf remote-node {
      type Orrspf-sh-node-id;
      description
        "Remote node ID";
    }
    leaf metric {
      type uint32;
      description
        "Link metric";
    }
  }

  grouping ORRSPF-IP-ADDR {
    description
      "ORRSPF IP ADDR";
    leaf af-id {
      type Orrspf-af-id;
      description
        "AFId";
    }
    leaf ipv4 {
      when "../af-id = 'ipv4'" {
        description
          "../AFId = 'IPv4'";
      }
      type Orrspf-ipv4-addr;
      description
        "IPV4 address type";
    }
    leaf ipv6 {
      when "../af-id = 'ipv6'" {
        description
          "../AFId = 'IPv6'";
      }
      type Orrspf-ipv6-addr;
      description
        "IPV6 address type";
    }
  }

  grouping ORRSPF-SH-GRAPH {
    description
      "ORRSPF show graph bag";
    container router-id {
      description
        "Router ID";
      uses ORRSPF-IP-ADDR;
    }
    leaf local-node {
      type Orrspf-sh-node-id;
      description
        "Local node ID";
    }
    list link-data {
      description
        "Link Data";
      uses ORRSPF-SH-LINK;
    }
  }
}
