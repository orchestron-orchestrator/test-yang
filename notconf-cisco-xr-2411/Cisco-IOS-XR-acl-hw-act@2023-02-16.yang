module Cisco-IOS-XR-acl-hw-act {
  namespace "http://cisco.com/ns/yang/Cisco-IOS-XR-acl-hw-act";
  prefix acl-hw-act;

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR acl-hw package action data.

     This module contains definitions
     for the following management objects:
       access-list-hardware: Root class of accesslist hardware

     Copyright (c) 2022-2023 by Cisco Systems, Inc.
     All rights reserved.";

  revision 2023-02-16 {
    semver:module-version "1.0.0";
    description
      "Initial Revision";
  }

  typedef dpa-fm-lkup {
    type enumeration {
      enum "ipv4" {
        description
          "IPv4 Lookup";
      }
      enum "ipv6" {
        description
          "IPv6 Lookup";
      }
      enum "ethernet-services" {
        description
          "Layer 2 MAC Lookup";
      }
    }
    description
      "Lookup type";
  }

  typedef dpa-fm-direction {
    type enumeration {
      enum "ingress" {
        description
          "Ingress direction";
      }
      enum "egress" {
        description
          "Egress direction";
      }
    }
    description
      "Direction";
  }

  rpc clear-access-list-hardware-location {
    description
      "Clear access-list hardware location";

    input {
      leaf node-location {
        type string;
        mandatory true;
        description
          "Node location";
      }
      leaf name {
        type string;
        mandatory true;
        description
          "Name of the ACL";
      }
      leaf sequence {
        type uint32 {
          range "0..2147483646";
        }
        mandatory true;
        description
          "ACE sequence number. 0 means all ACE under an ACL";
      }
      leaf direction {
        type dpa-fm-direction;
        mandatory true;
        description
          "Direction to which the ACL is attached";
      }
      leaf lookupType {
        type dpa-fm-lkup;
        mandatory true;
        description
          "ACL Lookup Type";
      }
    }
  }
}
