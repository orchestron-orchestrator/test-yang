module Cisco-IOS-XR-asr9k-ep-port-mode-cfg {
  namespace "http://cisco.com/ns/yang/Cisco-IOS-XR-asr9k-ep-port-mode-cfg";
  prefix asr9k-ep-port-mode-cfg;

  import Cisco-IOS-XR-types {
    prefix xr;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR asr9k-ep-port-mode package configuration.

     This module contains definitions
     for the following management objects:
       hw-module-ep-port-mode: HW Module EP port-mode configuration

     Copyright (c) 2013-2019 by Cisco Systems, Inc.
     All rights reserved.";

  revision 2019-04-05 {
    semver:module-version "1.0.0";
    description
      "Establish semantic version baseline.";
  }
  revision 2019-01-06 {
    description
      "IOS XR 6.6.2 revision.";
  }
  revision 2015-11-09 {
    description
      "IOS XR 6.0 revision.";
  }

  typedef Hw-module-ep-if-port-mode {
    type enumeration {
      enum "2xhundredgige-16qam" {
        value 1;
        description
          "2xHundredGigE 16QAM mode configuration";
      }
      enum "2xhundredgige-8qam" {
        value 2;
        description
          "2xHundredGigE 8QAM mode configuration";
      }
    }
    description
      "Hw module ep if port mode";
  }

  container hw-module-ep-port-mode {
    description
      "HW Module EP port-mode configuration";
    list ep-port-mode-configuration {
      key "active";
      description
        "active or pre configuration";
      leaf active {
        type xr:Cisco-ios-xr-string;
        description
          "act or pre configuration";
      }
      list node {
        key "location";
        description
          "line-card node location";
        container bays {
          description
            "port-mode configuration for EP bay number";
          list bay {
            key "bay-number";
            description
              "EP Bay number";
            container ports {
              description
                "port-mode configuration for port number";
              list port {
                key "port-number";
                description
                  "Optics port number";
                leaf if-port-mode {
                  type Hw-module-ep-if-port-mode;
                  description
                    "port-mode type";
                }
                leaf port-number {
                  type xr:Cisco-ios-xr-string;
                  description
                    "Optics port number";
                }
              }
            }
            leaf bay-number {
              type xr:Cisco-ios-xr-string;
              description
                "bay number";
            }
          }
        }
        leaf location {
          type xr:Cisco-ios-xr-string;
          description
            "Fully qualified line-card location";
        }
      }
    }
  }
}
