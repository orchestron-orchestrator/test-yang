module Cisco-IOS-XR-platforms-common-dnx-infra-oper {
  namespace "http://cisco.com/ns/yang/Cisco-IOS-XR-platforms-common-dnx-infra-oper";
  prefix platforms-common-dnx-infra-oper;

  import cisco-semver {
    prefix semver;
  }

  include Cisco-IOS-XR-platforms-common-dnx-infra-oper-sub1 {
    revision-date 2019-04-05;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR platforms-common-dnx-infra package operational data.

     This module contains definitions
     for the following management objects:
       hw-module-profile: hw-mod profile info

     Copyright (c) 2013-2019 by Cisco Systems, Inc.
     All rights reserved.";

  revision 2019-04-05 {
    semver:module-version "1.0.0";
    description
      "Establish semantic version baseline.";
  }
  revision 2015-11-09 {
    description
      "IOS XR 6.0 revision.";
  }

  container hw-module-profile {
    config false;
    description
      "hw-mod profile info";
    container npu-operating-mode {
      description
        "NPU operating mode - native or compatability
         mode";
      uses DNX-NPU-OP-MODE-ST;
    }
    container mdb-scale-profile {
      description
        "mdb scale profile configured on the system";
      uses DNX-MDB-SCALE-PROFILE-ST;
    }
  }
}
