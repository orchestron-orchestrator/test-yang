module Cisco-IOS-XR-um-control-plane-cfg {
  namespace "http://cisco.com/ns/yang/Cisco-IOS-XR-um-control-plane-cfg";
  prefix um-control-plane-cfg;

  import Cisco-IOS-XR-types {
    prefix xr;
  }
  import ietf-inet-types {
    prefix inet;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR control-plane package configuration.

     This YANG module augments the
     modules with configuration data.

     Copyright (c) 2022 by Cisco Systems, Inc.
     All rights reserved.";

  revision 2022-09-30 {
    semver:module-version "1.1.0";
    description
      "enable-inband-behavior container added";
  }
  revision 2021-03-11 {
    semver:module-version "1.0.0";
    description
      "Initial release";
  }

  container control-plane {
    description
      "Configure Control Plane";
    container management-plane {
      description
        "Configure management plane protection";
      container inband {
        description
          "Configure an inband interface/protocol";
        container interfaces {
          description
            "Configure an inband interface";
          list interface {
            key "interface-name";
            description
              "Configure a specific interface";
            leaf interface-name {
              type xr:Interface-name;
              description
                "Configure a specific interface";
            }
            container allow {
              description
                "Allow a protocol on this interface";
              container ssh {
                presence "Indicates a ssh node is configured.";
                description
                  "Secure Shell (v1 & v2)";
              }
              container ssh-peer {
                description
                  "Configure peer address on this interface";
                container address {
                  description
                    "Configure peer address on this interface";
                  container ipv4 {
                    description
                      "Configure peer IPv4 address on this interface";
                    container ipv4-address-prefixes {
                      description
                        "Enter IPv4 address with prefix";
                      list ipv4-address-prefix {
                        key "address length";
                        description
                          "Enter IPv4 address with prefix";
                        leaf address {
                          type inet:ipv4-address-no-zone;
                          description
                            "Enter IPv4 address with prefix";
                        }
                        leaf length {
                          type uint32 {
                            range "0..32";
                          }
                          description
                            "Enter IPv4 address with prefix";
                        }
                      }
                    }
                    container ipv4-addresses {
                      description
                        "Enter IPv4 address";
                      list ipv4-address {
                        key "address";
                        description
                          "Enter IPv4 address";
                        leaf address {
                          type inet:ipv4-address-no-zone;
                          description
                            "Enter IPv4 address";
                        }
                      }
                    }
                  }
                  container ipv6 {
                    description
                      "Configure peer IPv6 address on this interface";
                    container ipv6-address-prefixes {
                      description
                        "Enter IPv6 address with prefix";
                      list ipv6-address-prefix {
                        key "address length";
                        description
                          "Enter IPv6 address with prefix";
                        leaf address {
                          type inet:ipv6-address-no-zone;
                          description
                            "Enter IPv6 address with prefix";
                        }
                        leaf length {
                          type uint32 {
                            range "0..128";
                          }
                          description
                            "Enter IPv6 address with prefix";
                        }
                      }
                    }
                    container ipv6-addresses {
                      description
                        "Enter IPv6 address";
                      list ipv6-address {
                        key "address";
                        description
                          "Enter IPv6 address";
                        leaf address {
                          type inet:ipv6-address-no-zone;
                          description
                            "Enter IPv6 address";
                        }
                      }
                    }
                  }
                }
              }
              container telnet {
                presence "Indicates a telnet node is configured.";
                description
                  "Telnet";
              }
              container telnet-peer {
                description
                  "Configure peer address on this interface";
                container address {
                  description
                    "Configure peer address on this interface";
                  container ipv4 {
                    description
                      "Configure peer IPv4 address on this interface";
                    container ipv4-address-prefixes {
                      description
                        "Enter IPv4 address with prefix";
                      list ipv4-address-prefix {
                        key "address length";
                        description
                          "Enter IPv4 address with prefix";
                        leaf address {
                          type inet:ipv4-address-no-zone;
                          description
                            "Enter IPv4 address with prefix";
                        }
                        leaf length {
                          type uint32 {
                            range "0..32";
                          }
                          description
                            "Enter IPv4 address with prefix";
                        }
                      }
                    }
                    container ipv4-addresses {
                      description
                        "Enter IPv4 address";
                      list ipv4-address {
                        key "address";
                        description
                          "Enter IPv4 address";
                        leaf address {
                          type inet:ipv4-address-no-zone;
                          description
                            "Enter IPv4 address";
                        }
                      }
                    }
                  }
                  container ipv6 {
                    description
                      "Configure peer IPv6 address on this interface";
                    container ipv6-address-prefixes {
                      description
                        "Enter IPv6 address with prefix";
                      list ipv6-address-prefix {
                        key "address length";
                        description
                          "Enter IPv6 address with prefix";
                        leaf address {
                          type inet:ipv6-address-no-zone;
                          description
                            "Enter IPv6 address with prefix";
                        }
                        leaf length {
                          type uint32 {
                            range "0..128";
                          }
                          description
                            "Enter IPv6 address with prefix";
                        }
                      }
                    }
                    container ipv6-addresses {
                      description
                        "Enter IPv6 address";
                      list ipv6-address {
                        key "address";
                        description
                          "Enter IPv6 address";
                        leaf address {
                          type inet:ipv6-address-no-zone;
                          description
                            "Enter IPv6 address";
                        }
                      }
                    }
                  }
                }
              }
              container snmp {
                presence "Indicates a snmp node is configured.";
                description
                  "SNMP (all versions)";
              }
              container snmp-peer {
                description
                  "Configure peer address on this interface";
                container address {
                  description
                    "Configure peer address on this interface";
                  container ipv4 {
                    description
                      "Configure peer IPv4 address on this interface";
                    container ipv4-address-prefixes {
                      description
                        "Enter IPv4 address with prefix";
                      list ipv4-address-prefix {
                        key "address length";
                        description
                          "Enter IPv4 address with prefix";
                        leaf address {
                          type inet:ipv4-address-no-zone;
                          description
                            "Enter IPv4 address with prefix";
                        }
                        leaf length {
                          type uint32 {
                            range "0..32";
                          }
                          description
                            "Enter IPv4 address with prefix";
                        }
                      }
                    }
                    container ipv4-addresses {
                      description
                        "Enter IPv4 address";
                      list ipv4-address {
                        key "address";
                        description
                          "Enter IPv4 address";
                        leaf address {
                          type inet:ipv4-address-no-zone;
                          description
                            "Enter IPv4 address";
                        }
                      }
                    }
                  }
                  container ipv6 {
                    description
                      "Configure peer IPv6 address on this interface";
                    container ipv6-address-prefixes {
                      description
                        "Enter IPv6 address with prefix";
                      list ipv6-address-prefix {
                        key "address length";
                        description
                          "Enter IPv6 address with prefix";
                        leaf address {
                          type inet:ipv6-address-no-zone;
                          description
                            "Enter IPv6 address with prefix";
                        }
                        leaf length {
                          type uint32 {
                            range "0..128";
                          }
                          description
                            "Enter IPv6 address with prefix";
                        }
                      }
                    }
                    container ipv6-addresses {
                      description
                        "Enter IPv6 address";
                      list ipv6-address {
                        key "address";
                        description
                          "Enter IPv6 address";
                        leaf address {
                          type inet:ipv6-address-no-zone;
                          description
                            "Enter IPv6 address";
                        }
                      }
                    }
                  }
                }
              }
              container tftp {
                presence "Indicates a tftp node is configured.";
                description
                  "TFTP";
              }
              container tftp-peer {
                description
                  "Configure peer address on this interface";
                container address {
                  description
                    "Configure peer address on this interface";
                  container ipv4 {
                    description
                      "Configure peer IPv4 address on this interface";
                    container ipv4-address-prefixes {
                      description
                        "Enter IPv4 address with prefix";
                      list ipv4-address-prefix {
                        key "address length";
                        description
                          "Enter IPv4 address with prefix";
                        leaf address {
                          type inet:ipv4-address-no-zone;
                          description
                            "Enter IPv4 address with prefix";
                        }
                        leaf length {
                          type uint32 {
                            range "0..32";
                          }
                          description
                            "Enter IPv4 address with prefix";
                        }
                      }
                    }
                    container ipv4-addresses {
                      description
                        "Enter IPv4 address";
                      list ipv4-address {
                        key "address";
                        description
                          "Enter IPv4 address";
                        leaf address {
                          type inet:ipv4-address-no-zone;
                          description
                            "Enter IPv4 address";
                        }
                      }
                    }
                  }
                  container ipv6 {
                    description
                      "Configure peer IPv6 address on this interface";
                    container ipv6-address-prefixes {
                      description
                        "Enter IPv6 address with prefix";
                      list ipv6-address-prefix {
                        key "address length";
                        description
                          "Enter IPv6 address with prefix";
                        leaf address {
                          type inet:ipv6-address-no-zone;
                          description
                            "Enter IPv6 address with prefix";
                        }
                        leaf length {
                          type uint32 {
                            range "0..128";
                          }
                          description
                            "Enter IPv6 address with prefix";
                        }
                      }
                    }
                    container ipv6-addresses {
                      description
                        "Enter IPv6 address";
                      list ipv6-address {
                        key "address";
                        description
                          "Enter IPv6 address";
                        leaf address {
                          type inet:ipv6-address-no-zone;
                          description
                            "Enter IPv6 address";
                        }
                      }
                    }
                  }
                }
              }
              container http {
                presence "Indicates a http node is configured.";
                description
                  "HTTP(S)";
              }
              container http-peer {
                description
                  "Configure peer address on this interface";
                container address {
                  description
                    "Configure peer address on this interface";
                  container ipv4 {
                    description
                      "Configure peer IPv4 address on this interface";
                    container ipv4-address-prefixes {
                      description
                        "Enter IPv4 address with prefix";
                      list ipv4-address-prefix {
                        key "address length";
                        description
                          "Enter IPv4 address with prefix";
                        leaf address {
                          type inet:ipv4-address-no-zone;
                          description
                            "Enter IPv4 address with prefix";
                        }
                        leaf length {
                          type uint32 {
                            range "0..32";
                          }
                          description
                            "Enter IPv4 address with prefix";
                        }
                      }
                    }
                    container ipv4-addresses {
                      description
                        "Enter IPv4 address";
                      list ipv4-address {
                        key "address";
                        description
                          "Enter IPv4 address";
                        leaf address {
                          type inet:ipv4-address-no-zone;
                          description
                            "Enter IPv4 address";
                        }
                      }
                    }
                  }
                  container ipv6 {
                    description
                      "Configure peer IPv6 address on this interface";
                    container ipv6-address-prefixes {
                      description
                        "Enter IPv6 address with prefix";
                      list ipv6-address-prefix {
                        key "address length";
                        description
                          "Enter IPv6 address with prefix";
                        leaf address {
                          type inet:ipv6-address-no-zone;
                          description
                            "Enter IPv6 address with prefix";
                        }
                        leaf length {
                          type uint32 {
                            range "0..128";
                          }
                          description
                            "Enter IPv6 address with prefix";
                        }
                      }
                    }
                    container ipv6-addresses {
                      description
                        "Enter IPv6 address";
                      list ipv6-address {
                        key "address";
                        description
                          "Enter IPv6 address";
                        leaf address {
                          type inet:ipv6-address-no-zone;
                          description
                            "Enter IPv6 address";
                        }
                      }
                    }
                  }
                }
              }
              container xr-xml {
                presence "Indicates a xr-xml node is configured.";
                description
                  "XML";
              }
              container xr-xml-peer {
                description
                  "Configure peer address on this interface";
                container address {
                  description
                    "Configure peer address on this interface";
                  container ipv4 {
                    description
                      "Configure peer IPv4 address on this interface";
                    container ipv4-address-prefixes {
                      description
                        "Enter IPv4 address with prefix";
                      list ipv4-address-prefix {
                        key "address length";
                        description
                          "Enter IPv4 address with prefix";
                        leaf address {
                          type inet:ipv4-address-no-zone;
                          description
                            "Enter IPv4 address with prefix";
                        }
                        leaf length {
                          type uint32 {
                            range "0..32";
                          }
                          description
                            "Enter IPv4 address with prefix";
                        }
                      }
                    }
                    container ipv4-addresses {
                      description
                        "Enter IPv4 address";
                      list ipv4-address {
                        key "address";
                        description
                          "Enter IPv4 address";
                        leaf address {
                          type inet:ipv4-address-no-zone;
                          description
                            "Enter IPv4 address";
                        }
                      }
                    }
                  }
                  container ipv6 {
                    description
                      "Configure peer IPv6 address on this interface";
                    container ipv6-address-prefixes {
                      description
                        "Enter IPv6 address with prefix";
                      list ipv6-address-prefix {
                        key "address length";
                        description
                          "Enter IPv6 address with prefix";
                        leaf address {
                          type inet:ipv6-address-no-zone;
                          description
                            "Enter IPv6 address with prefix";
                        }
                        leaf length {
                          type uint32 {
                            range "0..128";
                          }
                          description
                            "Enter IPv6 address with prefix";
                        }
                      }
                    }
                    container ipv6-addresses {
                      description
                        "Enter IPv6 address";
                      list ipv6-address {
                        key "address";
                        description
                          "Enter IPv6 address";
                        leaf address {
                          type inet:ipv6-address-no-zone;
                          description
                            "Enter IPv6 address";
                        }
                      }
                    }
                  }
                }
              }
              container netconf {
                presence "Indicates a netconf node is configured.";
                description
                  "NETCONF version 1.1 protocol";
              }
              container netconf-peer {
                description
                  "Configure peer address on this interface";
                container address {
                  description
                    "Configure peer address on this interface";
                  container ipv4 {
                    description
                      "Configure peer IPv4 address on this interface";
                    container ipv4-address-prefixes {
                      description
                        "Enter IPv4 address with prefix";
                      list ipv4-address-prefix {
                        key "address length";
                        description
                          "Enter IPv4 address with prefix";
                        leaf address {
                          type inet:ipv4-address-no-zone;
                          description
                            "Enter IPv4 address with prefix";
                        }
                        leaf length {
                          type uint32 {
                            range "0..32";
                          }
                          description
                            "Enter IPv4 address with prefix";
                        }
                      }
                    }
                    container ipv4-addresses {
                      description
                        "Enter IPv4 address";
                      list ipv4-address {
                        key "address";
                        description
                          "Enter IPv4 address";
                        leaf address {
                          type inet:ipv4-address-no-zone;
                          description
                            "Enter IPv4 address";
                        }
                      }
                    }
                  }
                  container ipv6 {
                    description
                      "Configure peer IPv6 address on this interface";
                    container ipv6-address-prefixes {
                      description
                        "Enter IPv6 address with prefix";
                      list ipv6-address-prefix {
                        key "address length";
                        description
                          "Enter IPv6 address with prefix";
                        leaf address {
                          type inet:ipv6-address-no-zone;
                          description
                            "Enter IPv6 address with prefix";
                        }
                        leaf length {
                          type uint32 {
                            range "0..128";
                          }
                          description
                            "Enter IPv6 address with prefix";
                        }
                      }
                    }
                    container ipv6-addresses {
                      description
                        "Enter IPv6 address";
                      list ipv6-address {
                        key "address";
                        description
                          "Enter IPv6 address";
                        leaf address {
                          type inet:ipv6-address-no-zone;
                          description
                            "Enter IPv6 address";
                        }
                      }
                    }
                  }
                }
              }
              container all {
                presence "Indicates a all node is configured.";
                description
                  "All Protocols";
              }
              container all-peer {
                description
                  "Configure peer address on this interface";
                container address {
                  description
                    "Configure peer address on this interface";
                  container ipv4 {
                    description
                      "Configure peer IPv4 address on this interface";
                    container ipv4-address-prefixes {
                      description
                        "Enter IPv4 address with prefix";
                      list ipv4-address-prefix {
                        key "address length";
                        description
                          "Enter IPv4 address with prefix";
                        leaf address {
                          type inet:ipv4-address-no-zone;
                          description
                            "Enter IPv4 address with prefix";
                        }
                        leaf length {
                          type uint32 {
                            range "0..32";
                          }
                          description
                            "Enter IPv4 address with prefix";
                        }
                      }
                    }
                    container ipv4-addresses {
                      description
                        "Enter IPv4 address";
                      list ipv4-address {
                        key "address";
                        description
                          "Enter IPv4 address";
                        leaf address {
                          type inet:ipv4-address-no-zone;
                          description
                            "Enter IPv4 address";
                        }
                      }
                    }
                  }
                  container ipv6 {
                    description
                      "Configure peer IPv6 address on this interface";
                    container ipv6-address-prefixes {
                      description
                        "Enter IPv6 address with prefix";
                      list ipv6-address-prefix {
                        key "address length";
                        description
                          "Enter IPv6 address with prefix";
                        leaf address {
                          type inet:ipv6-address-no-zone;
                          description
                            "Enter IPv6 address with prefix";
                        }
                        leaf length {
                          type uint32 {
                            range "0..128";
                          }
                          description
                            "Enter IPv6 address with prefix";
                        }
                      }
                    }
                    container ipv6-addresses {
                      description
                        "Enter IPv6 address";
                      list ipv6-address {
                        key "address";
                        description
                          "Enter IPv6 address";
                        leaf address {
                          type inet:ipv6-address-no-zone;
                          description
                            "Enter IPv6 address";
                        }
                      }
                    }
                  }
                }
              }
            }
          }
          container all {
            description
              "configure all the interfaces";
            container allow {
              description
                "Allow a protocol on this interface";
              container ssh {
                presence "Indicates a ssh node is configured.";
                description
                  "Secure Shell (v1 & v2)";
              }
              container ssh-peer {
                description
                  "Configure peer address on this interface";
                container address {
                  description
                    "Configure peer address on this interface";
                  container ipv4 {
                    description
                      "Configure peer IPv4 address on this interface";
                    container ipv4-address-prefixes {
                      description
                        "Enter IPv4 address with prefix";
                      list ipv4-address-prefix {
                        key "address length";
                        description
                          "Enter IPv4 address with prefix";
                        leaf address {
                          type inet:ipv4-address-no-zone;
                          description
                            "Enter IPv4 address with prefix";
                        }
                        leaf length {
                          type uint32 {
                            range "0..32";
                          }
                          description
                            "Enter IPv4 address with prefix";
                        }
                      }
                    }
                    container ipv4-addresses {
                      description
                        "Enter IPv4 address";
                      list ipv4-address {
                        key "address";
                        description
                          "Enter IPv4 address";
                        leaf address {
                          type inet:ipv4-address-no-zone;
                          description
                            "Enter IPv4 address";
                        }
                      }
                    }
                  }
                  container ipv6 {
                    description
                      "Configure peer IPv6 address on this interface";
                    container ipv6-address-prefixes {
                      description
                        "Enter IPv6 address with prefix";
                      list ipv6-address-prefix {
                        key "address length";
                        description
                          "Enter IPv6 address with prefix";
                        leaf address {
                          type inet:ipv6-address-no-zone;
                          description
                            "Enter IPv6 address with prefix";
                        }
                        leaf length {
                          type uint32 {
                            range "0..128";
                          }
                          description
                            "Enter IPv6 address with prefix";
                        }
                      }
                    }
                    container ipv6-addresses {
                      description
                        "Enter IPv6 address";
                      list ipv6-address {
                        key "address";
                        description
                          "Enter IPv6 address";
                        leaf address {
                          type inet:ipv6-address-no-zone;
                          description
                            "Enter IPv6 address";
                        }
                      }
                    }
                  }
                }
              }
              container telnet {
                presence "Indicates a telnet node is configured.";
                description
                  "Telnet";
              }
              container telnet-peer {
                description
                  "Configure peer address on this interface";
                container address {
                  description
                    "Configure peer address on this interface";
                  container ipv4 {
                    description
                      "Configure peer IPv4 address on this interface";
                    container ipv4-address-prefixes {
                      description
                        "Enter IPv4 address with prefix";
                      list ipv4-address-prefix {
                        key "address length";
                        description
                          "Enter IPv4 address with prefix";
                        leaf address {
                          type inet:ipv4-address-no-zone;
                          description
                            "Enter IPv4 address with prefix";
                        }
                        leaf length {
                          type uint32 {
                            range "0..32";
                          }
                          description
                            "Enter IPv4 address with prefix";
                        }
                      }
                    }
                    container ipv4-addresses {
                      description
                        "Enter IPv4 address";
                      list ipv4-address {
                        key "address";
                        description
                          "Enter IPv4 address";
                        leaf address {
                          type inet:ipv4-address-no-zone;
                          description
                            "Enter IPv4 address";
                        }
                      }
                    }
                  }
                  container ipv6 {
                    description
                      "Configure peer IPv6 address on this interface";
                    container ipv6-address-prefixes {
                      description
                        "Enter IPv6 address with prefix";
                      list ipv6-address-prefix {
                        key "address length";
                        description
                          "Enter IPv6 address with prefix";
                        leaf address {
                          type inet:ipv6-address-no-zone;
                          description
                            "Enter IPv6 address with prefix";
                        }
                        leaf length {
                          type uint32 {
                            range "0..128";
                          }
                          description
                            "Enter IPv6 address with prefix";
                        }
                      }
                    }
                    container ipv6-addresses {
                      description
                        "Enter IPv6 address";
                      list ipv6-address {
                        key "address";
                        description
                          "Enter IPv6 address";
                        leaf address {
                          type inet:ipv6-address-no-zone;
                          description
                            "Enter IPv6 address";
                        }
                      }
                    }
                  }
                }
              }
              container snmp {
                presence "Indicates a snmp node is configured.";
                description
                  "SNMP (all versions)";
              }
              container snmp-peer {
                description
                  "Configure peer address on this interface";
                container address {
                  description
                    "Configure peer address on this interface";
                  container ipv4 {
                    description
                      "Configure peer IPv4 address on this interface";
                    container ipv4-address-prefixes {
                      description
                        "Enter IPv4 address with prefix";
                      list ipv4-address-prefix {
                        key "address length";
                        description
                          "Enter IPv4 address with prefix";
                        leaf address {
                          type inet:ipv4-address-no-zone;
                          description
                            "Enter IPv4 address with prefix";
                        }
                        leaf length {
                          type uint32 {
                            range "0..32";
                          }
                          description
                            "Enter IPv4 address with prefix";
                        }
                      }
                    }
                    container ipv4-addresses {
                      description
                        "Enter IPv4 address";
                      list ipv4-address {
                        key "address";
                        description
                          "Enter IPv4 address";
                        leaf address {
                          type inet:ipv4-address-no-zone;
                          description
                            "Enter IPv4 address";
                        }
                      }
                    }
                  }
                  container ipv6 {
                    description
                      "Configure peer IPv6 address on this interface";
                    container ipv6-address-prefixes {
                      description
                        "Enter IPv6 address with prefix";
                      list ipv6-address-prefix {
                        key "address length";
                        description
                          "Enter IPv6 address with prefix";
                        leaf address {
                          type inet:ipv6-address-no-zone;
                          description
                            "Enter IPv6 address with prefix";
                        }
                        leaf length {
                          type uint32 {
                            range "0..128";
                          }
                          description
                            "Enter IPv6 address with prefix";
                        }
                      }
                    }
                    container ipv6-addresses {
                      description
                        "Enter IPv6 address";
                      list ipv6-address {
                        key "address";
                        description
                          "Enter IPv6 address";
                        leaf address {
                          type inet:ipv6-address-no-zone;
                          description
                            "Enter IPv6 address";
                        }
                      }
                    }
                  }
                }
              }
              container tftp {
                presence "Indicates a tftp node is configured.";
                description
                  "Enable TFTP";
              }
              container tftp-peer {
                description
                  "Configure peer address on this interface";
                container address {
                  description
                    "Configure peer address on this interface";
                  container ipv4 {
                    description
                      "Configure peer IPv4 address on this interface";
                    container ipv4-address-prefixes {
                      description
                        "Enter IPv4 address with prefix";
                      list ipv4-address-prefix {
                        key "address length";
                        description
                          "Enter IPv4 address with prefix";
                        leaf address {
                          type inet:ipv4-address-no-zone;
                          description
                            "Enter IPv4 address with prefix";
                        }
                        leaf length {
                          type uint32 {
                            range "0..32";
                          }
                          description
                            "Enter IPv4 address with prefix";
                        }
                      }
                    }
                    container ipv4-addresses {
                      description
                        "Enter IPv4 address";
                      list ipv4-address {
                        key "address";
                        description
                          "Enter IPv4 address";
                        leaf address {
                          type inet:ipv4-address-no-zone;
                          description
                            "Enter IPv4 address";
                        }
                      }
                    }
                  }
                  container ipv6 {
                    description
                      "Configure peer IPv6 address on this interface";
                    container ipv6-address-prefixes {
                      description
                        "Enter IPv6 address with prefix";
                      list ipv6-address-prefix {
                        key "address length";
                        description
                          "Enter IPv6 address with prefix";
                        leaf address {
                          type inet:ipv6-address-no-zone;
                          description
                            "Enter IPv6 address with prefix";
                        }
                        leaf length {
                          type uint32 {
                            range "0..128";
                          }
                          description
                            "Enter IPv6 address with prefix";
                        }
                      }
                    }
                    container ipv6-addresses {
                      description
                        "Enter IPv6 address";
                      list ipv6-address {
                        key "address";
                        description
                          "Enter IPv6 address";
                        leaf address {
                          type inet:ipv6-address-no-zone;
                          description
                            "Enter IPv6 address";
                        }
                      }
                    }
                  }
                }
              }
              container http {
                presence "Indicates a http node is configured.";
                description
                  "HTTP(S)";
              }
              container http-peer {
                description
                  "Configure peer address on this interface";
                container address {
                  description
                    "Configure peer address on this interface";
                  container ipv4 {
                    description
                      "Configure peer IPv4 address on this interface";
                    container ipv4-address-prefixes {
                      description
                        "Enter IPv4 address with prefix";
                      list ipv4-address-prefix {
                        key "address length";
                        description
                          "Enter IPv4 address with prefix";
                        leaf address {
                          type inet:ipv4-address-no-zone;
                          description
                            "Enter IPv4 address with prefix";
                        }
                        leaf length {
                          type uint32 {
                            range "0..32";
                          }
                          description
                            "Enter IPv4 address with prefix";
                        }
                      }
                    }
                    container ipv4-addresses {
                      description
                        "Enter IPv4 address";
                      list ipv4-address {
                        key "address";
                        description
                          "Enter IPv4 address";
                        leaf address {
                          type inet:ipv4-address-no-zone;
                          description
                            "Enter IPv4 address";
                        }
                      }
                    }
                  }
                  container ipv6 {
                    description
                      "Configure peer IPv6 address on this interface";
                    container ipv6-address-prefixes {
                      description
                        "Enter IPv6 address with prefix";
                      list ipv6-address-prefix {
                        key "address length";
                        description
                          "Enter IPv6 address with prefix";
                        leaf address {
                          type inet:ipv6-address-no-zone;
                          description
                            "Enter IPv6 address with prefix";
                        }
                        leaf length {
                          type uint32 {
                            range "0..128";
                          }
                          description
                            "Enter IPv6 address with prefix";
                        }
                      }
                    }
                    container ipv6-addresses {
                      description
                        "Enter IPv6 address";
                      list ipv6-address {
                        key "address";
                        description
                          "Enter IPv6 address";
                        leaf address {
                          type inet:ipv6-address-no-zone;
                          description
                            "Enter IPv6 address";
                        }
                      }
                    }
                  }
                }
              }
              container xr-xml {
                presence "Indicates a xr-xml node is configured.";
                description
                  "XML";
              }
              container xr-xml-peer {
                description
                  "Configure peer address on this interface";
                container address {
                  description
                    "Configure peer address on this interface";
                  container ipv4 {
                    description
                      "Configure peer IPv4 address on this interface";
                    container ipv4-address-prefixes {
                      description
                        "Enter IPv4 address with prefix";
                      list ipv4-address-prefix {
                        key "address length";
                        description
                          "Enter IPv4 address with prefix";
                        leaf address {
                          type inet:ipv4-address-no-zone;
                          description
                            "Enter IPv4 address with prefix";
                        }
                        leaf length {
                          type uint32 {
                            range "0..32";
                          }
                          description
                            "Enter IPv4 address with prefix";
                        }
                      }
                    }
                    container ipv4-addresses {
                      description
                        "Enter IPv4 address";
                      list ipv4-address {
                        key "address";
                        description
                          "Enter IPv4 address";
                        leaf address {
                          type inet:ipv4-address-no-zone;
                          description
                            "Enter IPv4 address";
                        }
                      }
                    }
                  }
                  container ipv6 {
                    description
                      "Configure peer IPv6 address on this interface";
                    container ipv6-address-prefixes {
                      description
                        "Enter IPv6 address with prefix";
                      list ipv6-address-prefix {
                        key "address length";
                        description
                          "Enter IPv6 address with prefix";
                        leaf address {
                          type inet:ipv6-address-no-zone;
                          description
                            "Enter IPv6 address with prefix";
                        }
                        leaf length {
                          type uint32 {
                            range "0..128";
                          }
                          description
                            "Enter IPv6 address with prefix";
                        }
                      }
                    }
                    container ipv6-addresses {
                      description
                        "Enter IPv6 address";
                      list ipv6-address {
                        key "address";
                        description
                          "Enter IPv6 address";
                        leaf address {
                          type inet:ipv6-address-no-zone;
                          description
                            "Enter IPv6 address";
                        }
                      }
                    }
                  }
                }
              }
              container netconf {
                presence "Indicates a netconf node is configured.";
                description
                  "NETCONF version 1.1 protocol";
              }
              container netconf-peer {
                description
                  "Configure peer address on this interface";
                container address {
                  description
                    "Configure peer address on this interface";
                  container ipv4 {
                    description
                      "Configure peer IPv4 address on this interface";
                    container ipv4-address-prefixes {
                      description
                        "Enter IPv4 address with prefix";
                      list ipv4-address-prefix {
                        key "address length";
                        description
                          "Enter IPv4 address with prefix";
                        leaf address {
                          type inet:ipv4-address-no-zone;
                          description
                            "Enter IPv4 address with prefix";
                        }
                        leaf length {
                          type uint32 {
                            range "0..32";
                          }
                          description
                            "Enter IPv4 address with prefix";
                        }
                      }
                    }
                    container ipv4-addresses {
                      description
                        "Enter IPv4 address";
                      list ipv4-address {
                        key "address";
                        description
                          "Enter IPv4 address";
                        leaf address {
                          type inet:ipv4-address-no-zone;
                          description
                            "Enter IPv4 address";
                        }
                      }
                    }
                  }
                  container ipv6 {
                    description
                      "Configure peer IPv6 address on this interface";
                    container ipv6-address-prefixes {
                      description
                        "Enter IPv6 address with prefix";
                      list ipv6-address-prefix {
                        key "address length";
                        description
                          "Enter IPv6 address with prefix";
                        leaf address {
                          type inet:ipv6-address-no-zone;
                          description
                            "Enter IPv6 address with prefix";
                        }
                        leaf length {
                          type uint32 {
                            range "0..128";
                          }
                          description
                            "Enter IPv6 address with prefix";
                        }
                      }
                    }
                    container ipv6-addresses {
                      description
                        "Enter IPv6 address";
                      list ipv6-address {
                        key "address";
                        description
                          "Enter IPv6 address";
                        leaf address {
                          type inet:ipv6-address-no-zone;
                          description
                            "Enter IPv6 address";
                        }
                      }
                    }
                  }
                }
              }
              container all {
                presence "Indicates a all node is configured.";
                description
                  "All Protocols";
              }
              container all-peer {
                description
                  "Configure peer address on this interface";
                container address {
                  description
                    "Configure peer address on this interface";
                  container ipv4 {
                    description
                      "Configure peer IPv4 address on this interface";
                    container ipv4-address-prefixes {
                      description
                        "Enter IPv4 address with prefix";
                      list ipv4-address-prefix {
                        key "address length";
                        description
                          "Enter IPv4 address with prefix";
                        leaf address {
                          type inet:ipv4-address-no-zone;
                          description
                            "Enter IPv4 address with prefix";
                        }
                        leaf length {
                          type uint32 {
                            range "0..32";
                          }
                          description
                            "Enter IPv4 address with prefix";
                        }
                      }
                    }
                    container ipv4-addresses {
                      description
                        "Enter IPv4 address";
                      list ipv4-address {
                        key "address";
                        description
                          "Enter IPv4 address";
                        leaf address {
                          type inet:ipv4-address-no-zone;
                          description
                            "Enter IPv4 address";
                        }
                      }
                    }
                  }
                  container ipv6 {
                    description
                      "Configure peer IPv6 address on this interface";
                    container ipv6-address-prefixes {
                      description
                        "Enter IPv6 address with prefix";
                      list ipv6-address-prefix {
                        key "address length";
                        description
                          "Enter IPv6 address with prefix";
                        leaf address {
                          type inet:ipv6-address-no-zone;
                          description
                            "Enter IPv6 address with prefix";
                        }
                        leaf length {
                          type uint32 {
                            range "0..128";
                          }
                          description
                            "Enter IPv6 address with prefix";
                        }
                      }
                    }
                    container ipv6-addresses {
                      description
                        "Enter IPv6 address";
                      list ipv6-address {
                        key "address";
                        description
                          "Enter IPv6 address";
                        leaf address {
                          type inet:ipv6-address-no-zone;
                          description
                            "Enter IPv6 address";
                        }
                      }
                    }
                  }
                }
              }
            }
          }
        }
      }
      container out-of-band {
        description
          "Configure an out-of-band interface/protocol";
        container interfaces {
          description
            "Configure an outband interface";
          list interface {
            key "interface-name";
            description
              "Configure a specific interface";
            leaf interface-name {
              type xr:Interface-name;
              description
                "Configure a specific interface";
            }
            container allow {
              description
                "Allow a protocol on this interface";
              container ssh {
                presence "Indicates a ssh node is configured.";
                description
                  "Secure Shell (v1 & v2)";
              }
              container ssh-peer {
                description
                  "Configure peer address on this interface";
                container address {
                  description
                    "Configure peer address on this interface";
                  container ipv4 {
                    description
                      "Configure peer IPv4 address on this interface";
                    container ipv4-address-prefixes {
                      description
                        "Enter IPv4 address with prefix";
                      list ipv4-address-prefix {
                        key "address length";
                        description
                          "Enter IPv4 address with prefix";
                        leaf address {
                          type inet:ipv4-address-no-zone;
                          description
                            "Enter IPv4 address with prefix";
                        }
                        leaf length {
                          type uint32 {
                            range "0..32";
                          }
                          description
                            "Enter IPv4 address with prefix";
                        }
                      }
                    }
                    container ipv4-addresses {
                      description
                        "Enter IPv4 address";
                      list ipv4-address {
                        key "address";
                        description
                          "Enter IPv4 address";
                        leaf address {
                          type inet:ipv4-address-no-zone;
                          description
                            "Enter IPv4 address";
                        }
                      }
                    }
                  }
                  container ipv6 {
                    description
                      "Configure peer IPv6 address on this interface";
                    container ipv6-address-prefixes {
                      description
                        "Enter IPv6 address with prefix";
                      list ipv6-address-prefix {
                        key "address length";
                        description
                          "Enter IPv6 address with prefix";
                        leaf address {
                          type inet:ipv6-address-no-zone;
                          description
                            "Enter IPv6 address with prefix";
                        }
                        leaf length {
                          type uint32 {
                            range "0..128";
                          }
                          description
                            "Enter IPv6 address with prefix";
                        }
                      }
                    }
                    container ipv6-addresses {
                      description
                        "Enter IPv6 address";
                      list ipv6-address {
                        key "address";
                        description
                          "Enter IPv6 address";
                        leaf address {
                          type inet:ipv6-address-no-zone;
                          description
                            "Enter IPv6 address";
                        }
                      }
                    }
                  }
                }
              }
              container telnet {
                presence "Indicates a telnet node is configured.";
                description
                  "Telnet";
              }
              container telnet-peer {
                description
                  "Configure peer address on this interface";
                container address {
                  description
                    "Configure peer address on this interface";
                  container ipv4 {
                    description
                      "Configure peer IPv4 address on this interface";
                    container ipv4-address-prefixes {
                      description
                        "Enter IPv4 address with prefix";
                      list ipv4-address-prefix {
                        key "address length";
                        description
                          "Enter IPv4 address with prefix";
                        leaf address {
                          type inet:ipv4-address-no-zone;
                          description
                            "Enter IPv4 address with prefix";
                        }
                        leaf length {
                          type uint32 {
                            range "0..32";
                          }
                          description
                            "Enter IPv4 address with prefix";
                        }
                      }
                    }
                    container ipv4-addresses {
                      description
                        "Enter IPv4 address";
                      list ipv4-address {
                        key "address";
                        description
                          "Enter IPv4 address";
                        leaf address {
                          type inet:ipv4-address-no-zone;
                          description
                            "Enter IPv4 address";
                        }
                      }
                    }
                  }
                  container ipv6 {
                    description
                      "Configure peer IPv6 address on this interface";
                    container ipv6-address-prefixes {
                      description
                        "Enter IPv6 address with prefix";
                      list ipv6-address-prefix {
                        key "address length";
                        description
                          "Enter IPv6 address with prefix";
                        leaf address {
                          type inet:ipv6-address-no-zone;
                          description
                            "Enter IPv6 address with prefix";
                        }
                        leaf length {
                          type uint32 {
                            range "0..128";
                          }
                          description
                            "Enter IPv6 address with prefix";
                        }
                      }
                    }
                    container ipv6-addresses {
                      description
                        "Enter IPv6 address";
                      list ipv6-address {
                        key "address";
                        description
                          "Enter IPv6 address";
                        leaf address {
                          type inet:ipv6-address-no-zone;
                          description
                            "Enter IPv6 address";
                        }
                      }
                    }
                  }
                }
              }
              container snmp {
                presence "Indicates a snmp node is configured.";
                description
                  "SNMP (all versions)";
              }
              container snmp-peer {
                description
                  "Configure peer address on this interface";
                container address {
                  description
                    "Configure peer address on this interface";
                  container ipv4 {
                    description
                      "Configure peer IPv4 address on this interface";
                    container ipv4-address-prefixes {
                      description
                        "Enter IPv4 address with prefix";
                      list ipv4-address-prefix {
                        key "address length";
                        description
                          "Enter IPv4 address with prefix";
                        leaf address {
                          type inet:ipv4-address-no-zone;
                          description
                            "Enter IPv4 address with prefix";
                        }
                        leaf length {
                          type uint32 {
                            range "0..32";
                          }
                          description
                            "Enter IPv4 address with prefix";
                        }
                      }
                    }
                    container ipv4-addresses {
                      description
                        "Enter IPv4 address";
                      list ipv4-address {
                        key "address";
                        description
                          "Enter IPv4 address";
                        leaf address {
                          type inet:ipv4-address-no-zone;
                          description
                            "Enter IPv4 address";
                        }
                      }
                    }
                  }
                  container ipv6 {
                    description
                      "Configure peer IPv6 address on this interface";
                    container ipv6-address-prefixes {
                      description
                        "Enter IPv6 address with prefix";
                      list ipv6-address-prefix {
                        key "address length";
                        description
                          "Enter IPv6 address with prefix";
                        leaf address {
                          type inet:ipv6-address-no-zone;
                          description
                            "Enter IPv6 address with prefix";
                        }
                        leaf length {
                          type uint32 {
                            range "0..128";
                          }
                          description
                            "Enter IPv6 address with prefix";
                        }
                      }
                    }
                    container ipv6-addresses {
                      description
                        "Enter IPv6 address";
                      list ipv6-address {
                        key "address";
                        description
                          "Enter IPv6 address";
                        leaf address {
                          type inet:ipv6-address-no-zone;
                          description
                            "Enter IPv6 address";
                        }
                      }
                    }
                  }
                }
              }
              container tftp {
                presence "Indicates a tftp node is configured.";
                description
                  "TFTP";
              }
              container tftp-peer {
                description
                  "Configure peer address on this interface";
                container address {
                  description
                    "Configure peer address on this interface";
                  container ipv4 {
                    description
                      "Configure peer IPv4 address on this interface";
                    container ipv4-address-prefixes {
                      description
                        "Enter IPv4 address with prefix";
                      list ipv4-address-prefix {
                        key "address length";
                        description
                          "Enter IPv4 address with prefix";
                        leaf address {
                          type inet:ipv4-address-no-zone;
                          description
                            "Enter IPv4 address with prefix";
                        }
                        leaf length {
                          type uint32 {
                            range "0..32";
                          }
                          description
                            "Enter IPv4 address with prefix";
                        }
                      }
                    }
                    container ipv4-addresses {
                      description
                        "Enter IPv4 address";
                      list ipv4-address {
                        key "address";
                        description
                          "Enter IPv4 address";
                        leaf address {
                          type inet:ipv4-address-no-zone;
                          description
                            "Enter IPv4 address";
                        }
                      }
                    }
                  }
                  container ipv6 {
                    description
                      "Configure peer IPv6 address on this interface";
                    container ipv6-address-prefixes {
                      description
                        "Enter IPv6 address with prefix";
                      list ipv6-address-prefix {
                        key "address length";
                        description
                          "Enter IPv6 address with prefix";
                        leaf address {
                          type inet:ipv6-address-no-zone;
                          description
                            "Enter IPv6 address with prefix";
                        }
                        leaf length {
                          type uint32 {
                            range "0..128";
                          }
                          description
                            "Enter IPv6 address with prefix";
                        }
                      }
                    }
                    container ipv6-addresses {
                      description
                        "Enter IPv6 address";
                      list ipv6-address {
                        key "address";
                        description
                          "Enter IPv6 address";
                        leaf address {
                          type inet:ipv6-address-no-zone;
                          description
                            "Enter IPv6 address";
                        }
                      }
                    }
                  }
                }
              }
              container http {
                presence "Indicates a http node is configured.";
                description
                  "HTTP(S)";
              }
              container http-peer {
                description
                  "Configure peer address on this interface";
                container address {
                  description
                    "Configure peer address on this interface";
                  container ipv4 {
                    description
                      "Configure peer IPv4 address on this interface";
                    container ipv4-address-prefixes {
                      description
                        "Enter IPv4 address with prefix";
                      list ipv4-address-prefix {
                        key "address length";
                        description
                          "Enter IPv4 address with prefix";
                        leaf address {
                          type inet:ipv4-address-no-zone;
                          description
                            "Enter IPv4 address with prefix";
                        }
                        leaf length {
                          type uint32 {
                            range "0..32";
                          }
                          description
                            "Enter IPv4 address with prefix";
                        }
                      }
                    }
                    container ipv4-addresses {
                      description
                        "Enter IPv4 address";
                      list ipv4-address {
                        key "address";
                        description
                          "Enter IPv4 address";
                        leaf address {
                          type inet:ipv4-address-no-zone;
                          description
                            "Enter IPv4 address";
                        }
                      }
                    }
                  }
                  container ipv6 {
                    description
                      "Configure peer IPv6 address on this interface";
                    container ipv6-address-prefixes {
                      description
                        "Enter IPv6 address with prefix";
                      list ipv6-address-prefix {
                        key "address length";
                        description
                          "Enter IPv6 address with prefix";
                        leaf address {
                          type inet:ipv6-address-no-zone;
                          description
                            "Enter IPv6 address with prefix";
                        }
                        leaf length {
                          type uint32 {
                            range "0..128";
                          }
                          description
                            "Enter IPv6 address with prefix";
                        }
                      }
                    }
                    container ipv6-addresses {
                      description
                        "Enter IPv6 address";
                      list ipv6-address {
                        key "address";
                        description
                          "Enter IPv6 address";
                        leaf address {
                          type inet:ipv6-address-no-zone;
                          description
                            "Enter IPv6 address";
                        }
                      }
                    }
                  }
                }
              }
              container xr-xml {
                presence "Indicates a xr-xml node is configured.";
                description
                  "XML";
              }
              container xr-xml-peer {
                description
                  "Configure peer address on this interface";
                container address {
                  description
                    "Configure peer address on this interface";
                  container ipv4 {
                    description
                      "Configure peer IPv4 address on this interface";
                    container ipv4-address-prefixes {
                      description
                        "Enter IPv4 address with prefix";
                      list ipv4-address-prefix {
                        key "address length";
                        description
                          "Enter IPv4 address with prefix";
                        leaf address {
                          type inet:ipv4-address-no-zone;
                          description
                            "Enter IPv4 address with prefix";
                        }
                        leaf length {
                          type uint32 {
                            range "0..32";
                          }
                          description
                            "Enter IPv4 address with prefix";
                        }
                      }
                    }
                    container ipv4-addresses {
                      description
                        "Enter IPv4 address";
                      list ipv4-address {
                        key "address";
                        description
                          "Enter IPv4 address";
                        leaf address {
                          type inet:ipv4-address-no-zone;
                          description
                            "Enter IPv4 address";
                        }
                      }
                    }
                  }
                  container ipv6 {
                    description
                      "Configure peer IPv6 address on this interface";
                    container ipv6-address-prefixes {
                      description
                        "Enter IPv6 address with prefix";
                      list ipv6-address-prefix {
                        key "address length";
                        description
                          "Enter IPv6 address with prefix";
                        leaf address {
                          type inet:ipv6-address-no-zone;
                          description
                            "Enter IPv6 address with prefix";
                        }
                        leaf length {
                          type uint32 {
                            range "0..128";
                          }
                          description
                            "Enter IPv6 address with prefix";
                        }
                      }
                    }
                    container ipv6-addresses {
                      description
                        "Enter IPv6 address";
                      list ipv6-address {
                        key "address";
                        description
                          "Enter IPv6 address";
                        leaf address {
                          type inet:ipv6-address-no-zone;
                          description
                            "Enter IPv6 address";
                        }
                      }
                    }
                  }
                }
              }
              container netconf {
                presence "Indicates a netconf node is configured.";
                description
                  "NETCONF version 1.1 protocol";
              }
              container netconf-peer {
                description
                  "Configure peer address on this interface";
                container address {
                  description
                    "Configure peer address on this interface";
                  container ipv4 {
                    description
                      "Configure peer IPv4 address on this interface";
                    container ipv4-address-prefixes {
                      description
                        "Enter IPv4 address with prefix";
                      list ipv4-address-prefix {
                        key "address length";
                        description
                          "Enter IPv4 address with prefix";
                        leaf address {
                          type inet:ipv4-address-no-zone;
                          description
                            "Enter IPv4 address with prefix";
                        }
                        leaf length {
                          type uint32 {
                            range "0..32";
                          }
                          description
                            "Enter IPv4 address with prefix";
                        }
                      }
                    }
                    container ipv4-addresses {
                      description
                        "Enter IPv4 address";
                      list ipv4-address {
                        key "address";
                        description
                          "Enter IPv4 address";
                        leaf address {
                          type inet:ipv4-address-no-zone;
                          description
                            "Enter IPv4 address";
                        }
                      }
                    }
                  }
                  container ipv6 {
                    description
                      "Configure peer IPv6 address on this interface";
                    container ipv6-address-prefixes {
                      description
                        "Enter IPv6 address with prefix";
                      list ipv6-address-prefix {
                        key "address length";
                        description
                          "Enter IPv6 address with prefix";
                        leaf address {
                          type inet:ipv6-address-no-zone;
                          description
                            "Enter IPv6 address with prefix";
                        }
                        leaf length {
                          type uint32 {
                            range "0..128";
                          }
                          description
                            "Enter IPv6 address with prefix";
                        }
                      }
                    }
                    container ipv6-addresses {
                      description
                        "Enter IPv6 address";
                      list ipv6-address {
                        key "address";
                        description
                          "Enter IPv6 address";
                        leaf address {
                          type inet:ipv6-address-no-zone;
                          description
                            "Enter IPv6 address";
                        }
                      }
                    }
                  }
                }
              }
              container all {
                presence "Indicates a all node is configured.";
                description
                  "All Protocols";
              }
              container all-peer {
                description
                  "Configure peer address on this interface";
                container address {
                  description
                    "Configure peer address on this interface";
                  container ipv4 {
                    description
                      "Configure peer IPv4 address on this interface";
                    container ipv4-address-prefixes {
                      description
                        "Enter IPv4 address with prefix";
                      list ipv4-address-prefix {
                        key "address length";
                        description
                          "Enter IPv4 address with prefix";
                        leaf address {
                          type inet:ipv4-address-no-zone;
                          description
                            "Enter IPv4 address with prefix";
                        }
                        leaf length {
                          type uint32 {
                            range "0..32";
                          }
                          description
                            "Enter IPv4 address with prefix";
                        }
                      }
                    }
                    container ipv4-addresses {
                      description
                        "Enter IPv4 address";
                      list ipv4-address {
                        key "address";
                        description
                          "Enter IPv4 address";
                        leaf address {
                          type inet:ipv4-address-no-zone;
                          description
                            "Enter IPv4 address";
                        }
                      }
                    }
                  }
                  container ipv6 {
                    description
                      "Configure peer IPv6 address on this interface";
                    container ipv6-address-prefixes {
                      description
                        "Enter IPv6 address with prefix";
                      list ipv6-address-prefix {
                        key "address length";
                        description
                          "Enter IPv6 address with prefix";
                        leaf address {
                          type inet:ipv6-address-no-zone;
                          description
                            "Enter IPv6 address with prefix";
                        }
                        leaf length {
                          type uint32 {
                            range "0..128";
                          }
                          description
                            "Enter IPv6 address with prefix";
                        }
                      }
                    }
                    container ipv6-addresses {
                      description
                        "Enter IPv6 address";
                      list ipv6-address {
                        key "address";
                        description
                          "Enter IPv6 address";
                        leaf address {
                          type inet:ipv6-address-no-zone;
                          description
                            "Enter IPv6 address";
                        }
                      }
                    }
                  }
                }
              }
            }
          }
          container all {
            description
              "configure all the interfaces";
            container allow {
              description
                "Allow a protocol on this interface";
              container ssh {
                presence "Indicates a ssh node is configured.";
                description
                  "Secure Shell (v1 & v2)";
              }
              container ssh-peer {
                description
                  "Configure peer address on this interface";
                container address {
                  description
                    "Configure peer address on this interface";
                  container ipv4 {
                    description
                      "Configure peer IPv4 address on this interface";
                    container ipv4-address-prefixes {
                      description
                        "Enter IPv4 address with prefix";
                      list ipv4-address-prefix {
                        key "address length";
                        description
                          "Enter IPv4 address with prefix";
                        leaf address {
                          type inet:ipv4-address-no-zone;
                          description
                            "Enter IPv4 address with prefix";
                        }
                        leaf length {
                          type uint32 {
                            range "0..32";
                          }
                          description
                            "Enter IPv4 address with prefix";
                        }
                      }
                    }
                    container ipv4-addresses {
                      description
                        "Enter IPv4 address";
                      list ipv4-address {
                        key "address";
                        description
                          "Enter IPv4 address";
                        leaf address {
                          type inet:ipv4-address-no-zone;
                          description
                            "Enter IPv4 address";
                        }
                      }
                    }
                  }
                  container ipv6 {
                    description
                      "Configure peer IPv6 address on this interface";
                    container ipv6-address-prefixes {
                      description
                        "Enter IPv6 address with prefix";
                      list ipv6-address-prefix {
                        key "address length";
                        description
                          "Enter IPv6 address with prefix";
                        leaf address {
                          type inet:ipv6-address-no-zone;
                          description
                            "Enter IPv6 address with prefix";
                        }
                        leaf length {
                          type uint32 {
                            range "0..128";
                          }
                          description
                            "Enter IPv6 address with prefix";
                        }
                      }
                    }
                    container ipv6-addresses {
                      description
                        "Enter IPv6 address";
                      list ipv6-address {
                        key "address";
                        description
                          "Enter IPv6 address";
                        leaf address {
                          type inet:ipv6-address-no-zone;
                          description
                            "Enter IPv6 address";
                        }
                      }
                    }
                  }
                }
              }
              container telnet {
                presence "Indicates a telnet node is configured.";
                description
                  "Telnet";
              }
              container telnet-peer {
                description
                  "Configure peer address on this interface";
                container address {
                  description
                    "Configure peer address on this interface";
                  container ipv4 {
                    description
                      "Configure peer IPv4 address on this interface";
                    container ipv4-address-prefixes {
                      description
                        "Enter IPv4 address with prefix";
                      list ipv4-address-prefix {
                        key "address length";
                        description
                          "Enter IPv4 address with prefix";
                        leaf address {
                          type inet:ipv4-address-no-zone;
                          description
                            "Enter IPv4 address with prefix";
                        }
                        leaf length {
                          type uint32 {
                            range "0..32";
                          }
                          description
                            "Enter IPv4 address with prefix";
                        }
                      }
                    }
                    container ipv4-addresses {
                      description
                        "Enter IPv4 address";
                      list ipv4-address {
                        key "address";
                        description
                          "Enter IPv4 address";
                        leaf address {
                          type inet:ipv4-address-no-zone;
                          description
                            "Enter IPv4 address";
                        }
                      }
                    }
                  }
                  container ipv6 {
                    description
                      "Configure peer IPv6 address on this interface";
                    container ipv6-address-prefixes {
                      description
                        "Enter IPv6 address with prefix";
                      list ipv6-address-prefix {
                        key "address length";
                        description
                          "Enter IPv6 address with prefix";
                        leaf address {
                          type inet:ipv6-address-no-zone;
                          description
                            "Enter IPv6 address with prefix";
                        }
                        leaf length {
                          type uint32 {
                            range "0..128";
                          }
                          description
                            "Enter IPv6 address with prefix";
                        }
                      }
                    }
                    container ipv6-addresses {
                      description
                        "Enter IPv6 address";
                      list ipv6-address {
                        key "address";
                        description
                          "Enter IPv6 address";
                        leaf address {
                          type inet:ipv6-address-no-zone;
                          description
                            "Enter IPv6 address";
                        }
                      }
                    }
                  }
                }
              }
              container snmp {
                presence "Indicates a snmp node is configured.";
                description
                  "SNMP (all versions)";
              }
              container snmp-peer {
                description
                  "Configure peer address on this interface";
                container address {
                  description
                    "Configure peer address on this interface";
                  container ipv4 {
                    description
                      "Configure peer IPv4 address on this interface";
                    container ipv4-address-prefixes {
                      description
                        "Enter IPv4 address with prefix";
                      list ipv4-address-prefix {
                        key "address length";
                        description
                          "Enter IPv4 address with prefix";
                        leaf address {
                          type inet:ipv4-address-no-zone;
                          description
                            "Enter IPv4 address with prefix";
                        }
                        leaf length {
                          type uint32 {
                            range "0..32";
                          }
                          description
                            "Enter IPv4 address with prefix";
                        }
                      }
                    }
                    container ipv4-addresses {
                      description
                        "Enter IPv4 address";
                      list ipv4-address {
                        key "address";
                        description
                          "Enter IPv4 address";
                        leaf address {
                          type inet:ipv4-address-no-zone;
                          description
                            "Enter IPv4 address";
                        }
                      }
                    }
                  }
                  container ipv6 {
                    description
                      "Configure peer IPv6 address on this interface";
                    container ipv6-address-prefixes {
                      description
                        "Enter IPv6 address with prefix";
                      list ipv6-address-prefix {
                        key "address length";
                        description
                          "Enter IPv6 address with prefix";
                        leaf address {
                          type inet:ipv6-address-no-zone;
                          description
                            "Enter IPv6 address with prefix";
                        }
                        leaf length {
                          type uint32 {
                            range "0..128";
                          }
                          description
                            "Enter IPv6 address with prefix";
                        }
                      }
                    }
                    container ipv6-addresses {
                      description
                        "Enter IPv6 address";
                      list ipv6-address {
                        key "address";
                        description
                          "Enter IPv6 address";
                        leaf address {
                          type inet:ipv6-address-no-zone;
                          description
                            "Enter IPv6 address";
                        }
                      }
                    }
                  }
                }
              }
              container tftp {
                presence "Indicates a tftp node is configured.";
                description
                  "TFTP";
              }
              container tftp-peer {
                description
                  "Configure peer address on this interface";
                container address {
                  description
                    "Configure peer address on this interface";
                  container ipv4 {
                    description
                      "Configure peer IPv4 address on this interface";
                    container ipv4-address-prefixes {
                      description
                        "Enter IPv4 address with prefix";
                      list ipv4-address-prefix {
                        key "address length";
                        description
                          "Enter IPv4 address with prefix";
                        leaf address {
                          type inet:ipv4-address-no-zone;
                          description
                            "Enter IPv4 address with prefix";
                        }
                        leaf length {
                          type uint32 {
                            range "0..32";
                          }
                          description
                            "Enter IPv4 address with prefix";
                        }
                      }
                    }
                    container ipv4-addresses {
                      description
                        "Enter IPv4 address";
                      list ipv4-address {
                        key "address";
                        description
                          "Enter IPv4 address";
                        leaf address {
                          type inet:ipv4-address-no-zone;
                          description
                            "Enter IPv4 address";
                        }
                      }
                    }
                  }
                  container ipv6 {
                    description
                      "Configure peer IPv6 address on this interface";
                    container ipv6-address-prefixes {
                      description
                        "Enter IPv6 address with prefix";
                      list ipv6-address-prefix {
                        key "address length";
                        description
                          "Enter IPv6 address with prefix";
                        leaf address {
                          type inet:ipv6-address-no-zone;
                          description
                            "Enter IPv6 address with prefix";
                        }
                        leaf length {
                          type uint32 {
                            range "0..128";
                          }
                          description
                            "Enter IPv6 address with prefix";
                        }
                      }
                    }
                    container ipv6-addresses {
                      description
                        "Enter IPv6 address";
                      list ipv6-address {
                        key "address";
                        description
                          "Enter IPv6 address";
                        leaf address {
                          type inet:ipv6-address-no-zone;
                          description
                            "Enter IPv6 address";
                        }
                      }
                    }
                  }
                }
              }
              container http {
                presence "Indicates a http node is configured.";
                description
                  "HTTP(S)";
              }
              container http-peer {
                description
                  "Configure peer address on this interface";
                container address {
                  description
                    "Configure peer address on this interface";
                  container ipv4 {
                    description
                      "Configure peer IPv4 address on this interface";
                    container ipv4-address-prefixes {
                      description
                        "Enter IPv4 address with prefix";
                      list ipv4-address-prefix {
                        key "address length";
                        description
                          "Enter IPv4 address with prefix";
                        leaf address {
                          type inet:ipv4-address-no-zone;
                          description
                            "Enter IPv4 address with prefix";
                        }
                        leaf length {
                          type uint32 {
                            range "0..32";
                          }
                          description
                            "Enter IPv4 address with prefix";
                        }
                      }
                    }
                    container ipv4-addresses {
                      description
                        "Enter IPv4 address";
                      list ipv4-address {
                        key "address";
                        description
                          "Enter IPv4 address";
                        leaf address {
                          type inet:ipv4-address-no-zone;
                          description
                            "Enter IPv4 address";
                        }
                      }
                    }
                  }
                  container ipv6 {
                    description
                      "Configure peer IPv6 address on this interface";
                    container ipv6-address-prefixes {
                      description
                        "Enter IPv6 address with prefix";
                      list ipv6-address-prefix {
                        key "address length";
                        description
                          "Enter IPv6 address with prefix";
                        leaf address {
                          type inet:ipv6-address-no-zone;
                          description
                            "Enter IPv6 address with prefix";
                        }
                        leaf length {
                          type uint32 {
                            range "0..128";
                          }
                          description
                            "Enter IPv6 address with prefix";
                        }
                      }
                    }
                    container ipv6-addresses {
                      description
                        "Enter IPv6 address";
                      list ipv6-address {
                        key "address";
                        description
                          "Enter IPv6 address";
                        leaf address {
                          type inet:ipv6-address-no-zone;
                          description
                            "Enter IPv6 address";
                        }
                      }
                    }
                  }
                }
              }
              container xr-xml {
                presence "Indicates a xr-xml node is configured.";
                description
                  "XML";
              }
              container xr-xml-peer {
                description
                  "Configure peer address on this interface";
                container address {
                  description
                    "Configure peer address on this interface";
                  container ipv4 {
                    description
                      "Configure peer IPv4 address on this interface";
                    container ipv4-address-prefixes {
                      description
                        "Enter IPv4 address with prefix";
                      list ipv4-address-prefix {
                        key "address length";
                        description
                          "Enter IPv4 address with prefix";
                        leaf address {
                          type inet:ipv4-address-no-zone;
                          description
                            "Enter IPv4 address with prefix";
                        }
                        leaf length {
                          type uint32 {
                            range "0..32";
                          }
                          description
                            "Enter IPv4 address with prefix";
                        }
                      }
                    }
                    container ipv4-addresses {
                      description
                        "Enter IPv4 address";
                      list ipv4-address {
                        key "address";
                        description
                          "Enter IPv4 address";
                        leaf address {
                          type inet:ipv4-address-no-zone;
                          description
                            "Enter IPv4 address";
                        }
                      }
                    }
                  }
                  container ipv6 {
                    description
                      "Configure peer IPv6 address on this interface";
                    container ipv6-address-prefixes {
                      description
                        "Enter IPv6 address with prefix";
                      list ipv6-address-prefix {
                        key "address length";
                        description
                          "Enter IPv6 address with prefix";
                        leaf address {
                          type inet:ipv6-address-no-zone;
                          description
                            "Enter IPv6 address with prefix";
                        }
                        leaf length {
                          type uint32 {
                            range "0..128";
                          }
                          description
                            "Enter IPv6 address with prefix";
                        }
                      }
                    }
                    container ipv6-addresses {
                      description
                        "Enter IPv6 address";
                      list ipv6-address {
                        key "address";
                        description
                          "Enter IPv6 address";
                        leaf address {
                          type inet:ipv6-address-no-zone;
                          description
                            "Enter IPv6 address";
                        }
                      }
                    }
                  }
                }
              }
              container netconf {
                presence "Indicates a netconf node is configured.";
                description
                  "NETCONF version 1.1 protocol";
              }
              container netconf-peer {
                description
                  "Configure peer address on this interface";
                container address {
                  description
                    "Configure peer address on this interface";
                  container ipv4 {
                    description
                      "Configure peer IPv4 address on this interface";
                    container ipv4-address-prefixes {
                      description
                        "Enter IPv4 address with prefix";
                      list ipv4-address-prefix {
                        key "address length";
                        description
                          "Enter IPv4 address with prefix";
                        leaf address {
                          type inet:ipv4-address-no-zone;
                          description
                            "Enter IPv4 address with prefix";
                        }
                        leaf length {
                          type uint32 {
                            range "0..32";
                          }
                          description
                            "Enter IPv4 address with prefix";
                        }
                      }
                    }
                    container ipv4-addresses {
                      description
                        "Enter IPv4 address";
                      list ipv4-address {
                        key "address";
                        description
                          "Enter IPv4 address";
                        leaf address {
                          type inet:ipv4-address-no-zone;
                          description
                            "Enter IPv4 address";
                        }
                      }
                    }
                  }
                  container ipv6 {
                    description
                      "Configure peer IPv6 address on this interface";
                    container ipv6-address-prefixes {
                      description
                        "Enter IPv6 address with prefix";
                      list ipv6-address-prefix {
                        key "address length";
                        description
                          "Enter IPv6 address with prefix";
                        leaf address {
                          type inet:ipv6-address-no-zone;
                          description
                            "Enter IPv6 address with prefix";
                        }
                        leaf length {
                          type uint32 {
                            range "0..128";
                          }
                          description
                            "Enter IPv6 address with prefix";
                        }
                      }
                    }
                    container ipv6-addresses {
                      description
                        "Enter IPv6 address";
                      list ipv6-address {
                        key "address";
                        description
                          "Enter IPv6 address";
                        leaf address {
                          type inet:ipv6-address-no-zone;
                          description
                            "Enter IPv6 address";
                        }
                      }
                    }
                  }
                }
              }
              container all {
                presence "Indicates a all node is configured.";
                description
                  "All Protocols";
              }
              container all-peer {
                description
                  "Configure peer address on this interface";
                container address {
                  description
                    "Configure peer address on this interface";
                  container ipv4 {
                    description
                      "Configure peer IPv4 address on this interface";
                    container ipv4-address-prefixes {
                      description
                        "Enter IPv4 address with prefix";
                      list ipv4-address-prefix {
                        key "address length";
                        description
                          "Enter IPv4 address with prefix";
                        leaf address {
                          type inet:ipv4-address-no-zone;
                          description
                            "Enter IPv4 address with prefix";
                        }
                        leaf length {
                          type uint32 {
                            range "0..32";
                          }
                          description
                            "Enter IPv4 address with prefix";
                        }
                      }
                    }
                    container ipv4-addresses {
                      description
                        "Enter IPv4 address";
                      list ipv4-address {
                        key "address";
                        description
                          "Enter IPv4 address";
                        leaf address {
                          type inet:ipv4-address-no-zone;
                          description
                            "Enter IPv4 address";
                        }
                      }
                    }
                  }
                  container ipv6 {
                    description
                      "Configure peer IPv6 address on this interface";
                    container ipv6-address-prefixes {
                      description
                        "Enter IPv6 address with prefix";
                      list ipv6-address-prefix {
                        key "address length";
                        description
                          "Enter IPv6 address with prefix";
                        leaf address {
                          type inet:ipv6-address-no-zone;
                          description
                            "Enter IPv6 address with prefix";
                        }
                        leaf length {
                          type uint32 {
                            range "0..128";
                          }
                          description
                            "Enter IPv6 address with prefix";
                        }
                      }
                    }
                    container ipv6-addresses {
                      description
                        "Enter IPv6 address";
                      list ipv6-address {
                        key "address";
                        description
                          "Enter IPv6 address";
                        leaf address {
                          type inet:ipv6-address-no-zone;
                          description
                            "Enter IPv6 address";
                        }
                      }
                    }
                  }
                }
              }
            }
          }
        }
        leaf vrf {
          type xr:Cisco-ios-xr-string {
            length "1..800" {
              description
                "Enter vrf name";
            }
          }
          description
            "configure mpp outband vrf";
        }
        container enable-inband-behavior {
          presence "Indicates a enable-inband-behavior node is configured.";
          description
            "allow only configured mgmt protocols in MPP out-of-band config";
        }
      }
    }
  }
}
