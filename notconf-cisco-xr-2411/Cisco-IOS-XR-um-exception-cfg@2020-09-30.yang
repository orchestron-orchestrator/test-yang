module Cisco-IOS-XR-um-exception-cfg {
  namespace "http://cisco.com/ns/yang/Cisco-IOS-XR-um-exception-cfg";
  prefix um-exception-cfg;

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR exception package configuration.

     This YANG module augments the
     modules with configuration data.

     Copyright (c) 2020, 2022 by Cisco Systems, Inc.
     All rights reserved.";

  revision 2020-09-30 {
    semver:module-version "1.0.0";
    description
      "Initial release";
  }

  container exception {
    description
      "Coredump configuration commands";
    container choices {
      description
        "Preference for the following dump location";
      list choice {
        key "dump-location-preference";
        description
          "Preference for the following dump location";
        leaf dump-location-preference {
          type uint32 {
            range "1..3" {
              description
                "Order of preference";
            }
          }
          description
            "Preference for the following dump location";
        }
        leaf filepath {
          type string {
            length "1..1024" {
              description
                "Protocol and directory";
            }
          }
          mandatory true;
          description
            "Give the dump location next";
        }
      }
    }
  }
}
