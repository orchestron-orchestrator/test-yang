module Cisco-IOS-XR-sysadmin-ethsw-esdma-summary {
  namespace "http://www.cisco.com/ns/yang/Cisco-IOS-XR-sysadmin-ethsw-esdma-summary";
  prefix esdma_summary;

  import Cisco-IOS-XR-sysadmin-ethsw-esdma-types {
    prefix esdma_types;
  }
  import cisco-semver {
    prefix semver;
  }

  organization
    "Cisco Systems Inc.";
  contact
    "Cisco Systems, Inc.
     Customer Service

     Postal: 170 West Tasman Drive
     San Jose, CA 95134

     Tel: +1 800 553-NETS

     E-mail: cs-yang@cisco.com";
  description
    "This module contains the YANG definitions
     for the Cisco IOS-XR SysAdmin
     'show controller switch summary' commands.

     Copyright (c) 2011-2020 by Cisco Systems, Inc.
     All rights reserved.";

  revision 2020-12-23 {
    semver:module-version "1.1.0";
    description
      "Addition of new list for RSIP port format for iosxrwbd";
  }
  revision 2019-04-15 {
    semver:module-version "1.0.0";
    description
      "Establish semantic version baseline.";
  }
  revision 2017-05-01 {
    description
      "Namespace change to comply with Cisco guidelines on namespace";
  }
  revision 2016-07-06 {
    description
      "Initial revision with content extracted from esdma_cli.yang.";
  }

  grouping switch-summary-group {
    container summary {
      list location {
        key "rack card switch-id";
        leaf rack {
          type esdma_types:esdma-rack-num-enum;
        }
        leaf card {
          type esdma_types:esdma-cpu;
          description
            "Card that owns a switch of interest";
        }
        leaf switch-id {
          type esdma_types:esdma-switch-type-enum;
          description
            "Switch type";
        }
        leaf serial-num {
          type string;
          description
            "Rack serial number";
        }
        list port-iter {
          key "port";
          leaf port {
            type esdma_types:esdma-switch-port-type;
            description
              "Switch port";
          }
          leaf phys-state {
            type esdma_types:esdma-switch-port-state;
            description
              "Physical port state";
          }
          leaf admin-state {
            type esdma_types:esdma-switch-port-state;
            description
              "Administrative port state";
          }
          leaf port-speed {
            type string;
            description
              "Indicates the port speed in bits per second";
          }
          leaf protocol-state {
            type esdma_types:mlap-state-enum;
            description
              "Protocol invoked port state";
          }
          leaf forwarding {
            type esdma_types:switch-forwarding-state;
            description
              "Indicates whether this port is allowed to forward traffic";
          }
          leaf connects-to {
            type string;
            description
              "Indicates what this port connects to";
          }
        }
      }
    }
  }

  grouping switch-summary-group-iosxrwbd {
    container summary {
      list location {
        key "rack card switch-id";
        leaf rack {
          type esdma_types:esdma-rack-num-enum;
        }
        leaf card {
          type esdma_types:esdma-cpu;
          description
            "Card that owns a switch of interest";
        }
        leaf switch-id {
          type esdma_types:esdma-switch-type-enum;
          description
            "Switch type";
        }
        leaf serial-num {
          type string;
          description
            "Rack serial number";
        }
        list port-iter-rsip {
          key "port-rsip";
          leaf port-rsip {
            type string;
            description
              "Switch port RSIP";
          }
          leaf phys-state {
            type esdma_types:esdma-switch-port-state;
            description
              "Physical port state";
          }
          leaf admin-state {
            type esdma_types:esdma-switch-port-state;
            description
              "Administrative port state";
          }
          leaf port-speed {
            type string;
            description
              "Indicates the port speed in bits per second";
          }
          leaf protocol-state {
            type esdma_types:mlap-state-enum;
            description
              "Protocol invoked port state";
          }
          leaf forwarding {
            type esdma_types:switch-forwarding-state;
            description
              "Indicates whether this port is allowed to forward traffic";
          }
        }
      }
    }
  }
}
