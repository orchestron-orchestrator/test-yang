module Cisco-IOS-XR-um-line-timestamp-cfg {
  namespace "http://cisco.com/ns/yang/Cisco-IOS-XR-um-line-timestamp-cfg";
  prefix um-line-timestamp-cfg;

  import Cisco-IOS-XR-um-line-cfg {
    prefix a1;
  }
  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR line-timestamp package configuration.

     This YANG module augments the
     modules with configuration data.

     Copyright (c) 2020-2022 by Cisco Systems, Inc.
     All rights reserved.";

  revision 2022-07-11 {
    semver:module-version "1.0.0";
    description
      "Added missing description statement to nodes";
  }
  revision 2020-10-01 {
    semver:module-version "1.0.0";
    description
      "Initial release";
  }

  augment "/a1:line/a1:console" {
    description
      "This augment extends line console nodes
       configuration";
    container timestamp {
      presence "Indicates a timestamp node is configured";
      description
        "To enable timestamp printing before each command.";
      container disable {
        presence "Indicates a disable node is configured.";
        description
          "To disable timestamp printing before each command.";
      }
    }
    leaf pager {
      type enumeration {
        enum "more" {
          value 1;
          description
            "More Utility";
        }
        enum "less" {
          value 2;
          description
            "Less Utility";
        }
        enum "none" {
          value 3;
          description
            "No Pagers";
        }
      }
      description
        "To enable pager functionality";
    }
  }
  augment "/a1:line/a1:default" {
    description
      "This augment extends line default nodes
       configuration";
    container timestamp {
      presence "Indicates a timestamp node is configured";
      description
        "To enable timestamp printing before each command.";
      container disable {
        presence "Indicates a disable node is configured.";
        description
          "To disable timestamp printing before each command.";
      }
    }
    leaf pager {
      type enumeration {
        enum "more" {
          value 1;
          description
            "More Utility";
        }
        enum "less" {
          value 2;
          description
            "Less Utility";
        }
        enum "none" {
          value 3;
          description
            "No Pagers";
        }
      }
      description
        "To enable pager functionality";
    }
  }
  augment "/a1:line/a1:templates/a1:template" {
    description
      "This augment extends line template nodes
       configuration";
    container timestamp {
      presence "Indicates a timestamp node is configured";
      description
        "To enable timestamp printing before each command.";
      container disable {
        presence "Indicates a disable node is configured.";
        description
          "To disable timestamp printing before each command.";
      }
    }
    leaf pager {
      type enumeration {
        enum "more" {
          value 1;
          description
            "More Utility";
        }
        enum "less" {
          value 2;
          description
            "Less Utility";
        }
        enum "none" {
          value 3;
          description
            "No Pagers";
        }
      }
      description
        "To enable pager functionality";
    }
  }
}
