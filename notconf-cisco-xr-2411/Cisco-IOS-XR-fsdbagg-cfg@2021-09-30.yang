module Cisco-IOS-XR-fsdbagg-cfg {
  namespace "http://cisco.com/ns/yang/Cisco-IOS-XR-fsdbagg-cfg";
  prefix fsdbagg-cfg;

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR fsdbagg package configuration.

     This module contains definitions
     for the following management objects:
       fsdb-agg-config: none

     Copyright (c) 2013-2021 by Cisco Systems, Inc.
     All rights reserved.";

  revision 2021-09-30 {
    semver:module-version "1.0.0";
    description
      "Yang Schema update to remove support of Oversubscribed FC mode.";
  }
  revision 2020-10-27 {
    semver:module-version "1.0.0";
    description
      "Yang Schema update to support new 5fc config.";
  }
  revision 2020-06-26 {
    description
      "Yang Schema added with 5fc config support and task-name.";
  }
  revision 2019-04-05 {
    description
      "Establish semantic version baseline.";
  }
  revision 2015-11-09 {
    description
      "IOS XR 6.0 revision.";
  }

  container fsdb-agg-config {
    description
      "none";
    container fabric-mode {
      description
        "Configure Fabric Mode as either 8FC or 5FC";
      leaf five-fc {
        type uint32;
        description
          "enable 5FC(slot:1-2-3-4-5)=1; enable 5FC(slot
           :0-2-4-5-6)=2";
      }
    }
    container planes {
      description
        "Configure fabric.";
      list plane {
        key "plane";
        description
          "Configure fabric planes";
        leaf plane-shutdown {
          type uint32;
          description
            "Shutdown fabric planes";
        }
        leaf plane {
          type uint32;
          description
            "Plane";
        }
      }
    }
  }
}
