module Cisco-IOS-XR-infra-ltrace-oper {
  namespace "http://cisco.com/ns/yang/Cisco-IOS-XR-infra-ltrace-oper";
  prefix infra-ltrace-oper;

  import Cisco-IOS-XR-types {
    prefix xr;
  }
  import cisco-semver {
    prefix semver;
  }

  include Cisco-IOS-XR-infra-ltrace-oper-sub1 {
    revision-date 2022-08-01;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR infra-ltrace package operational data.

     This module contains definitions
     for the following management objects:
       ltrace: Ltrace infra operational data

     Copyright (c) 2013-2022 by Cisco Systems, Inc.
     All rights reserved.";

  revision 2022-08-01 {
    semver:module-version "1.0.0";
    description
      "adding schema support for infra ltrace cfg path";
  }
  revision 2019-04-05 {
    description
      "Establish semantic version baseline.";
  }
  revision 2015-11-09 {
    description
      "IOS XR 6.0 revision.";
  }

  container ltrace {
    config false;
    description
      "Ltrace infra operational data";
    container nodes {
      description
        "Node-specific LTrace operational data";
      list node {
        key "node-name";
        description
          "LTrace operational data for a particular node";
        container ltrace-buffer-stats {
          description
            "Ltrace Limits on node";
          list ltrace-buffer-stat {
            key "name";
            description
              "Ltrace Limits on node";
            leaf name {
              type xr:Cisco-ios-xr-string;
              description
                "Ltrace Buffer name";
            }
            uses LTRACE-BUF-STATS;
          }
        }
        container memory-size {
          description
            "Shared Memory Ltrace Size on node";
          uses LTRACE-SYNC-BG;
        }
        container ltrace-limits {
          description
            "Ltrace Limits on node";
          uses LTRACE-YAML-STATS;
        }
        leaf node-name {
          type xr:Node-id;
          description
            "The node";
        }
      }
    }
  }
}
