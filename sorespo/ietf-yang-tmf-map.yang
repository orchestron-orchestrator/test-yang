module ietf-yang-tmf-map {
  yang-version 1.1;
  namespace "urn:ietf:params:xml:ns:yang:ietf-yang-tmf-map";
  prefix tmf;

  organization
    "IETF ONSEN Working Group.";
  contact
    "Kris Lambrechts
     Email: kris@netedge.plus";
  description
    "This YANG module defines a set of YANG extensions to annotate
     YANG schema nodes with mapping information to TMF Data Models.

     Copyright (c) 2026 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).
     
     This version of this YANG module is part of RFC XXXX
     (https://www.rfc-editor.org/info/rfcXXXX); see the RFC itself
     for full legal notices.";

  revision 2026-02-23 {
    description
      "Initial revision.";
    reference
      "RFC XXXX";
  }

  extension cfs-service {
    argument name;
    description
      "The TMF CFS Service that this YANG subtree maps to.";
  }

  extension rfs-service {
    argument name;
    description
      "The TMF RFS Service that this YANG subtree maps to.";
  }

  extension resource {
    argument name;
    description
      "The TMF Resource that this YANG subtree maps to.";
  }

  extension ignore {
    description
      "Indicates that the annotated YANG data node and its
       subtree are ignored by the mapping mechanism.";
  }
}
