module orchestron-rfs {
  yang-version "1.1";
  namespace "http://orchestron.org/yang/orchestron-rfs.yang";
  prefix "orfs";

  import ietf-inet-types {
    prefix inet;
  }
  import stratoweave {
    prefix sw;
  }

  description "RFS services";

  list device {
    key name;

    sw:device;

    leaf name {
      type string;
    }

    leaf description {
      type string;
    }

    leaf type {
      type string;
    }

    list address {
      key name;
      leaf name {
        description "Name of address, e.g. 'loopback' or 'OOB'";
        type string;
      }
      leaf address {
        type inet:host;
        mandatory true;
      }
      leaf port {
        type uint16;
      }
      list initial-credentials {
        key "username password key";
        leaf username {
          type string;
        }
        leaf password {
          type string;
        }
        leaf key {
          type string;
        }
      }
    }

    container credentials {
      leaf username {
        type string;
        mandatory true;
      }
      leaf password {
        type string;
      }
      list key {
        key key;
        leaf key {
          type string;
        }
        leaf private-key {
          type string;
        }
      }
    }

    list initial-credentials {
      key "username password key";
      leaf username {
        type string;
      }
      leaf password {
        type string;
      }
      leaf key {
        type string;
      }
    }

    leaf approval-required {
      description "Require approval of each individual configuration change to this device";
      type boolean;
      default "false";
    }

    container mock {
      leaf-list preset {
        type enumeration {
          enum cisco-ios-xr;
          enum juniper-junos;
        }
      }
      list module {
        key "name";
        leaf name {
          type string;
        }
        leaf namespace {
          type string;
          mandatory true;
        }
        leaf revision {
          type string;
        }
        leaf-list feature {
          type string;
        }
      }
    }

    container debug {
      leaf connection {
        type boolean;
        default "false";
      }
    }

    container state {
      config false;
    }
  }

  list rfs {
    key name;

    leaf name {
      description "Device name";
      type string;
    }

    // Augment
  }
}
