module stratoweave-device {
  yang-version "1.1";
  namespace "http://stratoweave.org/yang/stratoweave-device.yang";
  prefix "sw-dev";
  import stratoweave {
    prefix sw;
  }

  description "Device config";

  container devices {
    list device {
      key name;

      sw:device-config;

      leaf name {
        type string;
      }

      leaf modset_id {
        type string;
      }

      //anydata config {
      //  description "Device configuration";
      //}
    }
  }
}
