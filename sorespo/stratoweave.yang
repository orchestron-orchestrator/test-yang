module stratoweave {
  yang-version "1.1";
  namespace "http://stratoweave.org/yang/stratoweave.yang";
  prefix "sw";

  description
    "This module defines Stratoweave YANG extensions.";

  revision 2026-04-01;

  extension device {
    description
      "Used internally in the list defining the device manager model.";
  }
  extension device-config {
    description
      "Used internally in the list defining the device configuration store.";
  }
  extension transform {
    description
      "Used in a list or container defining a transform model. Takes as an
      argument the fully qualified name of the type implementing the transform
      function in user code. Makes the code generator create the base type in
      app.layers.base_X.";
    argument "function";
  }
  extension rfs-transform {
    description
      "Used in a list or container defining an RFS transform model. Takes as an
      argument the fully qualified name of the type implementing the RFS
      transform function in user code. Makes the code generator create the base
      type in app.layers.base_X.";
    argument "function";
  }
  extension dynstate {
    description
      "Used in the dynstate container of a transform model. Enriches the
      transform function inputs with an additional read-only structure. This
      subtree is accessible for writes to the transform actor for async
      (environmental) updates.";
  }
  extension memory {
    description
      "Used in the memory container of a transform model. Enriches the transform
      function inputs with an additional read-only structure. The transform
      function may update this subtree by returning new data.";
  }
}
