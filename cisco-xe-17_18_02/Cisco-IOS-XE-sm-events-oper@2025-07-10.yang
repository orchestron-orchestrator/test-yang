module Cisco-IOS-XE-sm-events-oper {
  yang-version 1.1;
  namespace "http://cisco.com/ns/yang/Cisco-IOS-XE-sm-events-oper";
  prefix sm-event-oper;

  import Cisco-IOS-XE-sm-enum-types {
    prefix sm-enum-types;
  }
  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for session operations events generated from the Cisco Wired
     devices. These models may produce high volume of data.
     Copyright (c) 2019-2020, 2022 by Cisco Systems, Inc.
     All rights reserved";

  revision 2025-07-10 {
    description
      "- Added support for Average Round trip time and transaction count in session event data";
    reference
      "2.1.17180(m)";
    cisco-semver:module-version "2.1.17180(m)";
  }
  revision 2022-11-01 {
    description
      "Update yang-version to 1.1";
    reference
      "2.1.0";
    cisco-semver:module-version "2.1.0";
  }
  revision 2020-07-01 {
    description
      "- Remove unused empty container sm-events";
    reference
      "2.0.0";
    cisco-semver:module-version "2.0.0";
  }
  revision 2020-03-01 {
    description
      "- Added interface name to session event data";
    reference
      "1.1.0";
    cisco-semver:module-version "1.1.0";
  }
  revision 2019-11-01 {
    description
      "Initial revision";
    reference
      "1.0.0";
    cisco-semver:module-version "1.0.0";
  }

  grouping session-authc-success-params {
    description
      "Parameters sent in case of a authentication SUCCESS event";
    leaf eap-method {
      type sm-enum-types:session-eap-method;
      description
        "EAP method for a dot1x client";
    }
  }

  grouping session-authz-success-params {
    description
      "Parameters sent in case of a authorization SUCCESS event";
    leaf res-vlan-id {
      type uint32;
      description
        "Resultant Vlan ID applied on a session";
    }
    leaf res-vlan-name {
      type string;
      description
        "Resultant Vlan name applied on a session";
    }
    leaf sgt {
      type uint32;
      description
        "Security Group Tag applied on a session";
    }
    leaf eap-method {
      type sm-enum-types:session-eap-method;
      description
        "EAP method for a dot1x client";
    }
  }

  grouping session-failure-params {
    description
      "Parameters sent in case of a FAILURE event";
    leaf failure-reason {
      type sm-enum-types:session-event-failure-reason;
      description
        "Reason for authentication session failure";
    }
    leaf failed-attribute {
      type string;
      description
        "Failed Attribute in case of session failure";
    }
  }

  grouping session-coa-params {
    description
      "Parameters sent in case of a COA event";
    leaf coa-req-type {
      type sm-enum-types:session-coa-request-type;
      description
        "COA request type";
    }
  }

  grouping session-security-violation-params {
    description
      "Parameters sent in case of a security violation event";
    leaf security-violation-action {
      type sm-enum-types:session-security-violation-action;
      description
        "Security violation type";
    }
  }

  grouping session-event-data {
    description
      "Wired session lifecycle events data model";
    leaf client-mac {
      type yang:mac-address;
      description
        "Wired Client's MAC Address";
    }
    leaf audit-session-id {
      type string;
      description
        "Audit session id of the session";
    }
    leaf method-id {
      type sm-enum-types:session-auth-method-id;
      description
        "Authentication method used for the session";
    }
    leaf username {
      type string;
      description
        "Client's username for a session";
    }
    leaf client-join-time {
      type yang:date-and-time;
      description
        "Client's join time";
    }
    leaf server-address {
      type inet:ip-address;
      description
        "IP address for the authentication server";
    }
    leaf interface-name {
      type string;
      description
        "Name of the interface connected to client";
    }
    leaf avg-rtt {
      type uint32;
      units "milliseconds";
      description
        "Average RTT across all the request/response pairs
         sent/received for the latest authentication attempt
         to/from the AAA server for a client";
    }
    leaf trans-count {
      type uint8;
      description
        "Number of request-response pairs were sent/received
         for the latest authentication attempt to/from the AAA server";
    }
    choice session-event-choice {
      description
        "Union of Session Events";
      case session-event-session-authc-success {
        container authc-success-params {
          description
            "Session event result authentication success parameters";
          uses sm-event-oper:session-authc-success-params;
        }
      }
      case session-event-session-authc-failed {
        container authc-failure-params {
          description
            "Session event result authentication failure parameters";
          uses sm-event-oper:session-failure-params;
        }
      }
      case session-event-session-authz-success {
        container authz-success-params {
          description
            "Session event result authorization success parameters";
          uses sm-event-oper:session-authz-success-params;
        }
      }
      case session-event-session-authz-failed {
        container authz-failure-params {
          description
            "Session event result authorization failure parameters";
          uses sm-event-oper:session-failure-params;
        }
      }
      case session-event-policy-update {
        container policy-change-params {
          description
            "Session event policy update parameters";
          uses sm-event-oper:session-authz-success-params;
        }
      }
      case session-event-coa-start {
        container coa-params {
          description
            "Event coa start parameters";
          uses sm-event-oper:session-coa-params;
        }
      }
      case session-event-security-violation {
        container security-violation-params {
          description
            "Event security violation parameters";
          uses sm-event-oper:session-security-violation-params;
        }
      }
    }
  }

  notification sessionevent {
    description
      "Session event Notification";
    uses sm-event-oper:session-event-data;
  }
}
