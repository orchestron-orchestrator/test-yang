submodule Cisco-IOS-XE-sip-ua {
  yang-version 1.1;
  belongs-to Cisco-IOS-XE-voice {
    prefix ios-voice;
  }

  import cisco-semver {
    prefix cisco-semver;
  }
  import Cisco-IOS-XE-native {
    prefix ios;
  }
  import ietf-inet-types {
    prefix inet;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native sip-ua Yang model.
     Copyright (c) 2020 by Cisco Systems, Inc.
     All rights reserved.";

  revision 2025-07-10 {
    description
      "- Added warning in TLS version 1.0 and 1.1 for sip-ua";
    cisco-semver:module-version "1.5.0";
  }
  revision 2024-07-01 {
    description
      "- Added TLS 1.3 and TLS 1.2 minimum to sip-ua";
    cisco-semver:module-version "1.4.0";
  }
  revision 2024-03-01 {
    description
      "Converted absolute xpath to relative xpath";
    cisco-semver:module-version "1.3.0";
  }
  revision 2022-11-01 {
    description
      "- Update yang-version to 1.1
       - Added max-forwards, xfer, permit to sip-ua";
    cisco-semver:module-version "1.2.0";
  }
  revision 2021-11-01 {
    description
      "- Added authentication and credentials CLI
       - Added protocol mode to sip-ua
       - Added address-hiding, emergency, silent-discard, asserted-id,
         midcall-signaling, remote-party-id, g729-annexb, redirection,
         set pstn-cause, set sip-status, host-registrar, sip-register configurations";
    cisco-semver:module-version "1.1.0";
  }
  revision 2021-03-01 {
    description
      "- Added sip-ua";
    cisco-semver:module-version "1.0.0";
  }

  typedef sip-status-code-range {
    type uint16 {
      range "400..410 | 412..417 | 420..424 | 480..489 | 491 | 493 | 500..505 | 513 | 580 | 600 | 603..604 | 606" {
        error-message "should be in 400-410|412-417|420-424|480-489|491|493|500-505|513|580|600|603-604|606";
      }
    }
  }

  typedef ipv4-mask-pattern {
    type string {
      pattern '([0]|([2][5][5]))\.([0]|([2][5][5]))\.([0]|([(2][5][5]))\.([0]|([2][5][5]))' {
        error-message "Incorrect regular expression format. Expected values  0 or 255 ";
      }
    }
  }

  grouping config-sip-signaling-timers-grouping {
    leaf buffer-invite {
      description
        "Time to buffer the INVITE while waiting for display info";
      type uint16 {
        range "50..5000";
      }
    }
    leaf connect {
      description
        "Time to wait for confirmation a session connected";
      type uint16 {
        range "100..1000";
      }
      default "500";
    }
    container connection {
      description
        "Connection related timers";
      container aging {
        description
          "Time to wait before aging out a TCP/UDP connection";
        leaf value {
          description
            "TCP/UDP aging timer value in minutes";
          type uint16 {
            range "5..1440";
          }
          default "5";
        }
        leaf tls {
          description
            "TCP/UDP aging timer value in minutes";
          type uint16 {
            range "60..4320";
          }
          default "60";
        }
      }
    }
    leaf disconnect {
      description
        "Time to wait for confirmation a session disconnected";
      type uint16 {
        range "100..1000";
      }
      default "500";
    }
    container dns {
      description
        "Expiry timer value for the DNS resolved address cache";
      container registrar-cache {
        description
          "DNS cache refresh time for registrar";
        choice cache-choice {
          case timer-val {
            leaf timer {
              description
                "timer value in seconds";
              type uint16 {
                range "60..65535";
              }
            }
          }
          case ttl-val {
            leaf ttl {
              description
                "timer value to be set as ttl seconds";
              type empty;
            }
          }
        }
      }
    }
    leaf expires {
      description
        "Time to wait for the expiration of an INVITE request";
      type uint32 {
        range "60000..1800000";
      }
      default "180000";
    }
    leaf hold {
      description
        "Time to wait during hold before disconnecting";
      type uint16 {
        range "15..2880";
      }
      default "2880";
    }
    leaf info {
      description
        "Time to wait before INFO retransmission";
      type uint16 {
        range "100..1000";
      }
      default "500";
    }
    leaf notify {
      description
        "Time to wait before NOTIFY retransmission";
      type uint16 {
        range "100..1000";
      }
      default "500";
    }
    leaf options {
      description
        "Time to wait before OPTIONS retransmission";
      type uint16 {
        range "100..1000";
      }
      default "500";
    }
    leaf prack {
      description
        "Time to wait before PRACK retransmission";
      type uint16 {
        range "100..1000";
      }
      default "500";
    }
    leaf refer {
      description
        "Time to wait before REFER retransmission";
      type uint16 {
        range "100..1000";
      }
      default "500";
    }
    leaf register {
      description
        "Time to wait before REGISTER retransmission";
      type uint16 {
        range "100..1000";
      }
      default "500";
    }
    leaf rel1xx {
      description
        "Time to wait before starting reliable 1xx retransmission";
      type uint16 {
        range "100..1000";
      }
      default "500";
    }
    leaf trying {
      description
        "Time to wait for provisional response to INVITE";
      type uint16 {
        range "100..1000";
      }
      default "500";
    }
    leaf update {
      description
        "Time to wait before starting UPDATE retransmission";
      type uint16 {
        range "100..1000";
      }
      default "500";
    }
  }

  grouping config-sip-retry-timers-grouping {
    leaf bye {
      description
        "BYE retry value";
      type uint8 {
        range "1..10";
      }
      default "10";
    }
    leaf cancel {
      description
        "CANCEL retry value";
      type uint8 {
        range "1..10";
      }
      default "10";
    }
    leaf info {
      description
        "INFO retry value";
      type uint8 {
        range "1..10";
      }
      default "6";
    }
    leaf invite {
      description
        "INVITE retry value";
      type uint8 {
        range "1..10";
      }
      default "6";
    }
    leaf notify {
      description
        "NOTIFY retry value";
      type uint8 {
        range "1..10";
      }
      default "10";
    }
    leaf options {
      description
        "OPTIONS retry value";
      type uint8 {
        range "1..10";
      }
      default "6";
    }
    leaf prack {
      description
        "PRACK retry value";
      type uint8 {
        range "1..10";
      }
      default "10";
    }
    leaf refer {
      description
        "REFER retry value";
      type uint8 {
        range "1..10";
      }
      default "10";
    }
    leaf register {
      description
        "REGISTER retry value";
      type uint8 {
        range "1..10";
      }
      default "6";
    }
    leaf rel1xx {
      description
        "Reliable 1xx retry value";
      type uint8 {
        range "1..10";
      }
      default "6";
    }
    leaf response {
      description
        "Response retry value";
      type uint8 {
        range "1..10";
      }
      default "6";
    }
    leaf subscribe {
      description
        "SUBSCRIBE retry value";
      type uint8 {
        range "1..10";
      }
      default "6";
    }
    leaf update {
      description
        "UPDATE retry value";
      type uint8 {
        range "1..10";
      }
      default "6";
    }
  }

  grouping config-sip-ua-common-grouping {
    container xfer {
      description
        "Configure xfer related aspects of the SIP UA";
      leaf target {
        description
          "Configure where to select the xfer target from";
        type enumeration {
          enum dial-peer {
            description
              "Get xfer target address from dial-peer";
          }
          enum refer-to {
            description
              "Get xfer target address from refer-to header";
          }
        }
        default "dial-peer";
      }
    }
    container g729-annexb {
      description
        "Configure settings for G729 codec interoperability";
      leaf override {
        description
          "Override default value, yes, if annexb attribute is not present";
        type empty;
      }
    }
    container notify {
      description
        "Accept NOTIFY without Subscription-State header";
      container ignore {
        description
          "Ignore Subscription-State header";
        leaf substate {
          description
            "Ignore  Subscription-State header";
          type empty;
        }
      }
      container telephone-event {
        description
          "Configuring Telephone Events sent in NOTIFY body";
        leaf max-duration {
          description
            "Max time interval between two consecutive NOTIFYs for a single DTMF event";
          type uint16 {
            range "40..3000";
          }
        }
      }
    }
    container reason-header {
      description
        "Configure settings for supporting SIP Reason Header";
      leaf override {
        description
          "Enable Reason header to override SIP<->Q850 Mappings";
        type empty;
      }
    }
    list permit {
      description
        "Permit hostname for this gateway";
      max-elements 10;
      key "hostname";
      leaf hostname {
        description
          "Permit hostname in Req URI for incoming INVITEs";
        type string {
          length "1..50";
          pattern '(dns:.*)' {
            error-message
              "Ill-formed hostname permit address. Valid formats are:

               dns:host.domain or dns:domain";
          }
        }
      }
    }
    leaf max-forwards {
      description
        "Change number of max-forwards for SIP Methods";
      type uint8 {
        range "1..70";
      }
    }
    leaf host-registrar {
      description
        "Use sip-ua registrar value in Diversion and Contact header for 3xx messages";
      type empty;
    }
    leaf handle-replaces {
      description
        "Handle INVITE with REPLACES header at SIP spi";
      type empty;
    }
    leaf disable-early-media {
      description
        "Disable early-media cut through";
      type enumeration {
        enum 180 {
          description
            "180 Response with SDP";
        }
      }
    }
  }

  grouping config-password {
    container password {
      leaf encryption {
        type enumeration {
          enum 0;
          enum 6;
          enum 7;
        }
      }
      leaf password-string {
        type string;
      }
    }
  }

  grouping config-username-password {
    leaf username {
      description
        "name of the user authenticating";
      type string {
        length "4..70";
      }
    }
    uses config-password;
  }

  grouping config-authentication {
    container authentication {
      description
        "Digest Authentication Configuration";
      container auth-with-realm {
        description
          "Limitation: only one realm is supported in this config";
        uses config-username-password {
          refine "password/password-string";
        }
        leaf realm {
          description
            "Realm at which the credentials are applicable";
          type string;
        }
      }
      container username-password {
        uses config-username-password;
      }
    }
  }

  grouping config-credentials {
    container credentials {
      description
        "User credentials for registration";
      list number-list {
        key "number";
        leaf number {
          description
            "number which is getting registered";
          type string {
            length "4..32";
          }
        }
        uses config-username-password {
          refine "password/password-string";
        }
        leaf realm {
          description
            "Realm at which the credentials are applicable";
          type string;
        }
      }
      list username-list {
        key "username";
        uses config-username-password {
          refine "username";
          refine "password/password-string";
        }
        leaf realm {
          description
            "Realm at which the credentials are applicable";
          type string;
        }
      }
      container dhcp {
        description
          "Provision user name using DHCP";
        uses config-password {
          refine "password/password-string";
        }
        leaf realm {
          description
            "Realm at which the credentials are applicable";
          type string;
        }
      }
    }
  }

  grouping config-sip-ua-grouping {
    container sip-ua {
      description
        "SIP User Agent (UA)";
      presence "true";
      container crypto {
        description
          "sip-ua crypto commands";
        container signaling {
          description
            "Configure crypto signaling for sip-ua configuration mode";
          container default {
            description
              "Configure the default trust point";
            leaf tls-profile {
              description
                "Associate a tls-profile";
              type leafref {
                path "../../../../../../ios:native/voice/class/tls-profile/id";
              }
            }
          }
          list remote-addr {
            description
              "Associate an IP network to a trustpoint";
            max-elements 10;
            key "ipv4address subnetmask";
            leaf ipv4address {
              description
                "Enter the IP address";
              type inet:ipv4-address;
            }
            leaf subnetmask {
              description
                "Enter the mask";
              type union {
                type ipv4-mask-pattern;
                type string {
                  pattern '/([0-9]|[1-2][0-9]|3[0-2])';
                }
              }
            }
            leaf tls-profile {
              description
                "Associate a tls-profile";
              mandatory true;
              type leafref {
                path "../../../../../../ios:native/voice/class/tls-profile/id";
              }
            }
          }
        }
      }
      container transport {
        description
          "Enable SIP UA transport for TCP/UDP";
        leaf udp {
          description
            "Enable SIP User Agent in UDP Mode";
          type boolean;
          default "true";
        }
        leaf tcp {
          description
            "Enable SIP User Agent in TCP Mode";
          type boolean;
          default "true";
        }
        container tcp-tls {
          container tcp {
            description
              "Enable SIP User Agent in TCP Mode";
            choice tls-choice {
              default "tls";
              case tls {
                leaf tls {
                  description
                    "Enable SIP User Agent in TLS over TCP mode (Default: All TLS versions with fallback)";
                  type boolean;
                  default "true";
                }
              }
              case tls-version {
                container tls-version {
                  container tls {
                    description
                      "Enable SIP User Agent in TLS over TCP mode (Default: All TLS versions with fallback)";
                    container version-config {
                      description
                        "Various config options";
                      choice tlsver-choice {
                        description
                          "TLS Version options";
                        case tlsv1.0-case {
                          description
                            "TLS Version 1.0 option";
                          leaf v1.0 {
                            status deprecated;
                            description
                              "TLS version 1.0";
                            type empty;
                          }
                        }
                        case tlsv1.1-case {
                          description
                            "TLS Version 1.1 option";
                          leaf v1.1 {
                            status deprecated;
                            description
                              "TLS version 1.1";
                            type empty;
                          }
                        }
                        case tlsv1.2-case {
                          description
                            "TLS Version 1.2 option";
                          container v1.2 {
                            description
                              "TLS version 1.2";
                            presence "true";
                            leaf minimum {
                              description
                                "Minimum TLS version";
                              type empty;
                            }
                          }
                        }
                        case tlsv1.3-case {
                          description
                            "TLS Version 1.3 option";
                          leaf v1.3 {
                            description
                              "TLS version 1.3";
                            type empty;
                          }
                        }
                      }
                    }
                    leaf version {
                      status deprecated;
                      type enumeration {
                        enum v1.0 {
                          description
                            "Enable TLS Version 1.0";
                        }
                        enum v1.1 {
                          description
                            "Enable TLS Version 1.1";
                        }
                        enum v1.2 {
                          description
                            "Enable TLS Version 1.2";
                        }
                      }
                    }
                  }
                }
              }
            }
          }
        }
      }
      leaf sip-server {
        description
          "Configure a SIP Server Interface";
        type string {
          pattern '(dns:.*)|(ipv4:[0-9]+\.[0-9]+\.[0-9]+\.[0-9]+(:[0-9]+)?)|(ipv6:\[([0-9A-Fa-f.:])+\](:[0-9]+)?)' {
            error-message "Must be of the form (dns:.*)|(ipv4:[0-9]+.[0-9]+.[0-9]+.[0-9]+(:[0-9]+)?) | ((ipv6:[([0-9A-Fa-f.:])+](:[0-9]+)?))";
          }
        }
      }
      leaf redirection {
        description
          "Enable call redirection (3XX) handling";
        type empty;
      }
      leaf remote-party-id {
        description
          "Enable Remote-Party-ID support in SIP User Agent calls";
        when "/ios:native/voice/service[type='voip']/allow-connections/sip/to/sip";
        type boolean;
        default "true";
      }
      container set {
        description
          "Sets the PSTN cause to SIP status code (and vice versa) and sets the PSTN cause to SIP requests";
        list pstn-cause {
          description
            "The string specifying that PSTN cause value shall be followed";
          max-elements 127;
          key "pstn-cause-code";
          leaf pstn-cause-code {
            description
              "The value should be decimal and in the specified range for the PSTN";
            type uint8 {
              range "1..127";
            }
          }
          leaf sip-status {
            description
              "The string specifying that SIP status code shall be followed";
            type sip-status-code-range;
          }
        }
        list sip-status {
          description
            "The string specifying that SIP status code shall be followed";
          max-elements 39;
          key "sip-status-code";
          leaf sip-status-code {
            description
              "The string specifying that SIP status code shall be followed";
            type sip-status-code-range;
          }
          leaf pstn-cause {
            description
              "The value should be decimal and in the specified range for the PSTN";
            type uint8 {
              range "1..127";
            }
          }
        }
        container sip-request {
          description
            "Changes cause code value for SIP Requests";
          container cancel {
            description
              "CANCEL SIP Request";
            leaf pstn-cause {
              description
                "The string specifying that PSTN cause value shall be followed";
              type uint8 {
                range "1..127";
              }
            }
          }
        }
      }
      container protocol {
        description
          "Configure SIP gateway mode of operation";
        when "/ios:native/ios-voice:voice/ios-voice:service[type='voip']/ios-voice:sip/ios-voice:call/ios-voice:service/ios-voice:stop";
        container mode {
          description
            "Specify SIP Protocol mode";
          choice mode-choice {
            default "ipv4-case";
            case dual-stack-case {
              container dual-stack {
                description
                  "Dual mode";
                presence "true";
                container preference {
                  description
                    "prefered address family";
                  choice ip-choice {
                    case ipv4 {
                      leaf ipv4 {
                        description
                          "IPv4 only mode";
                        type empty;
                      }
                    }
                    case ipv6 {
                      leaf ipv6 {
                        description
                          "IPv6 only mode";
                        type empty;
                      }
                    }
                  }
                }
              }
            }
            case ipv4-case {
              leaf ipv4 {
                description
                  "IPv4 only mode";
                type empty;
              }
            }
            case ipv6-case {
              leaf ipv6 {
                description
                  "IPv6 only mode";
                type empty;
              }
            }
          }
        }
      }
      uses config-authentication;
      uses config-credentials;
      uses config-sip-ua-common-grouping;
      container retry {
        description
          "Change default retries for each SIP Method";
        uses config-sip-retry-timers-grouping;
        leaf keepalive {
          description
            "KEEPALIVE retry value";
          type uint8 {
            range "1..10";
          }
          default "6";
        }
      }
      container timers {
        description
          "SIP Signaling Timers Configuration";
        uses config-sip-signaling-timers-grouping;
        container keepalive {
          description
            "Options keepalive related timers";
          leaf active {
            description
              "Time to wait between keepalive messages in active state";
            type uint16 {
              range "10..600";
            }
            default "120";
          }
          leaf down {
            description
              "Time to wait between keepalive messages in down state";
            type uint8 {
              range "1..120";
            }
            default "30";
          }
        }
      }
    }
  }
}
