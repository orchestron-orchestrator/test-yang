/*
 * Copyright (c) 2025 Juniper Networks, Inc.
 * All rights reserved.
 */
 module junos-rpc-version {
   namespace "http://yang.juniper.net/junos/rpc/version";

   prefix version;

   import junos-common-types {
     prefix jt;
     revision-date 2024-01-01;
   }

   organization "Juniper Networks, Inc.";

   contact "yang-support@juniper.net";

   description "Junos RPC YANG module for version command(s)";

   revision 2024-01-01 {
     description "Junos: 20241218.202301_builder.r1463698";
   }

   rpc get-software-information {
     description "Show software process revision levels";
     input {
       uses command-forwarding;
       leaf level {
         type enumeration {
           enum "brief" {
             description "Display brief output";
           }
           enum "detail" {
             description "Display detailed output";
           }
         }
       }
     }
     output {
       container software-information {
         uses software-information-block;
       }
     }
   }
   grouping software-information-block {
     leaf host-name {
       type string;
       description "Hostname of router";
     }
     leaf product-model {
       type string;
       description "Hardware model name";
     }
     leaf os-name {
       type string;
       description "Operating System Name";
     }
     leaf junos-version {
       type string;
       description "Junos Version";
     }
     leaf junos-edition {
       type string;
       description "Junos Edition";
     }
     leaf yocto-version {
       type string;
       description "Yocto Version";
     }
     leaf kernel-version {
       type string;
       description "Kernel version";
     }
     leaf junos-package {
       type string;
       description "Junos Package Version";
     }
     leaf product-name {
       type string;
       description "Product name";
     }
     leaf jsr {
       type empty;
       description "System is in services-router mode";
     }
     leaf fips {
       type empty;
       description "System conforms to FIPS requirements";
     }
     container external-package-information {
       list external-package-item {
         leaf external-package-name {
           type string;
         }
         leaf external-package-version {
           type string;
         }
       }
     }
     list package-information {
       leaf comment {
         type string;
       }
       leaf package-type {
         type string;
       }
       leaf name {
         type string;
         description "Syslog message tag name";
       }
       leaf version {
         type string;
         description "JUNOS version";
       }
       leaf package-name {
         type string;
         description "Name of software package";
       }
     }
     list version-information {
       leaf component {
         type string;
       }
       leaf release {
         type string;
         description "Release name";
       }
       leaf builder {
         type string;
       }
       leaf build-date {
         type string;
         description "Build date";
       }
       leaf build-machine {
         type string;
       }
       leaf build-directory {
         type string;
       }
       leaf service-interface {
         type string;
       }
       leaf major {
         type int32;
       }
       leaf minor {
         type int32;
       }
       leaf edit {
         type int32;
       }
       leaf release-category {
         type string;
       }
       leaf build-number {
         type int32;
       }
       leaf spin {
         type int32;
       }
     }
     container haiku {
       leaf content {
         type string;
       }
     }
   }
 }
