module Cisco-IOS-XR-um-udp-cfg {

  /*** NAMESPACE / PREFIX DEFINITION ***/

  namespace "http://cisco.com/ns/yang/Cisco-IOS-XR-um-udp-cfg";
  prefix um-udp-cfg;

  /*** LINKAGE (IMPORTS / INCLUDES) ***/

  import Cisco-IOS-XR-types {
    prefix xr;
  }

  import cisco-semver { prefix "semver"; }

  /*** META INFORMATION ***/

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR udp package configuration.

     This YANG module augments the
     modules with configuration data.

     Copyright (c) 2020-2022 by Cisco Systems, Inc.
     All rights reserved.";

  revision 2021-01-11 {
    description
      "Initial release";
    semver:module-version "1.0.0";
  }


  container service {
    description
      "Modify use of network based services";
    container ipv4 {
      description
        "Ipv4 small servers";
      container udp-small-servers {
        description
          "Enable small UDP servers (e.g., ECHO)";
        leaf max-servers {
          type union {
            type enumeration {
              enum no-limit {
                value 0;
                description
                  "No limit to number of allowable UDP small servers";
              }
            }
            type uint32 {
              range "1..2147483647";
            }
          }
          description
            "Set number of allowable UDP small servers";
        }
        leaf access-list {
          type xr:Cisco-ios-xr-string {
            length "1..64" {
              description
                "Access list - Maximum 64 characters";
            }
          }
          must '../max-servers';
          description
            "Access list";
        }
      }
    }
    container ipv6 {
      description
        "Ipv6 small servers";
      container udp-small-servers {
        description
          "Enable small UDP servers (e.g., ECHO)";
        leaf max-servers {
          type union {
            type enumeration {
              enum no-limit {
                value 0;
                description
                  "No limit to number of allowable UDP small servers";
              }
            }
            type uint32 {
              range "1..2147483647";
            }
          }
          description
            "Set number of allowable UDP small servers";
        }
        leaf access-list {
          type xr:Cisco-ios-xr-string {
            length "1..64" {
              description
                "Access list - Maximum 64 characters";
            }
          }
          must '../max-servers';
          description
            "Access list";
        }
      }
    }
  }
  container udp {
    description
      "Global UDP configuration command";
    container directory {
      description
        "Specify debug directory location";
      leaf location {
        type string {
          length "1..256" {
            description
              "Place debug files in this directory";
          }
        }
        must '../files and ../size';
        description
          "Place debug files in this directory";
      }
      leaf files {
        type uint32 {
          range "1..5000" {
            description
              "Maximum debug files (default: 256)";
          }
        }
        must '../location and ../size';
        description
          "Set maximum debug files";
      }
      leaf size {
        type uint32 {
          range "1024..4294967295" {
            description
              "Maximum file size in bytes";
          }
        }
        must '../location and ../files';
        description
          "Set maximum file size";
      }
    }
    leaf receive-queue {
      type uint32 {
        range "40..800" {
          description
            "Number of packets in receive queue";
        }
      }
      description
        "UDP receive packet queue size";
    }
    leaf num-thread {
      type uint32 {
        range "1..16" {
          description
            "Ingress threads created by UDP (default: 8)";
        }
      }
      must '../max-threads';
      description
        "Set number of threads (takes effect only on process restart)";
    }
    leaf max-threads {
      type uint32 {
        range "1..16" {
          description
            "max threads in thread pool created by UDP (default: 8)";
        }
      }
      must '../num-thread';
      description
        "max threads in thread pool created by UDP (default: 8)";
    }
  }
  container forward-protocol {
    description
      "Controls forwarding of physical and directed IP broadcasts";
    container udp {
      description
        "Packets to a specific UDP port";
      container disable {
        presence "Indicates a disable node is configured.";
        description
          "Disable IP Forward Protocol UDP";
      }
      container domain {
        description
          "Domain Name Service (DNS, 53)";
        container disable {
          presence "Indicates a disable node is configured.";
          description
            "Disable IP Forward Protocol UDP for a specific port";
        }
      }
      container nameserver {
        description
          "IEN116 name service (obsolete, 42)";
        container disable {
          presence "Indicates a disable node is configured.";
          description
            "Disable IP Forward Protocol UDP for a specific port";
        }
      }
      container netbios-dgm {
        description
          "NetBios datagram service (138)";
        container disable {
          presence "Indicates a disable node is configured.";
          description
            "Disable IP Forward Protocol UDP for a specific port";
        }
      }
      container netbios-ns {
        description
          "NetBios name service (137)";
        container disable {
          presence "Indicates a disable node is configured.";
          description
            "Disable IP Forward Protocol UDP for a specific port";
        }
      }
      container tacacs {
        description
          "TAC Access Control System (49)";
        container disable {
          presence "Indicates a disable node is configured.";
          description
            "Disable IP Forward Protocol UDP for a specific port";
        }
      }
      container tftp {
        description
          "Trivial File Transfer Protocol (69)";
        container disable {
          presence "Indicates a disable node is configured.";
          description
            "Disable IP Forward Protocol UDP for a specific port";
        }
      }
      container ports {
        description
          "Packets to a specific UDP port";
        list port {
          key "port-number";
          description
            "Packets to a specific UDP port";
          leaf port-number {
            type uint32 {
              range "1..65535";
            }
            description
              "Port number";
          }
        }
      }
    }
  }
}
