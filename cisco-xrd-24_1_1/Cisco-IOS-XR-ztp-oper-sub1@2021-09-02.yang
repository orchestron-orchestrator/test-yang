submodule Cisco-IOS-XR-ztp-oper-sub1 {

  belongs-to Cisco-IOS-XR-ztp-oper {
    prefix Cisco-IOS-XR-ztp-oper;
  }

  /*** LINKAGE (IMPORTS / INCLUDES) ***/

  import cisco-semver { prefix "semver"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ztp package operational data.

     Copyright (c) 2013-2021 by Cisco Systems, Inc.
     All rights reserved.";

  revision "2021-09-02" {
    description
      "Added breakout mode information.";
    semver:module-version "1.1.0";
  }

  revision "2019-04-05" {
    description
      "Establish semantic version baseline.";
    semver:module-version "1.0.0";
  }

  revision "2015-11-09" {
    description
      "IOS XR 6.0 revision.";
  }

  typedef Ztp-state {
    type enumeration {
      enum success {
        value 0;
        description "ZTP was successful";
      }
      enum failure {
        value 1;
        description "ZTP has failed due to internal error";
      }
      enum terminated {
        value 2;
        description "ZTP has terminated";
      }
      enum initializing {
        value 3;
        description "ZTP has started and currently in-progress";
      }
      enum discovery {
        value 4;
        description
          "ZTP is trying to discover the provisioning file
          source";
      }
      enum fetching {
        value 5;
        description "ZTP is fetching the provisioning data";
      }
      enum provisioning {
        value 6;
        description "ZTP is provisioning the device";
      }
    }
    description "ZTP state type";
  }
  typedef Ztp-vlan-discovery {
    type enumeration {
      enum dynamic {
        value 0;
        description "ZTP will snoop VLAN IDs in the network";
      }
      enum static {
        value 1;
        description "ZTP will use VLAN IDs configured in ztp.ini";
      }
      enum disabled {
        value 2;
        description "Vlan discovery is disabled";
      }
    }
    description "ZTP vlan discovery type";
  }

  grouping ZTP-STATUS-BAG {
    description "ZTP status";
    leaf state {
      type Ztp-state;
      description "ZTP state";
    }
    leaf fetcher {
      type string;
      description "Current fetcher name";
    }
  }

  grouping ZTP-INFO-BAG {
    description "ZTP information";
    leaf is-enabled {
      type boolean;
      description "Is ZTP enabled";
    }
    leaf is-secure {
      type boolean;
      description "Is ZTP secure mode enabled";
    }
    leaf vlan-discovery {
      type Ztp-vlan-discovery;
      description
        "ZTP Vlan discovery mode - static, dynamic or
        disabled";
    }
    leaf is-breakout-enabled {
      type boolean;
      description "Will ZTP breakout down interfaces";
    }
    leaf is-retry-enabled {
      type boolean;
      description "Will ZTP keep retrying";
    }
    leaf fetchers {
      type string;
      description "ZTP fetchers ordered based on priority";
    }
  }
}
