module Cisco-IOS-XR-ip-daps-oper {

  /*** NAMESPACE / PREFIX DEFINITION ***/

  namespace "http://cisco.com/ns/yang/Cisco-IOS-XR-ip-daps-oper";


  prefix "ip-daps-oper";

  /*** LINKAGE (IMPORTS / INCLUDES) ***/

  import ietf-inet-types { prefix "inet"; }

  import Cisco-IOS-XR-types { prefix "xr"; }

  import cisco-semver { prefix "semver"; }

  include Cisco-IOS-XR-ip-daps-oper-sub1 {
    revision-date 2019-04-05;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ip-daps package operational data.

     This module contains definitions
     for the following management objects:
       address-pool-service: Pool operational data

     Copyright (c) 2013-2019 by Cisco Systems, Inc.
     All rights reserved.";

  revision "2019-04-05" {
    description
      "Establish semantic version baseline.";
    semver:module-version "1.0.1";
  }

  revision "2015-11-09" {
    description
      "IOS XR 6.0 revision.";
  }

  container address-pool-service {
    config false;
    description "Pool operational data";

    container nodes {
      description "Pool operational data for a particular location";

      list node {
        key "node-name";
        description "Location. For eg., 0/1/CPU0";

        container pools {
          description "List of IPv4/IPv6 pool data";

          list pool {
            key "pool-name";
            description "Pool data by pool name";

            container address-ranges {
              description "Summary info for pool";

              list address-range {
                key "start-address";
                description "Start Address of the Range";
                leaf start-address {
                  type inet:ip-address-no-zone;
                  description "IP Address";
                }
                uses IP-DAPS-SHOW-POOL-BRIEF;
              }
            }

            container allocated-addresses {
              description "Detailed info for the Pool";
              uses DAPS-POOL-DETAIL;
            }

            container configuration {
              description "Configuration info for pool";
              uses IP-DAPS-SHOW-POOL-CFG;
            }
            leaf pool-name {
              type xr:Cisco-ios-xr-string;
              description "The pool name";
            }
          }
        }

        container total-utilization {
          description "Show total utilization for pool";
          uses IP-DAPS-SHOW-POOL-TOTAL-UTIL;
        }

        container vrfs {
          description "Pool VRF data";

          list vrf {
            key "vrf-name";
            description "VRF level Pool information";

            container ipv4 {
              description "IPv4 pool VRF data";
              uses DAPS-VRF-INFO;
            }

            container ipv6 {
              description "IPv6 Pool VRF data";
              uses DAPS-VRF-INFO;
            }
            leaf vrf-name {
              type xr:Cisco-ios-xr-string;
              description "The VRF name";
            }
          }
        }
        leaf node-name {
          type xr:Node-id;
          description "Node name";
        }
      }
    }
  }
}
