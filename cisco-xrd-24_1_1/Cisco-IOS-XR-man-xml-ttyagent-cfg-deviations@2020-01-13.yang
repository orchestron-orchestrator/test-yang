module Cisco-IOS-XR-man-xml-ttyagent-cfg-deviations {

    /*** NAMESPACE / PREFIX DEFINITION ***/

    namespace "http://cisco.com/ns/yang/Cisco-IOS-XR-man-xml-ttyagent-cfg-deviations.yang";

    prefix "cisco-ios-ttyagent-cfg-dev";

    /*** LINKAGE (IMPORTS / INCLUDES) ***/
    import Cisco-IOS-XR-man-xml-ttyagent-cfg { prefix mxt-dev; }

    /*** META INFORMATION ***/
    organization "Cisco Systems, Inc.";

    contact
        "Cisco Systems, Inc.
        Customer Service

        Postal: 170 West Tasman Drive
        San Jose, CA 95134

        Tel: 1 800 553-NETS

        E-mail: cs-yang@cisco.com";

    description 
        "This module contains a set of deviations of leaf memory range data
        model set for Cisco IOS-XR.

        Copyright (c) 2016, 2020 by Cisco Systems, Inc.
        All rights reserved.";

    revision "2020-01-13" {
        description
            "Initial revision applicable to IOS-XR 6.1.2 and older releases";
    }

    deviation /mxt-dev:xr-xml/mxt-dev:agent/mxt-dev:default/mxt-dev:throttle/mxt-dev:memory{
        deviate replace {
           type uint32 {
              range "100..1024";
           }
        }
    }
    
    deviation /mxt-dev:xr-xml/mxt-dev:agent/mxt-dev:tty/mxt-dev:throttle/mxt-dev:memory{
        deviate replace {
           type uint32 {
              range "100..1024";
           }
        }
    }
    
    deviation /mxt-dev:xr-xml/mxt-dev:agent/mxt-dev:ssl/mxt-dev:throttle/mxt-dev:memory{
        deviate replace {
           type uint32 {
              range "100..1024";
           }
        }
    }
}
