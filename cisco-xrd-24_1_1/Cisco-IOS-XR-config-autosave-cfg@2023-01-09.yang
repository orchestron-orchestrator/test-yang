module Cisco-IOS-XR-config-autosave-cfg {

  /*** NAMESPACE / PREFIX DEFINITION ***/

  namespace "http://cisco.com/ns/yang"+
    "/Cisco-IOS-XR-config-autosave-cfg";


  prefix "config-autosave-cfg";

  /*** LINKAGE (IMPORTS / INCLUDES) ***/

  import Cisco-IOS-XR-types { prefix "xr"; }

  import cisco-semver { prefix "semver"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR config-autosave package configuration.

     This module contains definitions
     for the following management objects:
       config-autosave-cfg: config_autosave config

     Copyright (c) 2013-2023 by Cisco Systems, Inc.
     All rights reserved.";

  revision "2023-01-09" {
    description
      "Updated password datatypes.";
    semver:module-version "1.0.0";
  }

  revision "2023-01-05" {
    description
      "Made filename and password fields mandatory.";
  }

  revision "2022-11-17" {
    description
      "Add ranges to wait-time fields. Change filename to store protocol and url remainder.";
  }

  revision "2022-10-05" {
    description
      "IOS XR 7.9.1 revision";
  }

  revision "2019-04-05" {
    description
      "Establish semantic version baseline.";
  }

  revision "2015-11-09" {
    description
      "IOS XR 6.0 revision.";
  }

  typedef Encryption-algorithm {
    type enumeration {
      enum default {
        value 1;
        description "Default 2-way encryption algorithm";
      }
      enum aes {
        value 2;
        description "AES encryption algorithm";
      }
    }
    description "Encryption algorithm";
  }

  container config-autosave-cfg {
    presence "CLI submode compatibility.";
    description "config_autosave config";

    container config-autosave-cfg-filename {
      presence "Indicates a config-autosave-cfg-filename node is"+
        " configured.";
      description
        "Autosaved config will be sent to this
        destination";
      leaf protocol {
        type string;
        mandatory true;
        description "Protocol (e.g. sftp:)";
      }
      leaf url-remainder {
        type string;
        mandatory true;
        description
          "Remainder of url (e.g.
          //username@host/local_path)";
      }
    }

    container config-autosave-cfg-waittime {
      presence "Indicates a config-autosave-cfg-waittime node is"+
        " configured.";
      description
        "How long to wait after running config changes to
        start next autosave";
      leaf days {
        type uint32 {
          range "0..365";
        }
        units "day";
        mandatory true;
        description "Days to wait";
      }
      leaf hours {
        type uint32 {
          range "0..23";
        }
        units "hour";
        mandatory true;
        description "Hours to wait";
      }
      leaf minutes {
        type uint32 {
          range "0..59";
        }
        units "minute";
        mandatory true;
        description "Minutes to wait";
      }
      leaf seconds {
        type uint32 {
          range "0..59";
        }
        units "second";
        mandatory true;
        description "Seconds to wait";
      }
    }

    container config-autosave-cfg-password {
      description
        "The ENCRYPTED password for the remote url (if
        filepath is remote)";
      leaf algorithm {
        type Encryption-algorithm;
        description
          "The encryption algorithm used for the password";
      }
      leaf default-encrypted-password {
        when "../algorithm = 'default'" {
          description "../Algorithm = Default";
        }
        type xr:Proprietary-password;
        description
          "The default-encrypted authentication password
          for the remote url";
      }
      leaf aes-encrypted-password {
        when "../algorithm = 'aes'" {
          description "../Algorithm = AES";
        }
        type xr:Type6-password;
        description
          "The aes-encrypted authentication password for
          the remote url";
      }
    }
    leaf config-autosave-cfg-timestamp {
      type empty;
      description "Append timestamp to autosave filename";
    }
    leaf config-autosave-cfg-maximum {
      type uint32 {
        range "1..4294967295";
      }
      description "Max number of autosaves to keep";
    }
  }
}
