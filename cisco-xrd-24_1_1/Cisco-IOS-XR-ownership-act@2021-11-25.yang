module Cisco-IOS-XR-ownership-act {
  namespace "http://cisco.com/ns/yang/Cisco-IOS-XR-ownership-act";
  prefix sb-ownership;

  import Cisco-IOS-XR-types {
    prefix csc;
  }

  organization
    "Cisco Systems, Inc.";
  contact
    "Cisco Systems, Inc.
     Customer Service
     Postal: 170 West Tasman Drive
     San Jose, CA 95134
     Tel: +1 800 553-NETS
     E-mail: cs-yang@cisco.com";
  description
    "This module defines procedure to apply device ownership. 

     Copyright (c) 2017 IETF Trust and the persons identified
     as authors of the code. All rights reserved.

     Redistribution and use in source and binary forms, with
     or without modification, is permitted pursuant to, and
     subject to the license terms contained in, the Simplified
     BSD License set forth in Section 4.c of the IETF Trust''s
     Legal Provisions Relating to IETF Documents
     (http://trustee.ietf.org/license-info).

     This version of this YANG module is part of RFC VVVV; see
     the RFC itself for full legal notices.";

  revision "2021-11-25" {
    description
      "Removed signer from session-terminate";
  }

  revision "2021-10-22" {
    description
      "NSO build related fixes";
  }

  revision "2021-09-22" {
    description
      "Initial revision.";
  }


  typedef Bool-Input {
    type enumeration {
      enum false {
        value 0;
        description "No";
      }
      enum true {
        value 1;
        description "Yes";
      }
    }
    description
    "Input true or false";
  }

  rpc oshp-ovoc-apply {
    description
      "Establishes ownership of the device/system.
       Returns whether operation is succeeded or failed.";

    input {
      leaf ov-path {
        type string;
        mandatory true;
        description
         "Path to tar file containing Ownership Vouchers(OV) on local storage";
      }
      leaf oc-path {
        type string;
        mandatory true;
        description
          "Path to Ownership Certificate(OC) CMS on local storage";
      }
      leaf crl-optional {
        type Bool-Input; 
        description
          "CRL check enforcement ignore enable/disable";
      }
      leaf cert-chain-partial-match {
        type Bool-Input;
        description
        "Perform partial/full match of OC against trustpoint"; 
      }

      csc:xr-task "system";
      csc:cli-command "platform security device-ownership <ov> <oc> [certificate-chain partial-match ] [ crl optional ]";
    }
    csc:xr-task "system";
  }


  rpc oshp-ct-session-terminate {
    description
    "Terminate an existing Re-Image Protection Session.";

    csc:xr-task "system";
    csc:cli-command "platform security reimage-protection session-terminate";
  }



  rpc oshp-reimage-protection-challenge {
    description
      "Enable or Disable Re-Image Protection - Challenge";

    input {
      leaf reimage-protection {
        type enumeration {
            enum enable {
                value 1;
                description
                "Enable re-image protection";
            }
            enum disable {
                value 2;
                description
                "Disable re-image protection";
            }
        }
        mandatory true;
        description
          "Re-image protection";
      }
    
      leaf signer {
        type enumeration {
            enum cisco {
                value 1;
                description
                "Use Cisco consent token key for challenge";
            }
            enum customer {
                value 2;
                description
                "Use Customer consent token key for challenge";
            }
        }
        mandatory true;
        description
          "Generate challenge string";
      }
    }

    output {
      leaf challenge-string {
        type string;
        description
        "Challenge string output";
      }
    }

    csc:xr-task "system";
      csc:cli-command "platform security reimage-protection [ enable | disable ] challenge [ cisco | customer ] ";
    csc:xr-task "system";
  }



  rpc oshp-reimage-protection-response {
    description
      "Enable or Disable Re-Image Protection - Response";

    input {
      leaf reimage-protection {
        type enumeration {
            enum enable {
                value 1;
                description
                "Enable re-image protection";
            }
            enum disable {
                value 2;
                description
                "Disable re-image protection";
            }
        }
        mandatory true;
        description
          "Re-image protection";
      }

      leaf challenge-response {
        type string;
        mandatory true;
        description
        "Accept challenge response string";
      }
    }
    csc:xr-task "system";
    csc:cli-command "platform security reimage-protection [ enable | disable ] response ";
  }
}
