module Cisco-IOS-XR-um-cont-ether-cfg {

  /*** NAMESPACE / PREFIX DEFINITION ***/

  namespace "http://cisco.com/ns/yang/Cisco-IOS-XR-um-cont-ether-cfg";
  prefix um-cont-ether-cfg;

  /*** LINKAGE (IMPORTS / INCLUDES) ***/

  import Cisco-IOS-XR-types {
    prefix xr;
  }
  import Cisco-IOS-XR-um-interface-cfg {
    prefix a1;
  }

  import cisco-semver { prefix "semver"; }

  /*** META INFORMATION ***/

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR cont-ether package configuration.

     This YANG module augments the
     modules with configuration data.

     Copyright (c) 2021-2022 by Cisco Systems, Inc.
     All rights reserved.";

  revision 2022-07-20 {
    description
      "Added prbs support
       2022-07-11
         Added missing description statement to nodes
       2022-06-01
         Adjusted controller augmentation hierarchy";
    semver:module-version "1.1.0";
  }

  revision "2021-05-07" {
    description
      "Initial release";
    semver:module-version "1.0.0";
  }

  grouping CONT-BODY {
    description
      "Grouping for controller";
    container flow-control {
      description
        "Ethernet controller flow control";
      container ingress {
        presence "Indicates a ingress node is configured.";
        description
          "Set the flow control parameter to ingress";
      }
    }
    container perf-mon {
      description
        "Performance Monitoring";
      container disable {
        presence "Indicates a disable node is configured.";
        description
          "Disable performance monitoring";
      }
    }
    leaf loopback {
      type enumeration {
        enum external {
          value 0;
          description
            "Enable external loopback (requires loopback connector)";
        }
        enum internal {
          value 1;
          description
            "Enable internal loopback";
        }
        enum line {
          value 2;
          description
            "Enable line loopback";
        }
      }
      description
        "Set the loopback mode on a controller";
    }
    container laser-squelch {
      presence "Indicates a laser-squelch node is configured.";
      description
        "Enable Ethernet controller laser-squelch";
    }
    leaf fec {
      type enumeration {
        enum none {
          value 0;
          description
            "Disable any FEC enabled on the interface";
        }
        enum standard {
          value 1;
          description
            "Set the standard (Reed-Solomon) FEC";
        }
      }
      description
        "Set the Forward Error Correction mode on a controller";
    }
    container prbs {
      presence "Indicates a prbs node is configured.";
      description
        "Configure Pseudo Random Binary Sequence test";
      leaf mode {
        type enumeration {
          enum source {
            value 1;
            description
              "source mode";
          }
          enum sink {
            value 2;
            description
              "sink mode";
          }
          enum source-sink {
            value 3;
            description
              "source-sink mode";
          }
        }
        description
          "Configure PRBS mode";
      }
      leaf pattern {
        type enumeration {
          enum pn7 {
            value 1;
            description
              "Configure PRBS pattern pn7";
          }
          enum pn9 {
            value 2;
            description
              "Configure PRBS pattern pn9";
          }
          enum pn11 {
            value 3;
            description
              "Configure PRBS pattern pn11";
          }
          enum pn15 {
            value 4;
            description
              "Configure PRBS pattern pn15";
          }
          enum pn23 {
            value 5;
            description
              "Configure PRBS pattern pn23";
          }
          enum pn31 {
            value 6;
            description
              "Configure PRBS pattern pn31";
          }
          enum user-defined {
            value 7;
            description
              "Configure any 64-bit user defined pattern";
          }
        }
        description
          "Configure PRBS pattern";
      }
      leaf direction {
        type enumeration {
          enum line {
            value 1;
            description
              "Run prbs towards line side";
          }
          enum system {
            value 2;
            description
              "Run prbs towards system side";
          }
        }
        description
          "Configure prbs direction";
      }
      leaf error-inject {
        type enumeration {
          enum single {
            value 1;
            description
              "Inject error once";
          }
          enum continuous {
            value 2;
            description
              "Inject error continuously";
          }
        }
        description
          "Inject errors in the PRBS pattern";
      }
      leaf framing {
        type enumeration {
          enum framed {
            value 2;
            description
              "Framed PRBS";
          }
          enum unframed {
            value 1;
            description
              "Unframed PRBS";
          }
        }
        description
          "Configure prbs framing type";
      }
      leaf user-pattern {
        type xr:Hex-long-integer;
        mandatory true;
        description
          "PRBS user defined pattern(64-bit hex value)";
      }
    }
    container holdoff-time {
      description
        "Holdoff time configuration";
      leaf trunk-fault {
        type uint32 {
          range "0..3000" {
            description
              "Time in ms";
          }
        }
        description
          "Holdoff time trunk fault configuration";
      }
    }
    container extended-loopback {
      description
        "Extended loopback (diagnostics)";
      container levels {
        description
          "Level at which to loopback";
        list level {
          key "level-id";
          description
            "Level at which to loopback";
          leaf level-id {
            type uint32 {
              range "1..3" {
                description
                  "";
              }
            }
            description
              "Level at which to loopback";
          }
        }
      }
    }
  }

  augment "/a1:controllers/a1:controller" {
    description
      "This augment extends active nodes configuration";
    /*  when "a1:controller-name[starts-with(text(),'FortyGigECtrlr')]" +
         " or a1:controller-name[starts-with(text(),'FourHundredGigECtrlr')]" +
         " or a1:controller-name[starts-with(text(),'GigabitEthCtrlr')]" +
         " or a1:controller-name[starts-with(text(),'HundredGigECtrlr')]" +
         " or a1:controller-name[starts-with(text(),'TenGigECtrlr')]" {
          tailf:dependency 'a1:controller-name';
    }
     */
    uses CONT-BODY;
  }

  augment "/a1:controllers/a1:controller-preconfigure" {
    description
      "This augment extends preconfigured nodes
       configuration";
    /*  when "a1:controller-name[starts-with(text(),'FortyGigECtrlr')]" +
         " or a1:controller-name[starts-with(text(),'FourHundredGigECtrlr')]" +
         " or a1:controller-name[starts-with(text(),'GigabitEthCtrlr')]" +
         " or a1:controller-name[starts-with(text(),'HundredGigECtrlr')]" +
         " or a1:controller-name[starts-with(text(),'TenGigECtrlr')]" {
          tailf:dependency 'a1:controller-name';
    }
     */
    uses CONT-BODY;
  }
}
