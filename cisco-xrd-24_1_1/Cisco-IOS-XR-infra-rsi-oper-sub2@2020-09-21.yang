submodule Cisco-IOS-XR-infra-rsi-oper-sub2 {

  belongs-to Cisco-IOS-XR-infra-rsi-oper {
    prefix Cisco-IOS-XR-infra-rsi-oper;
  }

  /*** LINKAGE (IMPORTS / INCLUDES) ***/

  import cisco-semver { prefix "semver"; }

  include Cisco-IOS-XR-infra-rsi-oper-sub1 {
    revision-date 2020-09-21;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR infra-rsi package operational data.

     Copyright (c) 2013-2020 by Cisco Systems, Inc.
     All rights reserved.";

  revision "2020-09-21" {
    description
      "Operational support for new safi bier.";
    semver:module-version "1.1.0";
  }

  revision "2019-04-05" {
    description
      "Establish semantic version baseline.";
    semver:module-version "1.0.1";
  }

  revision "2019-02-13" {
    description
      "Fixing yang oper coverage.";
  }

  revision "2018-11-26" {
    description
      "Fixing yang usability issues.";
  }

  revision "2017-09-07" {
    description
      "Fixed type translation error.";
  }

  revision "2017-05-01" {
    description
      "Fixing backward compatibility error in module.";
  }

  revision "2015-01-07" {
    description
      "IOS XR 5.3.1 revision.";
  }

  typedef Source {
    type enumeration {
      enum configured {
        value 1;
        description "Configured";
      }
      enum from-group {
        value 2;
        description "From group";
      }
      enum inherited {
        value 4;
        description "Inherited";
      }
      enum from-optical {
        value 8;
        description "From optical";
      }
      enum configured-and-notified {
        value 17;
        description "Configured and notified";
      }
      enum from-group-and-notified {
        value 18;
        description "From group and notified";
      }
      enum inherited-and-notified {
        value 20;
        description "Inherited and notified";
      }
      enum from-optical-and-notified {
        value 24;
        description "From optical and notified";
      }
    }
    description "Source";
  }
  typedef Priority {
    type enumeration {
      enum critical {
        value 0;
        description "Critical";
      }
      enum high {
        value 1;
        description "High";
      }
      enum medium {
        value 2;
        description "Medium";
      }
      enum low {
        value 3;
        description "Low";
      }
      enum very-low {
        value 4;
        description "Very low";
      }
      enum invald {
        value 5;
        description "Invalid";
      }
    }
    description "Priority";
  }

  grouping RSI-SRLG-NAME-INTF-SHOW {
    description "Interface name for RSI SRLG";

    container interfaces {
      description "Interfaces information";
      uses RSI-SRLG-INTF-SHOW;
    }
    leaf srlg-name-xr {
      type string;
      description "SRLG name";
    }
    leaf srlg-value {
      type uint32;
      description "SRLG value";
    }
    leaf description {
      type string;
      description "SRLG description";
    }
  }

  grouping RSI-SRLG-INTF-SHOW {
    description "Interface for RSI SRLG";

    list interface-name {
      description "Name of the interface which has SRLG values";
      leaf entry {
        type String1;
        description "Name of the interface which has SRLG values";
      }
    }
  }

  grouping RSI-SRLG-RSIP-LIST {
    description "RSIP list for RSI SRLG";
    leaf rsip-name {
      type string;
      description "list of names matching rsip";
    }
  }

  grouping RSI-SRLG-ATTR-DETAIL {
    description "Attribute details for RSI SRLG";
    leaf srlg-value {
      type uint32;
      description "SRLG value";
    }
    leaf priority {
      type Priority;
      description "Priority level";
    }
    leaf source {
      type Source;
      description "Source flag";
    }
    leaf source-name {
      type string;
      description "Source for SRLG value";
    }
    leaf srlg-index {
      type uint16;
      description "Index";
    }
  }

  grouping RSI-SRLG-INTF-DETAIL-SHOW {
    description "Interface for RSI SRLG";
    leaf groups {
      type uint32;
      description "Group count";
    }
    leaf nodes {
      type uint32;
      description "Nodes";
    }

    list srlg-attribute {
      description "SRLG attributes";
      uses RSI-SRLG-ATTR-DETAIL;
    }

    list rsip {
      description "rsip list";
      uses RSI-SRLG-RSIP-LIST;
    }
  }

  grouping RSI-SRLG-DESC-SHOW {
    description "Show RSI SRLG Description";
    leaf srlg-value {
      type uint32;
      description "SRLG value";
    }
    leaf description {
      type string;
      description "SRLG description";
    }
  }

  grouping RSI-SRLG-INHLOC-SHOW {
    description "Location for RSI SRLG";
    leaf location {
      type string;
      description "Inherit node name";
    }
    leaf node-values {
      type uint32;
      description "Node value count";
    }

    list srlg-attribute {
      description "SRLG attribute";
      uses RSI-SRLG-ATTR-BRIEF;
    }
  }

  grouping RSI-SRLG-NAME-VALUE-SHOW {
    description "Name value for RSI SRLG";
    leaf srlg-value {
      type uint32;
      description "SRLG value";
    }
    leaf srlg-name-xr {
      type string;
      description "SRLG name";
    }
  }

  grouping RSI-SRLG-RSIP-SHOW {
    description "RSIP for RSI SRLG";
    leaf optical-layer-interface-name {
      type string;
      description "Optics interface";
    }
    leaf registrations {
      type uint32;
      description "Registration count";
    }
    leaf interface-values {
      type uint32;
      description "Interface value count";
    }

    list srlg-attribute {
      description "SRLG attribute";
      uses RSI-SRLG-ATTR-BRIEF;
    }
  }

  grouping RSI-SRLG-INTF-BRIEF-SHOW {
    description "Interface for RSI SRLG";
    leaf interface-name-xr {
      type string;
      description "Interface list";
    }
    leaf value-count {
      type uint32;
      description "Values";
    }
    leaf registrations {
      type uint32;
      description "Registration count";
    }

    list srlg-value {
      description "SRLG values";
      leaf entry {
        type uint32;
        description "SRLG values";
      }
    }
  }

  grouping RSI-SRLG-ATTR-BRIEF {
    description "Attribute for RSI SRLG";
    leaf srlg-value {
      type uint32;
      description "SRLG value";
    }
    leaf priority {
      type Priority;
      description "Priority level";
    }
    leaf srlg-index {
      type uint16;
      description "Index";
    }
  }

  grouping RSI-SRLG-GROUP-SHOW {
    description "Show RSI SRLG group";
    leaf group-name-xr {
      type string;
      description "Group name";
    }
    leaf group-values {
      type uint32;
      description "Group value count";
    }

    list srlg-attribute {
      description "SRLG attribute";
      uses RSI-SRLG-ATTR-BRIEF;
    }
  }

  grouping RSI-VRFGROUP-ATTR-BRIEF {
    description "Attribute brief for RSI VRF group";
    leaf vrf-name {
      type string;
      description "VRF name";
    }
  }

  grouping RSI-VRFGROUP-GROUP-SHOW {
    description "Show RSI VRF group";
    leaf vr-fs {
      type uint32;
      description "Number of VRFs in this VRF group";
    }
    leaf forward-reference {
      type boolean;
      description "VRF group not present but used";
    }

    list vrf {
      description "VRF group's VRF";
      uses RSI-VRFGROUP-ATTR-BRIEF;
    }
  }
}
