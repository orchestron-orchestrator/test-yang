submodule Cisco-IOS-XR-fib-common-oper-sub3 {

  belongs-to Cisco-IOS-XR-fib-common-oper {
    prefix Cisco-IOS-XR-fib-common-oper;
  }

  /*** LINKAGE (IMPORTS / INCLUDES) ***/

  import ietf-yang-types { prefix "yang"; }

  import Cisco-IOS-XR-types { prefix "xr"; }

  import cisco-semver { prefix "semver"; }

  include Cisco-IOS-XR-fib-common-oper-sub2 {
    revision-date 2024-01-12;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR fib-common package operational data.

     Copyright (c) 2013-2024 by Cisco Systems, Inc.
     All rights reserved.";

  revision "2024-01-12" {
    description
      "Add back error/oor state for telemetry in oc-aft-l3 model
       2023-12-01
         Add platform-pbtsv6-support to platform capabilities
       2023-11-27
         Optimized schema for linklocal. Added is-non-recursive field to IP prefixes.
       2023-10-25
         Added GIL ID in PWHE information and Interface List attribute
       2023-10-19
         Added NextHop group ID to ext client output
       2023-10-11
         Added schema for external client, fixed schema for hardware egress/ingress
       2023-10-10
         Added and modified NPU mask and PWHE information
       2023-10-04
         Added encap-id and stat-id to recursive-nexthop dependents.
       2023-10-02
         Added VXLAN TEP tables.
       2023-09-21
         Eliminate name conflicts between keys and values
       2023-09-18
         Separated schema of linklocal prefix table from generic prefix table.
       2023-09-14
         Added via-nexthop-group to show cef output
       2023-08-15
         Added new errors sub-tree.
       2023-07-31
         Made hierarchical-loadbalancing parameters mandatory
       2023-07-28
         Internal cleanup, some type name changes.
       2023-07-26
         Fixed schema for exact-route and linklocal
       2023-07-17
         Changed pbts related variable type from static to dynamic array
       2023-07-13
         Added is-unresolved and is-frr to prefix tables
       2023-07-07
         Standardized leaf names and types throughout.
       2023-06-26
         Fix schema for hardware egress/ingress option
       2023-06-15
         Changed vni-info-key-type to an enum and added tblid-vni-key to vni-info-key-type
       2023-06-02
         Two Stage platform ObjectId capability added for cef-misc
       2023-06-01
         Added new field to ltep-nve-tunnels in order keep track of destination address protocol
       2023-05-31
         SRv6 accounting support added for FIB cef
       2023-05-25
         SRv6 accounting support added for FIB cef-accounting
       2023-05-24
         Added new detail field for hardware egress/ingress option
       2023-05-11
         Added class-id to support full exact-route functionality
       2023-05-08
         Remove oc-aft model from fib oper model
       2023-05-04
         Added new field to rtep-tunnels in order keep track of destination address protocol
       2023-04-24
         Combined separate evni tables for BGP and RTEP-ID to single evni table
       2023-04-15
         Added changes for show cef Interface
       2023-04-14
         Added hardware ingress and egress path for evni
       2023-04-05
         Added srv6_hardware ingress/egress
       2023-03-31
         Added resource-summary-infos and modified ip-prefix-detail
       2023-03-29
         Changed recursive nexthop display to be generic for address types
       2023-03-28
         Modified Interface List ID size from 16-bit to 32-bit
       2023-03-28
         Modifed fib_sh_policy_rl_entry rate field to uint64_t
       2023-03-20
         Added some preprograming related fields.
       2023-03-18
         Removed node tag from cef-accounting container.
       2023-03-06
         Added global policy table
       2023-02-07
         Added Exact route schema changes
       2023-02-06
         Added proto-retry-db-summary.
       2023-02-06
         Added disable-rfc5549-ipv4-over-ipv6-nexthop platform capability.
       2023-01-27
         Updated schema for ResourceHardwareIngress and Egress support
       2023-01-27
         Added exceptions-v4, exceptions-v6 and exceptions-mpls.
       2023-01-25
         Added global-retry-db-summary.
       2023-01-24
         Added cef-table-summary, drops-v6 and drops-mpls.
       2023-01-23
         srv6 accounting support
       2023-01-20
         Summary statistics: Added udp-src-port-msb information
       2023-01-04
         Updated evni-tunnel-bgp keys for VxLAN support
       2022-12-20
         Added changes for NHInfoHardwareIngress and NHInfoHardwareEgress in schema file.
       2022-12-06
         Added destionation address to Tunnel Decap, added destination address and underlay table id to Tunnel Decap-NVE
       2022-11-07
         protocol origin changes
       2022-11-01
         Updated FIB ext-client info bag to support ECD LTEP registrations
       2022-10-17
         CNHG changes
       2022-10-05
         Added PWHE and NPU mask for interface details
       2022-10-04
         Tunnel Encap/Decap: Added Prefix Length to the source and destination addresses
       2022-09-22
         Rate limiter statistics: Added drop stats
       2022-09-15
         Added Internal ID in PW-HE extension
       2022-08-29
         Summary statistics: Added udp-port information
       2022-07-19
         Added async-ack-support to FIB-SH-PLAT-CAPABILITIES, and ack-status, ack-latency, to FIB-GRIBI-ENTRY-INFO and FIB-GLOBAL-GRIBI-ENTRY.
       2022-07-07
         Added VRF base filtering for MPLS label stats
       2022-06-14
         Added program id, dst_ip and src_ip in next-hop and nhg fib.bag
       2022-06-13
         Added destination address to nve-ltep bag
       2022-05-13
         Added aft vrf-id to gribi bags
       2022-04-27
         Added vxlan-vni-id to ltep-tunnel
       2022-04-25
         Added RNH state
       2022-04-08
         Added table statistics
       2022-03-31
         Added sr-frr-nhid to frr-nhinfo-pending
       2022-03-24
         Added retry counts to object summary attributes
       2022-03-15
         Added vxlan-tunnels
       2022-03-01
         Added policy and hardware ingress and egress paths
       2022-02-16
         Added some SRv6 SIDs data
       2021-12-14
         Added gribi-table and hardware ingress and egress paths
       2021-11-26
         Added ltep-tunnels and hardware ingress and egress paths
       2021-11-05
         Added rtep-tunnels and hardware ingress and egress paths
       2021-11-03
         Added ltep-nve-tunnels hardware ingress and egress paths
       2021-10-23
         Added ltep-nve-tunnels and added object-id to object-base";
    semver:module-version "5.0.0";
  }

  revision "2021-10-17" {
    description
      "Modify the type of list fsum-attr-cnt
      2021-09-17
          Rename lists unicast-prefix, broadcast-prefix and leafs num-retry-objects, old-unresolved-entries, new-unresolved-entries, unresolved-entries
      2021-07-30
          Added evpn bridge ID and SHG ID to srv6-information-for-path bag
      2021-07-06
          Added global-main subtree and support show CLIs for FIB IPC infra
      2021-05-25
          Migrate NHINFO to TI infra";
    semver:module-version "4.0.0";
  }

  revision "2020-12-02" {
    description
      "Adding per-object accounting.
      2020-10-20
           NBC documentation of CSCvu06764, CSCvv14573,CSCvv76648
      2020-05-26
           Update SRv6 Block Space naming convention
      2020-05-05
           changes related to treat SRv6 and SID as well-known when parsing XML for yang";
    semver:module-version "3.0.0";
  }

  revision "2020-01-16" {
    description
      "NBC documentation of CSCvs27272,CSCvs22018,CSCvs45512
      2019-10-29
         Updated srv6 global bag";
    semver:module-version "2.0.0";
  }

  revision "2019-09-27" {
    description
      "IOS XR 7.0.x revision.";
    semver:module-version "1.1.0";
  }

  revision "2019-04-05" {
    description
      "Establish semantic version baseline.";
    semver:module-version "1.0.0";
  }

  revision "2019-04-02" {
    description
      "Fixed schema descriptions.";
  }

  revision "2017-09-07" {
    description
      "Fixed type translation error.";
  }

  revision "2017-05-01" {
    description
      "Fixing backward compatibility error in module.";
  }

  revision "2017-01-20" {
    description
      "IOS XR 6.2.1 revision";
  }

  revision "2015-11-09" {
    description
      "IOS XR 6.0 revision.";
  }

  typedef Next-hop {
    type enumeration {
      enum tx {
        value 0;
        description "TX";
      }
      enum rx {
        value 1;
        description "RX";
      }
      enum special {
        value 2;
        description "Special";
      }
    }
    description "MPLS Forwarding Next Hop Type";
  }
  typedef Proto {
    type enumeration {
      enum ipv4 {
        value 0;
        description "IPv4";
      }
      enum ipv6 {
        value 1;
        description "IPv6";
      }
      enum mpls {
        value 2;
        description "MPLS";
      }
    }
    description "MPLS Forwarding Protocol Type";
  }

  grouping MPLS-FRR-DB-ENTRY {
    description "MPLS FRR DB ENTRY";

    container frr-db {
      description "FRR DB";
      uses FIB-MPLS-FRR-DB-ENTRY;
    }
    leaf outgoing-lable-string {
      type string;
      description "Output label in string format";
    }
    leaf frr-lable-string {
      type string;
      description "FRR label in string format";
    }
  }

  grouping MPLS-SH-TEHEAD {
    description "Information about TE tunnel head";

    container tunnel-info {
      description "Tunnel head information";
      uses FIB-MPLS-SH-TUN-INFO;
    }

    container fwdg {
      description "Tunnel forwarding information";
      uses MPLS-SH-LEAF;
    }
  }

  grouping MPLS-LABEL-SECURITY-SUMMARY {
    description "MPLS LABEL SECURITY SUMMARY";
    leaf rpf-drops {
      type uint64;
      description "RPF drops";
    }
    leaf multi-label-drops {
      type uint64;
      description "Multi-label drops";
    }
  }

  grouping MPLS-LABEL-SECURITY-INTF {
    description "MPLS LABEL SECURITY INTF";
    leaf rpf-enabled {
      type boolean;
      description "RPF is enabled on interface";
    }
    leaf rpf-supported {
      type boolean;
      description "RPF stats supported per interface";
    }
    leaf mld-enabled {
      type boolean;
      description "Multi-label drop is enabled on interface";
    }
    leaf mld-supported {
      type boolean;
      description
        "Multi-label drop counters are supported per
        interface";
    }
    leaf rpf-drops {
      type uint64;
      description "RPF drops";
    }
    leaf multi-label-drops {
      type uint64;
      description "Multi-label drops";
    }
    leaf rpfifh {
      type xr:Interface-name;
      description "RPF interface handle";
    }
  }

  grouping MPLS-MCAST-INFO {
    description "Information for mpls multicast entries";
    leaf multicast-mol-base-flags {
      type uint32;
      description "MOL base flags";
    }
    leaf multicast-mol-flags {
      type uint16;
      description "MOL flags";
    }
    leaf multicast-mol-referance-count {
      type uint16;
      description "MOL refcount";
    }
    leaf multicast-tunnel-interface-handler {
      type xr:Interface-name;
      description "multicast mpls tunnel";
    }
    leaf multicast-tunnel-id {
      type uint32;
      description
        "multicast mpls P2MP-TE tunnel id or MLDP Tunnel
        LSMID on all nodes";
    }
    leaf multicast-tunnel-next-hop-information {
      type uint32;
      description "multicast nhinfo for p2mp TE Head";
    }
    leaf multicast-tunnel-lspvif {
      type uint32;
      description "multicast LSPVIF for MLDP Tunnels";
    }
    leaf multicast-mpls-output-paths {
      type uint16;
      description "num multicast mpls output paths ";
    }
    leaf multicast-mpls-protocol-output-paths {
      type uint16;
      description "num multicast mpls prot output paths ";
    }
    leaf multicast-mpls-local-output-paths {
      type uint16;
      description "num multicast mpls local output paths";
    }
    leaf multicast-rpf-id {
      type uint32;
      description "The multicast RPF-ID ";
    }
    leaf multicast-encap-id {
      type uint32;
      description "The multicast ENCAP-ID ";
    }
    leaf multicast-platform-data-length {
      type uint8;
      description "The multicast platform data len";
    }
    leaf multicast-platform-data {
      type yang:hex-string;
      description "The multicast platform data";
    }
  }

  grouping MPLS-LDI-INFO {
    description
      "Detailed load sharing information for mpls table
      entries";
    leaf ldi-hardware-information {
      type yang:hex-string;
      description "Hardware info";
    }
  }

  grouping MPLS-ADJ-EXACT-ROUTE-HASH-INFO {
    description "MPLS Adj Exact-Route Hash info";
    leaf hash-index-is-valid {
      type boolean;
      description "Is Hash Index valid?";
    }
    leaf hash-index {
      type uint8;
      description "Hash Index value";
    }
  }

  grouping MPLS-FWD-INFO {
    description "MPLS FWD INFO";
    leaf l3-mtu {
      type uint32;
      description "L3 MTU";
    }
    leaf total-encapsulation-size {
      type uint32;
      description "Total encapsulation size: L2 + MPLS";
    }
    leaf mac-size {
      type uint32;
      description "Length of L2 encapsulation";
    }
    leaf transmit-number-of-packets-switched {
      type uint64;
      description "Number of packets switched";
    }
    leaf transmit-number-of-bytes-switched {
      type uint64;
      units "byte";
      description "Number of Bytes switched";
    }
    leaf status {
      type int32;
      description "Status";
    }
    leaf next-hop-interface {
      type xr:Interface-name;
      description "Next hop interface";
    }
    leaf next-hop-protocol {
      type Proto;
      description "The address family (V4/V6) ";
    }
    leaf next-hop-string {
      type string;
      description "Next hop address in string format";
    }
    leaf-list label-stack {
      type uint32;
      description "Label stack";
    }
  }

  grouping MPLS-ADJ-INFO {
    description "MPLS ADJ INFO";

    container label-information-detail {
      description "Detail label info";
      uses MPLS-FWD-INFO;
    }

    container exact-route-hash-info {
      description "Path's Hash info in case of exact-route command";
      uses MPLS-ADJ-EXACT-ROUTE-HASH-INFO;
    }
    leaf label-information-type {
      type uint32;
      description "Label-Info type";
    }
    leaf local-label {
      type uint32;
      description "Local label";
    }
    leaf outgoing-label {
      type uint32;
      description "Outgoing label";
    }
    leaf mpls-adjacency-flags {
      type uint32;
      description "MPLS Adjacency flags";
    }
    leaf tunnel-id-present {
      type boolean;
      description "Tunnel id present?";
    }
    leaf label-information-path-index {
      type uint32;
      description "LabelInformationPathIndex";
    }
    leaf label-information-next-hop-type {
      type Next-hop;
      description "NHinfo Type";
    }
    leaf label-information-next-hop-protocol {
      type Proto;
      description "The address family (v4/v6) ";
    }
    leaf tx-bytes {
      type uint64;
      units "byte";
      description "Bytes transmitted per LSP";
    }
    leaf tx-packets {
      type uint64;
      description "Packets transmitted per LSP";
    }
    leaf outgoing-interface {
      type string;
      description "Output Interface in string format";
    }
    leaf outgoing-physical-interface {
      type string;
      description "Output Physical Interface in string format";
    }
    leaf outgoing-parent-interface {
      type string;
      description "Output Parent Interface in string format";
    }
    leaf tunnel-interface {
      type string;
      description "Tunnel Interface in string format";
    }
    leaf outgoing-label-string {
      type string;
      description "Output Label in string format";
    }
    leaf prefix-or-id {
      type string;
      description "Prefix Or ID";
    }
    leaf label-information-next-hop-string {
      type string;
      description "Next hop address in string format";
    }
    leaf label-information-route-version {
      type uint64;
      description "The version of the route";
    }
    leaf label-information-time-in-milli-seconds {
      type uint64;
      description "The time of last update in msec";
    }
  }

  grouping MPLS-SH-LEAF {
    description "Information about label leaf";

    container ldi-information {
      description "LDI-info in FIB leaf";
      uses MPLS-LDI-INFO;
    }

    container multicast-information {
      description "The multicast info";
      uses MPLS-MCAST-INFO;
    }
    leaf leaf-local-label {
      type uint32;
      description "Local label";
    }
    leaf eos-bit {
      type uint32;
      description "EOS bit";
    }
    leaf hardware-information {
      type yang:hex-string;
      description "Hardware info";
    }
    leaf leaf-referance-count {
      type uint32;
      description "Number of references to the leaf";
    }
    leaf leaf-flags {
      type uint32;
      description "The leaf flags";
    }
    leaf path-list-referance-count {
      type uint32;
      description "Number of references to the pathlist";
    }
    leaf path-list-flags {
      type uint32;
      description "The pathlist flags";
    }
    leaf ldi-referance-count {
      type uint32;
      description "Number of references to the LDI";
    }
    leaf ldi-flags {
      type uint32;
      description "The LDI flags";
    }
    leaf ldi-type {
      type uint32;
      description "The LDI type";
    }
    leaf ldi-pointer {
      type uint32;
      description "The pointer to the LDI";
    }
    leaf lw-ldi-type {
      type uint32;
      description "The LW-LDI type";
    }
    leaf lw-ldi-pointer {
      type uint32;
      description "The pointer to the LW-LDI";
    }
    leaf lw-ldi-refernace-count {
      type uint32;
      description "The LW-LDI refcounter";
    }
    leaf lw-shared-ldi-pointer {
      type uint32;
      description "The pointer to the shared LDI in LW-LDI";
    }
    leaf lspa-flags {
      type uint32;
      description "The LSPA flags";
    }
    leaf afi-table-id {
      type uint32;
      description "The AFI table ID";
    }
    leaf multicast-label {
      type boolean;
      description "The unicast or multicast label";
    }
    leaf leaf-time-in-milli-seconds {
      type uint64;
      description "The time of last update in msec";
    }
    leaf total-number-of-packets-switched {
      type uint64;
      description
        "The total number of packets switched on all
        paths";
    }
    leaf total-number-of-bytes-switched {
      type uint64;
      units "byte";
      description "The total number of bytes switched on all paths";
    }

    list label-information {
      description "Label-infos in FIB leaf";
      uses MPLS-ADJ-INFO;
    }
  }

  grouping MPLS-FWDING-SUMMARY {
    description "MPLS FWDING SUMMARY";
    leaf ipv4-imposition-entries {
      type uint32;
      description "Number of IPv4 imposition entries";
    }
    leaf reserved-label-entries {
      type uint32;
      description "Number of reserved label entries";
    }
    leaf label-switched-entries {
      type uint32;
      description "Number of label swap/disposition entries";
    }
    leaf protected-label-switched-entries {
      type uint32;
      description
        "Number of FRR protected label swap/disposition
        entries";
    }
    leaf frr-ready-label-switched-entries {
      type uint32;
      description
        "Number of FRR Ready label swap/disposition
        entries";
    }
    leaf frr-active-label-switched-entries {
      type uint32;
      description
        "Number of FRR Active label swap/disposition
        entries";
    }
    leaf deleted-stale-entries {
      type uint32;
      description "Number of delete stale label entries";
    }
    leaf te-head-entries {
      type uint32;
      description "Number of TE tunnel head imposition entries";
    }
    leaf te-frr-head-entries {
      type uint32;
      description "Number of TE FRR tunnel head imposition entries";
    }
    leaf te-frr-interface-entries {
      type uint32;
      description "Number of TE FRR protected interface entries";
    }
    leaf te-frr-next-hop-entries {
      type uint32;
      description "Number of TE FRR protected next-hop entries";
    }
    leaf te-mid-points-entries {
      type uint32;
      description "Number of TE MidPoints forwarding entries";
    }
    leaf te-frr-mid-points-entries {
      type uint32;
      description "Number of TE FRR MidPoints forwarding entries";
    }
    leaf te-internal-entries {
      type uint32;
      description "Number of TE internal forwarding entries";
    }
    leaf te-frr-internal-entries {
      type uint32;
      description "Number of TE internal forwarding entries";
    }
    leaf total-forwarding-updates {
      type uint32;
      description "Total forwarding updates from LSD to LFDs";
    }
    leaf total-forwarding-update-messages {
      type uint32;
      description
        "Total forwarding update messages from LSD to
        LFDs";
    }
    leaf total-p2mp-forwarding-updates {
      type uint32;
      description "Total forwarding updates from MRIB to LFDs";
    }
    leaf total-p2mp-forwarding-added-or-modify-messages {
      type uint32;
      description
        "Total p2mp forwarding add/modify messages from
        MRIB to LFDs";
    }
    leaf total-p2mp-forwarding-delete-messages {
      type uint32;
      description
        "Total p2mp forwarding del messages from MRIB to
        LFDs";
    }
    leaf total-p2mp-forwarding-drop-messages {
      type uint32;
      description
        "Total p2mp forwarding messages dropped from MRIB
        to LFDs";
    }
    leaf total-p2mp-iir-forwarding-drop-messages {
      type uint32;
      description
        "Total IIR triggered p2mp forwarding MRIB
        messages dropped";
    }
    leaf lowest-label {
      type uint32;
      description "Lowest label in use";
    }
    leaf highest-label {
      type uint32;
      description "Highest Label in use";
    }
    leaf ignore-protect {
      type uint32;
      description "Number of TE tunnels treated as non-protected";
    }
    leaf mte-head-entries {
      type uint32;
      description "Number of MTE tunnel head entries";
    }
    leaf mte-ll-entries {
      type uint32;
      description "Number of MTE local entries";
    }
    leaf mte-midpoint-entries {
      type uint32;
      description "Number of MTE midpoint entries";
    }
    leaf global-dropped-packets {
      type uint64;
      description "Number of global FIB packets dropped";
    }
    leaf global-fragmented-packets {
      type uint64;
      description "Number of global FIB packets fragmented";
    }
    leaf global-failed-lookups {
      type uint64;
      description "Number of global failed lookups";
    }
    leaf lrpf-entries {
      type uint32;
      description "Number of labels with RPF";
    }
  }
}
