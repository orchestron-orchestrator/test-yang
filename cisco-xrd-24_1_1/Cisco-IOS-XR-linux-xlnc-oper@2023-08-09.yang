module Cisco-IOS-XR-linux-xlnc-oper {

  /*** NAMESPACE / PREFIX DEFINITION ***/

  namespace "http://cisco.com/ns/yang/Cisco-IOS-XR-linux-xlnc-oper";


  prefix "linux-xlnc-oper";

  /*** LINKAGE (IMPORTS / INCLUDES) ***/

  import Cisco-IOS-XR-types { prefix "xr"; }

  import cisco-semver { prefix "semver"; }

  include Cisco-IOS-XR-linux-xlnc-oper-sub1 {
    revision-date 2023-08-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR linux-xlnc package operational data.

     This module contains definitions
     for the following management objects:
       linux-networking: Linux Networking operational data

     Copyright (c) 2013-2023 by Cisco Systems, Inc.
     All rights reserved.";

  revision "2023-08-09" {
    description
      "Correct name of the IPv6 address list
       2023-04-05
         Add support for Linux-owned VRF
       2022-09-28
         Added new conflict reason to enumeration
       2022-09-16
         Added VRF-disable, East-West and source hint support
       2021-12-03
         Added secondary IPv4 addresses";
    semver:module-version "2.0.0";
  }

  revision "2020-06-22" {
    description
      "Added address-only interface types and corresponding inconsistencies";
    semver:module-version "1.2.0";
  }

  revision "2019-04-05" {
    description
      "Establish semantic version baseline.";
    semver:module-version "1.1.0";
  }

  revision "2015-11-09" {
    description
      "IOS XR 6.0 revision.";
  }

  container linux-networking {
    config false;
    description "Linux Networking operational data";

    container global {
      description "Global operational data";

      container vrfs {
        description
          "Linux Networking VRF and network namespace
          information";

        list vrf {
          key "vrf-name";
          description
            "XR VRF and its corresponding Linux network
            namespace";
          leaf vrf-name {
            type xr:Cisco-ios-xr-string;
            description "VRF name";
          }
          uses XLNC-BAG-VRF-STATUS;
        }
      }

      container global-config-errors {
        description
          "Errors in Linux networking global configuration";
        uses XLNC-BAG-CONF-ERRS-GLOBAL;
      }

      container interfaces {
        description "Linux Networking interface information";

        container address-only-interfaces {
          description
            "Interfaces with addresses addeded to a Linux
            Loopback";

          list address-only-interface {
            key "vrf-name interface-name";
            description
              "Interface with an IP address added to a Linux
              Loopback";
            leaf vrf-name {
              type xr:Cisco-ios-xr-string;
              description "VRF name";
            }
            leaf interface-name {
              type xr:Interface-name;
              description "Interface name";
            }
            uses XLNC-BAG-INTERFACE-ADDRESS-ONLY;
          }
        }
      }

      container status {
        description "Linux Networking operational status";

        container status-info {
          description "Operational status data";
          uses XLNC-BAG-STATUS;
        }

        container inconsistencies-per-vrfs {
          description "Global inconsistencies table";

          list inconsistencies-per-vrf {
            key "vrf-name";
            description
              "Inconsistencies observed for a particular VRF
              .";
            leaf vrf-name {
              type xr:Cisco-ios-xr-string;
              description "VRF name";
            }
            uses XLNC-BAG-VRF-INCONSISTENCIES;
          }
        }

        container inconsistencies-per-interfaces {
          description "Global inconsistencies table";

          list inconsistencies-per-interface {
            key "interface-name";
            description
              "Inconsistencies observed for a particular
              interface.";
            leaf interface-name {
              type xr:Interface-name;
              description "Interface name";
            }
            uses XLNC-BAG-INTERFACE-INCONSISTENCIES;
          }
        }
      }

      container per-vrf-config-errors {
        description
          "Table of per-VRF errors in Linux networking
          configuration";

        list per-vrf-config-error {
          key "vrf-name";
          description
            "Errors in Linux networking configuration for a
            single VRF";
          leaf vrf-name {
            type xr:Cisco-ios-xr-string;
            description "VRF name";
          }
          uses XLNC-BAG-CONF-ERRS-PER-VRF;
        }
      }
    }
  }
}
