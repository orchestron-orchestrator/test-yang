module Cisco-IOS-XR-config-cfgmgr-cfg {

  /*** NAMESPACE / PREFIX DEFINITION ***/

  namespace "http://cisco.com/ns"+
    "/yang/Cisco-IOS-XR-config-cfgmgr-cfg";


  prefix "config-cfgmgr-cfg";

  /*** LINKAGE (IMPORTS / INCLUDES) ***/

  import cisco-semver { prefix "semver"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR config-cfgmgr package configuration.

     This module contains definitions
     for the following management objects:
       cfgmgr: Cfgmgr configuration

     Copyright (c) 2013-2020 by Cisco Systems, Inc.
     All rights reserved.";

  revision "2020-06-26" {
    description
      "Updated schema to restrict user-access based on taskgroup.";
    semver:module-version "1.0.1";
  }

  revision "2019-04-05" {
    description
      "Establish semantic version baseline.";
    semver:module-version "1.0.1";
  }

  revision "2015-11-09" {
    description
      "IOS XR 6.0 revision.";
  }

  container cfgmgr {
    description "Cfgmgr configuration";
    leaf mode-exclusive {
      type boolean;
      default "true";
      description "Enabled or Disabled";
    }
  }
}
