module Cisco-IOS-XR-mpls-oam-cfg {

  /*** NAMESPACE / PREFIX DEFINITION ***/

  namespace "http://cisco.com/ns/yang/Cisco-IOS-XR-mpls-oam-cfg";


  prefix "mpls-oam-cfg";

  /*** LINKAGE (IMPORTS / INCLUDES) ***/

  import cisco-semver { prefix "semver"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR mpls-oam package configuration.

     This model is deprecated and is replaced by
     Cisco-IOS-XR-um-mpls-oam-cfg.yang which will provide the
     compatible functionalities.

     This module contains definitions
     for the following management objects:
       mpls-oam: MPLS LSP verification configuration

     Copyright (c) 2013-2022 by Cisco Systems, Inc.
     All rights reserved.";

  revision "2022-02-18" {
    description
      "Unhide revision support and downstream disable.";
    semver:module-version "1.2.0";
  }

  revision "2019-05-12" {
    description
      "Deprecated the native model, replaced by UM model.";
    semver:module-version "1.1.0";
  }

  revision "2019-04-05" {
    description
      "Establish semantic version baseline.";
    semver:module-version "1.0.0";
  }

  revision "2015-11-09" {
    description
      "IOS XR 6.0 revision.";
  }

  typedef Mpls-oam-revision {
    type enumeration {
      enum draft03-initial {
        value 1;
        description "draft-ietf-mpls-lsp-ping-03 (initial)";
      }
      enum draft03-revision1 {
        value 2;
        description "draft-ietf-mpls-lsp-ping-03 (revision 1)";
      }
      enum draft03-revision2 {
        value 3;
        description "draft-ietf-mpls-lsp-ping-03 (revision 2)";
      }
      enum draft09-initial {
        value 4;
        description "draft-ietf-mpls-lsp-ping-09 (initial)";
      }
    }
    description "Mpls oam revision";
  }

  container mpls-oam {
    status "deprecated";
    description
      "This model is deprecated and is replaced by
      Cisco-IOS-XR-um-mpls-oam-cfg.yang which will
      provide the compatible functionalities.  MPLS LSP
      verification configuration";

    container dpm {
      description "MPLS OAM DPM";
      leaf enable-dpm {
        type empty;
        description "Enable/Disable MPLS OAM DPM";
      }
      leaf interval {
        type uint32 {
          range "1..3600";
        }
        units "minute";
        description "Running interval of DPM";
      }
      leaf rate-limit {
        type uint32 {
          range "1..250";
        }
        units "packet/s";
        description "Rate limit in packets per second";
      }
      leaf downstream-ecmp-faults {
        type empty;
        description "Report downstream mismatches";
      }
    }

    container reply-mode {
      description "Echo request reply mode attributes";

      container control-channel {
        description "Configure control channel reply mode";
        leaf allow-reverse-lsp {
          type empty;
          description "Use Reverse LSP as the control channel";
        }
      }
    }
    leaf default-revision {
      type Mpls-oam-revision;
      default "draft09-initial";
      description "Echo request default revision";
    }
    leaf enable-oam {
      type empty;
      description
        "Enable/Disable MPLS OAM globally.Without
        creating this object the MPLS OAM feature will
        not be enabled. Deleting this object will stop
        the MPLS OAM feature.";
    }
    leaf disable-vendor-extension {
      type empty;
      description "Disable vendor extension";
    }
  }
}
