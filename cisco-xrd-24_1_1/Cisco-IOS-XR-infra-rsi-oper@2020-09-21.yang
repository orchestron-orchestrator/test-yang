module Cisco-IOS-XR-infra-rsi-oper {

  /*** NAMESPACE / PREFIX DEFINITION ***/

  namespace "http://cisco.com/ns/yang/Cisco-IOS-XR-infra-rsi-oper";


  prefix "infra-rsi-oper";

  /*** LINKAGE (IMPORTS / INCLUDES) ***/

  import Cisco-IOS-XR-types { prefix "xr"; }

  import cisco-semver { prefix "semver"; }

  include Cisco-IOS-XR-infra-rsi-oper-sub2 {
    revision-date 2020-09-21;
  }

  include Cisco-IOS-XR-infra-rsi-oper-sub1 {
    revision-date 2020-09-21;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR infra-rsi package operational data.

     This module contains definitions
     for the following management objects:
       vrf-group: VRF group operational data
       srlg: RSI SRLG operational data
       selective-vrf-download: Selective VRF Download operational
         data

     Copyright (c) 2013-2020 by Cisco Systems, Inc.
     All rights reserved.";

  revision "2020-09-21" {
    description
      "Operational support for new safi bier.";
    semver:module-version "1.1.0";
  }

  revision "2019-04-05" {
    description
      "Establish semantic version baseline.";
    semver:module-version "1.0.1";
  }

  revision "2019-02-13" {
    description
      "Fixing yang oper coverage.";
  }

  revision "2018-11-26" {
    description
      "Fixing yang usability issues.";
  }

  revision "2017-09-07" {
    description
      "Fixed type translation error.";
  }

  revision "2017-05-01" {
    description
      "Fixing backward compatibility error in module.";
  }

  revision "2015-01-07" {
    description
      "IOS XR 5.3.1 revision.";
  }

  container vrf-group {
    config false;
    description "VRF group operational data";

    container nodes {
      description "Node operational data";

      list node {
        key "node-name";
        description "Node details";

        container groups {
          description "Group operational data";

          list group {
            key "group-name";
            description "Group details";
            leaf group-name {
              type xr:Cisco-ios-xr-string {
                length "1..32";
              }
              description "Group name";
            }
            uses RSI-VRFGROUP-GROUP-SHOW;
          }
        }
        leaf node-name {
          type xr:Node-id;
          description "Node";
        }
      }
    }
  }

  container srlg {
    config false;
    description "RSI SRLG operational data";

    container groups {
      description "Set of Groups configured for SRLG";

      list group {
        key "group-name";
        description "SRLG group details";
        leaf group-name {
          type xr:Cisco-ios-xr-string;
          description "Group name";
        }
        uses RSI-SRLG-GROUP-SHOW;
      }
    }

    container interfaces {
      description "Set of interfaces configured for SRLG";

      list interface {
        key "interface-name";
        description "SRLG interface summary";
        leaf interface-name {
          type xr:Interface-name;
          description "Interface name";
        }
        uses RSI-SRLG-INTF-BRIEF-SHOW;
      }
    }

    container rsips {
      description "Set of rsip configured for SRLG";

      list rsip {
        key "rsip-name";
        description "SRLG rsip details";
        leaf rsip-name {
          type xr:Interface-name;
          description "Interface name";
        }
        uses RSI-SRLG-RSIP-SHOW;
      }
    }

    container srlg-maps {
      description "Set of SRLG name, value maps configured";

      list srlg-map {
        key "srlg-name";
        description "Configured SRLG name details ";
        leaf srlg-name {
          type xr:Cisco-ios-xr-string {
            length "1..64";
          }
          description "SRLG name";
        }
        uses RSI-SRLG-NAME-VALUE-SHOW;
      }
    }

    container nodes {
      description "RSI SRLG operational data";

      list node {
        key "node-name";
        description "RSI SRLG operational data";

        container srlg-maps {
          description "Set of SRLG name, value maps configured";

          list srlg-map {
            key "srlg-name";
            description "Configured SRLG name details ";
            leaf srlg-name {
              type xr:Cisco-ios-xr-string {
                length "1..64";
              }
              description "SRLG name";
            }
            uses RSI-SRLG-NAME-VALUE-SHOW;
          }
        }

        container groups {
          description "Set of Groups configured for SRLG";

          list group {
            key "group-name";
            description "SRLG group details";
            leaf group-name {
              type xr:Cisco-ios-xr-string;
              description "Group name";
            }
            uses RSI-SRLG-GROUP-SHOW;
          }
        }

        container inherit-nodes {
          description
            "Set of inherit locations configured for SRLG";

          list inherit-node {
            key "inherit-node-name";
            description "SRLG inherit location details";
            leaf inherit-node-name {
              type xr:Node-id;
              description "Inherit node";
            }
            uses RSI-SRLG-INHLOC-SHOW;
          }
        }

        container interfaces {
          description "Set of interfaces configured for SRLG";

          list interface {
            key "interface-name";
            description "SRLG interface summary";
            leaf interface-name {
              type xr:Interface-name;
              description "Interface name";
            }
            uses RSI-SRLG-INTF-BRIEF-SHOW;
          }
        }

        container srlg-descriptions {
          description "Set of SRLG name, description configured";

          list srlg-description {
            key "srlg-name";
            description "Configured SRLG Description details ";
            leaf srlg-name {
              type xr:Cisco-ios-xr-string {
                length "1..64";
              }
              description "SRLG name";
            }
            uses RSI-SRLG-DESC-SHOW;
          }
        }

        container interface-details {
          description "Set of interfaces configured for SRLG";

          list interface-detail {
            key "interface-name";
            description "SRLG interface info";
            leaf interface-name {
              type xr:Interface-name;
              description "Interface name";
            }
            uses RSI-SRLG-INTF-DETAIL-SHOW;
          }
        }

        container srlg-values {
          description "Set of SRLG values configured";

          list srlg-value {
            key "value";
            description "Configured SRLG value details ";
            leaf value {
              type uint32 {
                range "0..4294967295";
              }
              description "SRLG value";
            }
            uses RSI-SRLG-INTF-SHOW;
          }
        }

        container interface-srlg-names {
          description "Set of SRLG names configured";

          list interface-srlg-name {
            key "srlg-name";
            description "Configured SRLG name details ";
            leaf srlg-name {
              type xr:Cisco-ios-xr-string {
                length "1..64";
              }
              description "SRLG name";
            }
            uses RSI-SRLG-NAME-INTF-SHOW;
          }
        }
        leaf node-name {
          type xr:Node-id;
          description "Node";
        }
      }
    }

    container interface-srlg-names {
      description "Set of SRLG names configured";

      list interface-srlg-name {
        key "srlg-name";
        description "Configured SRLG name details ";
        leaf srlg-name {
          type xr:Cisco-ios-xr-string {
            length "1..64";
          }
          description "SRLG name";
        }
        uses RSI-SRLG-NAME-INTF-SHOW;
      }
    }

    container inherit-nodes {
      description "Set of inherit locations configured for SRLG";

      list inherit-node {
        key "inherit-node-name";
        description "SRLG inherit location details";
        leaf inherit-node-name {
          type xr:Node-id;
          description "Inherit Locatio";
        }
        uses RSI-SRLG-INHLOC-SHOW;
      }
    }

    container srlg-values {
      description "Set of SRLG values configured";

      list srlg-value {
        key "value";
        description "Configured SRLG value details ";
        leaf value {
          type uint32 {
            range "0..4294967295";
          }
          description "SRLG value";
        }
        uses RSI-SRLG-INTF-SHOW;
      }
    }

    container interface-details {
      description "Set of interfaces configured for SRLG";

      list interface-detail {
        key "interface-name";
        description "SRLG interface info";
        leaf interface-name {
          type xr:Interface-name;
          description "Interface name";
        }
        uses RSI-SRLG-INTF-DETAIL-SHOW;
      }
    }
  }

  container selective-vrf-download {
    config false;
    description "Selective VRF Download operational data";

    container state {
      description "Selective VRF Download feature state details";
      uses RSI-MASTER-STATE;
    }
  }
}
