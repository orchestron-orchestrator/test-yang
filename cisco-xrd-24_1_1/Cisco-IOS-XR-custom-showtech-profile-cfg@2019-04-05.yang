module Cisco-IOS-XR-custom-showtech-profile-cfg {

  /*** NAMESPACE / PREFIX DEFINITION ***/

  namespace "http://cisco.com/ns/yang"+
    "/Cisco-IOS-XR-custom-showtech-profile-cfg";


  prefix "custom-showtech-profile-cfg";

  /*** LINKAGE (IMPORTS / INCLUDES) ***/

  import Cisco-IOS-XR-types { prefix "xr"; }

  import cisco-semver { prefix "semver"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR custom-showtech-profile package configuration.

     This module contains definitions
     for the following management objects:
       custom-show-tech: Custom ShowTech Configuration

     Copyright (c) 2013-2019 by Cisco Systems, Inc.
     All rights reserved.";

  revision "2019-04-05" {
    description
      "Establish semantic version baseline.";
    semver:module-version "1.0.0";
  }

  revision "2015-11-09" {
    description
      "IOS XR 6.0 revision.";
  }

  container custom-show-tech {
    description "Custom ShowTech Configuration";

    list profile-name {
      key "profile-name";
      description "Profile name";

      container command-strs {
        description "Custom commands";

        list command-str {
          key "command-str";
          description "Custom command string";
          leaf command-str {
            type string;
            description "Command String";
          }
        }
      }

      container admin-command-strs {
        description "Custom Admin commands";

        list admin-command-str {
          key "admin-command-str";
          description "Custom Admin command string";
          leaf admin-command-str {
            type string;
            description "Admin Command String";
          }
        }
      }
      leaf profile-name {
        type xr:Cisco-ios-xr-string {
          length "1..257";
        }
        description "Profile name";
      }
    }
  }
}
