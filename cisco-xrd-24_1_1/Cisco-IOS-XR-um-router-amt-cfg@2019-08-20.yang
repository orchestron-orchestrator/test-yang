module Cisco-IOS-XR-um-router-amt-cfg {

  /*** NAMESPACE / PREFIX DEFINITION ***/

  namespace "http://cisco.com/ns/yang/Cisco-IOS-XR-um-router-amt-cfg";

  prefix "um-router-amt-cfg";

  /*** LINKAGE (IMPORTS / INCLUDES) ***/

  import cisco-semver { prefix "semver"; }
  import Cisco-IOS-XR-types { prefix "xr"; }
  import ietf-inet-types { prefix "inet"; }


  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR router amt configuration.

     Copyright (c) 2019 by Cisco Systems, Inc.
     All rights reserved.";

  revision "2019-08-20" {
    description
      "Initial release";
    semver:module-version "1.0.0";
  }


  container router {
    description "Enable a routing process";
    container amt {
      presence "Indicates a amt node is configured.";
      description "Automatic Multicast Tunneling (AMT)";
      container relay {
        presence "Indicates a relay node is configured.";
        description "AMT Relay Submode";
        container ipv4 {
          presence "Indicates a ipv4 node is configured.";
          description "AMT Relay IPv4 Tunnel Submode";
          container anycast-prefix {
            description "AMT Relay IPv4 Anycast-Prefix";
            leaf prefix-address {
              type inet:ipv4-address-no-zone;
              description "anycast prefix address";
            }
            leaf prefix-length {
              type uint32 {
                    range "0..32";
              }
              description "Prefix mask for anycast prefix";
            }
          }
          container advertisement-address {
            presence "Indicates a advertisement-address node is configured.";
            description "AMT Relay IPv4 Advertisement Address";
            leaf relay-address {
              mandatory true;
              type inet:ipv4-address-no-zone;
              description "AMT Relay IPv4 Advertisement Address";
            }
            leaf interface {
              mandatory true;
              type xr:Interface-name;
              description "Source Interface";
            }
          }
          leaf gateway-filter {
            type xr:Cisco-ios-xr-string {
              length "1..1024" {
                description "Filter ACL name";
              }
            }
            description "AMT Gateway Filter ACL";
          }
          leaf mtu {
            type uint32 {
              range "100..65535" {
                description "MTU value";
              }
            }
            description "AMT Relay MTU configuration";
          }
          leaf tos {
            type uint32 {
              range "1..255" {
                description "TOS value";
              }
            }
            description "AMT Relay TOS configuration";
          }
          leaf ttl {
            type uint32 {
              range "1..255" {
                description "TTL value";
              }
            }
            description "AMT Relay TTL configuration";
          }
          leaf qqic {
            type uint32 {
              range "0..4294967295" {
                description "QQIC value in seconds";
              }
            }
            description "AMT Relay QQIC configuration";
          }
          container maximum {
            description "Maximum limits";
            leaf gateway {
              type uint32 {
                range "0..4294967295" {
                  description "Maximum number of Gateways";
                }
              }
              description "Maximum number of Gateways";
            }
            container route-gateway {
              description "Maximum number of route-gateways (Tunnels)";
              leaf ipv4 {
                type uint32 {
                  range "0..4294967295" {
                    description "Maximum number of IPv4 route-gateways (Tunnels)";
                  }
                }
                description "Maximum number of IPv4 route-gateways (Tunnels)";
              }
              leaf ipv6 {
                type uint32 {
                  range "0..4294967295" {
                    description "Maximum number of IPv6 route-gateways (Tunnels)";
                  }
                }
                description "Maximum number of IPv6 route-gateways (Tunnels)";
              }
            }
          }
        }
      }
    }
  }
}
