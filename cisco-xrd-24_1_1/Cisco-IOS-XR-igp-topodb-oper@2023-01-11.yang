module Cisco-IOS-XR-igp-topodb-oper {

  /*** NAMESPACE / PREFIX DEFINITION ***/

  namespace "http://cisco.com/ns/yang/Cisco-IOS-XR-igp-topodb-oper";


  prefix "igp-topodb-oper";

  /*** LINKAGE (IMPORTS / INCLUDES) ***/

  import Cisco-IOS-XR-types { prefix "xr"; }

  import cisco-semver { prefix "semver"; }

  include Cisco-IOS-XR-igp-topodb-oper-sub1 {
    revision-date 2023-01-11;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR igp-topodb package operational data.

     This module contains definitions
     for the following management objects:
       topo-db: Open Topology Database library operational data

     Copyright (c) 2013-2023 by Cisco Systems, Inc.
     All rights reserved.";

  revision "2023-01-11" {
    description
      "Added support for Memory Chunk information
       2022-04-06
         Renamed Node Flex Algo Topology Entry i.e. NFTE to Node Algo Topology Entryi.e. NATE.
       2022-02-02
         Modified for Flex algo firsthop gateway.
       2021-10-22
         Modified for Flex algo srlg exclude-any and Flex algo External features.";
    semver:module-version "4.0.0";
  }

  revision "2021-05-12" {
    description
      "Modified for Flex algo Inter-area support.";
    semver:module-version "3.0.0";
  }

  revision "2020-01-02" {
    description
      "Added topodb operational data support.";
    semver:module-version "1.1.0";
  }

  revision "2019-04-05" {
    description
      "Establish semantic version baseline.";
    semver:module-version "1.0.1";
  }

  revision "2015-11-09" {
    description
      "IOS XR 6.0 revision.";
  }

  container topo-db {
    config false;
    description "Open Topology Database library operational data";

    container topo-db-processes {
      description "Table for each process using topology library";

      list topo-db-process {
        key "process-name";
        description "Operational data for a particular process";

        container topology-prefixes {
          description "Container for Topology prefix information";

          list topology-prefix {
            key "topo-vrf-name";
            description "Topology prefix information";
            leaf topo-vrf-name {
              type xr:Cisco-ios-xr-string;
              description "VRF Name";
            }
            uses OTLIB-SHOW-INSTANCE;
          }
        }

        container topology-paths {
          description "Container for Topology path information";

          list topology-path {
            key "topo-vrf-name";
            description "Topology path information";
            leaf topo-vrf-name {
              type xr:Cisco-ios-xr-string;
              description "VRF Name";
            }
            uses OTLIB-SHOW-PATH-INSTANCE;
          }
        }

        container topology-microloop-avoidances {
          description
            "Container for Topology Microloop Avoidance
            information";

          list topology-microloop-avoidance {
            key "topo-vrf-name";
            description "Topology Microloop Avoidance information";
            leaf topo-vrf-name {
              type xr:Cisco-ios-xr-string;
              description "VRF Name";
            }
            uses OTLIB-SHOW-ULOOP-INSTANCE;
          }
        }

        container topology-forwarding-addresses {
          description
            "Container for Topology Forwarding Address
            information";

          list topology-forwarding-address {
            key "topo-vrf-name";
            description "Topology Forwarding Address information";
            leaf topo-vrf-name {
              type xr:Cisco-ios-xr-string;
              description "VRF Name";
            }
            uses OTLIB-SHOW-FORW-ADDR-INSTANCE;
          }
        }

        container topology-firsthop-gateways {
          description
            "Container for Topology Firsthop Gateway
            information";

          list topology-firsthop-gateway {
            key "topo-vrf-name";
            description "Topology Firsthop Gateway information";
            leaf topo-vrf-name {
              type xr:Cisco-ios-xr-string;
              description "VRF Name";
            }
            uses OTLIB-SHOW-FHGW-INSTANCE;
          }
        }

        container topology-fast-reroutes {
          description
            "Container for Topology Fast Reroute
            information";

          list topology-fast-reroute {
            key "topo-vrf-name";
            description "Topology Fast Reroute information";
            leaf topo-vrf-name {
              type xr:Cisco-ios-xr-string;
              description "VRF Name";
            }
            uses OTLIB-SHOW-IPFRR-INSTANCE;
          }
        }

        container topology-asbr-reachabilities {
          description
            "Container for Topology ASBR Reachability
            information";

          list topology-asbr-reachability {
            key "topo-vrf-name";
            description "Topology ASBR Reachability information";
            leaf topo-vrf-name {
              type xr:Cisco-ios-xr-string;
              description "VRF Name";
            }
            uses OTLIB-SHOW-ASBR-REACHABILITY-INSTANCE;
          }
        }

        container topology-routes {
          description "Container for Topology route information";

          list topology-route {
            key "topo-vrf-name";
            description "Topology Route Information";
            leaf topo-vrf-name {
              type xr:Cisco-ios-xr-string;
              description "VRF Name";
            }
            uses OTLIB-SHOW-ROUTE-INSTANCE;
          }
        }

        container topology-asbr-paths {
          description
            "Container for Topology ASBR path information";

          list topology-asbr-path {
            key "topo-vrf-name";
            description "Topology ASBR path information";
            leaf topo-vrf-name {
              type xr:Cisco-ios-xr-string;
              description "VRF Name";
            }
            uses OTLIB-SHOW-PATH-INSTANCE;
          }
        }

        container topology-summaries {
          description "Container for Topology summary information";

          list topology-summary {
            key "topo-vrf-name";
            description "Topology summary information";
            leaf topo-vrf-name {
              type xr:Cisco-ios-xr-string;
              description "VRF Name";
            }
            uses OTLIB-SH-INST-SUMMARY;
          }
        }

        container topologies {
          description "Container for Topology information";

          list topology {
            key "topo-vrf-name";
            description "Topology information";
            leaf topo-vrf-name {
              type xr:Cisco-ios-xr-string;
              description "VRF Name";
            }
            uses OTLIB-SHOW-INSTANCE;
          }
        }

        container topology-memory-chunks {
          description
            "Container for Topology Memory Chunk
            information";

          list topology-memory-chunk {
            key "topo-vrf-name";
            description "Topology Memory Chunk information";
            leaf topo-vrf-name {
              type xr:Cisco-ios-xr-string {
                length "1..32";
              }
              description "VRF name";
            }
            uses OTLIB-SHOW-MEM-CHUNK;
          }
        }
        leaf process-name {
          type xr:Cisco-ios-xr-string;
          description "Process name";
        }
      }
    }
  }
}
