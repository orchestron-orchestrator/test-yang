module Cisco-IOS-XR-um-if-vrf-cfg {

  /*** NAMESPACE / PREFIX DEFINITION ***/

  namespace "http://cisco.com/ns/yang/Cisco-IOS-XR-um-if-vrf-cfg";
  prefix um-if-vrf-cfg;

  /*** LINKAGE (IMPORTS / INCLUDES) ***/

  import cisco-semver {
    prefix semver;
  }
  import Cisco-IOS-XR-types {
    prefix xr;
  }
  import Cisco-IOS-XR-um-interface-cfg {
    prefix a1;
  }
  import tailf-common {
    prefix tailf;
  }

  /*** META INFORMATION ***/

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR if vrf package configuration.

     This YANG module augments the
     modules with configuration data.

     Copyright (c) 2019-2022 by Cisco Systems, Inc.
     All rights reserved.";

  revision 2022-07-11 {
    description
      "Added missing description statement to nodes";
    semver:module-version "1.1.0";
  }

  revision "2019-10-10" {
    description
      "Initial version";
    semver:module-version "1.0.0";
  }

  grouping GROUP-IFSUB {
    description
      "Grouping for interface";
    leaf vrf {
      when "../a1:interface-name[not(starts-with(text(),'tunnel-'))] and "
         + "../a1:interface-name[not(starts-with(text(),'cem'))] and "
         + "../a1:interface-name[not(starts-with(text(),'nve'))]" {
        tailf:dependency "../a1:interface-name";
      }
      type xr:Cisco-ios-xr-string {
        length "1..32" {
          description
            "VRF name";
        }
      }
      description
        "Set VRF in which the interface operates";
    }
    container address-family {
      when "../a1:interface-name[not(starts-with(text(),'pw-ether'))] "
         + "and ../a1:interface-name[not(starts-with(text(),'pw-iw'))] "
         + "and ../a1:interface-name[not(starts-with(text(),'cem'))]" {
        tailf:dependency "../a1:interface-name";
      }
      description
        "AFI/SAFI configuration";
      container ipv4 {
        description
          "IPv4 address family";
        container multicast {
          presence "Indicates a multicast node is configured.";
          description
            "Multicast topology";
          container default-topology {
            presence "Indicates a default-topology node is configured.";
            description
              "Multicast default topology";
          }
          container topologies {
            description
              "Specify a non-default topology";
            list topology {
              key "topology-name";
              description
                "Specify a non-default topology";
              leaf topology-name {
                type xr:Cisco-ios-xr-string {
                  length "1..32" {
                    description
                      "Topology name";
                  }
                }
                description
                  "Specify a non-default topology";
              }
            }
          }
        }
      }
      container ipv6 {
        description
          "IPv6 address family";
        container multicast {
          presence "Indicates a multicast node is configured.";
          description
            "Multicast topology";
          container default-topology {
            presence "Indicates a default-topology node is configured.";
            description
              "Multicast default topology";
          }
          container topologies {
            description
              "Specify a non-default topology";
            list topology {
              key "topology-name";
              description
                "Specify a non-default topology";
              leaf topology-name {
                type string {
                  length "1..32" {
                    description
                      "Topology name";
                  }
                }
                description
                  "Specify a non-default topology";
              }
            }
          }
        }
      }
    }
  }

  augment "/a1:interfaces/a1:interface" {
    description
      "This augment extends active nodes configuration";
    uses GROUP-IFSUB;
  }

  augment "/a1:interfaces/a1:interface-preconfigure" {
    description
      "This augment extends preconfigured nodes
       configuration";
    uses GROUP-IFSUB;
  }
}
