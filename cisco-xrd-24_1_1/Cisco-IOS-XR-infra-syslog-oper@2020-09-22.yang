module Cisco-IOS-XR-infra-syslog-oper {

  /*** NAMESPACE / PREFIX DEFINITION ***/

  namespace "http://cisco.com/ns"+
    "/yang/Cisco-IOS-XR-infra-syslog-oper";


  prefix "infra-syslog-oper";

  /*** LINKAGE (IMPORTS / INCLUDES) ***/

  import cisco-semver { prefix "semver"; }

  import ietf-yang-types { prefix yang; }

  include Cisco-IOS-XR-infra-syslog-oper-sub1 {
    revision-date 2020-09-22;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR infra-syslog package operational data.

     This module contains definitions
     for the following management objects:
       logging: Logging History data
       syslog: System message operational data

     Copyright (c) 2013-2020 by Cisco Systems, Inc.
     All rights reserved.";

  revision "2020-09-22" {
    description
      "Marking Sensor Paths for Event Driven Telemetry";
    semver:module-version "1.1.0";
  }

  revision "2019-04-05" {
    description
      "Establish semantic version baseline.";
    semver:module-version "1.0.1";
  }

  revision "2018-02-23" {
    description
      "Added a new rpc statement.";
  }

  revision "2018-02-22" {
    description
      "Fixed syslog message filter.";
  }

  revision "2017-09-07" {
    description
      "Fixed type translation error.";
  }

  revision "2016-06-24" {
    description
      "Schema added for Show logging files CLI";
  }

  revision "2015-01-07" {
    description
      "IOS XR 5.3.1 revision.";
  }

  container logging {
    config false;
    description "Logging History data";

    container history {
      description "Syslog Info ";
      leaf properties {
        type string;
        description "Syslog Properties";
      }
      leaf message {
        type string;
        description "Syslog Message";
      }
    }
  }

  container syslog {
    config false;
    description "System message operational data";

    container logging-files {
      description "Logging Files information";
      uses FILE-LOG-LIST-PATH;
    }

    container an-remote-servers {
      description "Logging AN remote servers information";
      uses AN-REMOTE-LOG-SERVERS;
    }

    container messages {
      description "Message table information";

      list message {
        key "message-id";
        description "A system message";
        leaf message-id {
          type uint32;
          description "Message ID of the system message";
        }
        uses SYSTEM-MESSAGE;
      }
    }

    container logging-statistics {
      description "Logging statistics information";
      uses SYSTEM-MESSAGE-STATISTICS;
    }
  }

  rpc get-syslog {
    input {
      container filters {
        description "A set of filters of syslog messages to be returned";
        must "start-time or end-time" {
          description "At least one of the filters must be specified.";
        }
        leaf start-time {
          type yang:date-and-time;
          description "Start timestamp of syslog messages to be returned";
        }
        leaf end-time {
          type yang:date-and-time;
          description "End timestamp of syslog messages to be returned";
        }
      }
    }
    output {
      container data {
        description "Output for RPC operation";

        container syslog {
          description "syslog";

          container messages {
            description "Message table information";

            list message {
              key "message-id";
              description "A system message";
              leaf message-id {
                type uint32;
                description "Message ID of the system message";
              }
              uses SYSTEM-MESSAGE;
            }
          }
        }
      }
    }
  }
}
