module Cisco-IOS-XR-um-subscriber-accounting-cfg {

  /*** NAMESPACE / PREFIX DEFINITION ***/

  namespace "http://cisco.com/ns/yang/Cisco-IOS-XR-um-subscriber-accounting-cfg";
  prefix um-subscriber-accounting-cfg;

  /*** LINKAGE (IMPORTS / INCLUDES) ***/

  import Cisco-IOS-XR-types {
    prefix xr;
  }
  import Cisco-IOS-XR-um-subscriber-cfg {
    prefix a1;
  }
  import Cisco-IOS-XR-um-dynamic-template-cfg {
    prefix a2;
  }

  import cisco-semver { prefix "semver"; }

  /*** META INFORMATION ***/

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR subscriber-accounting package configuration.

     This YANG module augments the
     modules with configuration data.

     Copyright (c) 2021-2022 by Cisco Systems, Inc.
     All rights reserved.";

  revision 2022-07-11 {
    description
      "Added missing description statement to nodes";
    semver:module-version "1.1.0";
  }

  revision "2021-02-10" {
    description
      "Initial release";
    semver:module-version "1.0.0";
  }

  grouping TEMPLATE-BODY {
    description
      "Grouping for template";
    container accounting {
      description
        "Accounting Feature Config";
      container aaa {
        description
          "Accounting Feature AAA Config";
        container list {
          description
            "Accounting Method-list";
          container type {
            description
              "Type of accounting performed";
            container session {
              presence "Indicates a session node is configured.";
              description
                "Apply accounting to a session";
              leaf method-list-name {
                type union {
                  type xr:Cisco-ios-xr-string {
                    length "1..256" {
                      description
                        "Preconfigured method-list name";
                    }
                  }
                  type xr:Cisco-ios-xr-string {
                    pattern 'default' {
                      description
                        "default method-list";
                    }
                  }
                }
                description
                  "Preconfigured method-list name";
              }
              leaf periodic-interval {
                type uint32 {
                  range "1..65535" {
                    description
                      "Enter value in minutes";
                  }
                }
                description
                  "Periodic accounting interval in minutes";
              }
              leaf dual-stack-delay {
                type uint32 {
                  range "1..30" {
                    description
                      "Enter value in seconds";
                  }
                }
                description
                  "Dual stack set delay wait";
              }
              leaf hold {
                type enumeration {
                  enum ipv6-prefix-delegation {
                    value 3;
                    description
                      "Based on IA_PD";
                  }
                }
                must '../dual-stack-delay';
                description
                  "Hold Accounting Start ";
              }
            }
            container service {
              when 'boolean(../../../../../../../a2:service/a2:template)';
              presence "Indicates a service node is configured.";
              description
                "Apply accounting to a service";
              leaf method-list-name {
                type union {
                  type xr:Cisco-ios-xr-string {
                    length "1..256" {
                      description
                        "Preconfigured method-list name";
                    }
                  }
                  type xr:Cisco-ios-xr-string {
                    pattern 'default' {
                      description
                        "default method-list";
                    }
                  }
                  type xr:Cisco-ios-xr-string {
                    pattern 'use-session-mlist' {
                      description
                        "picks up the session accounting method list for service accounting";
                    }
                  }
                }
                mandatory true;
                description
                  "Preconfigured method-list name";
              }
              leaf periodic-interval {
                type uint32 {
                  range "1..65535" {
                    description
                      "Enter value in minutes";
                  }
                }
                description
                  "Periodic accounting interval in minutes";
              }
            }
          }
        }
      }
    }
    leaf prepaid-config {
      when 'boolean(../../../a2:service/a2:template)';
      type xr:Cisco-ios-xr-string {
        length "1..64" {
          description
            "Preconfigured prepaid feature name";
        }
      }
      description
        "Accounting Feature Config";
    }
    container timeout {
      description
        "Subscriber Accounting Idle Timer Config";
      leaf idle {
        type uint32 {
          range "60..4320000" {
            description
              "Idle timeout duration in seconds";
          }
        }
        description
          "Subscriber Accounting Idle Timer Config";
      }
      leaf threshold {
        type uint32 {
          range "1..10000" {
            description
              "Duration of threshold in minute(s) per packet - should be less than idle duration";
          }
        }
        description
          "Configure threshold duration for idleness tracking";
      }
      container traffic {
        description
          "Traffic direction to consider while deriving idleness";
        container inbound {
          must 'not(../outbound or ../both)';
          presence "Indicates a inbound node is configured.";
          description
            "Consider Inbound traffic while deriving idleness(Default)";
        }
        container outbound {
          must 'not(../inbound or ../both)';
          presence "Indicates a outbound node is configured.";
          description
            "Consider outbound traffic while deriving idleness";
        }
        container both {
          must 'not(../inbound or ../outbound)';
          presence "Indicates a both node is configured.";
          description
            "Consider both inbound and outbound traffic while deriving idleness";
        }
      }
    }
  }

  augment "/a1:subscriber" {
    description
      "This augment extends subscriber nodes configuration";
    container accounting {
      description
        "Subscriber Accounting Feature Configuration";
      container prepaids {
        description
          "Subscriber Prepaid Feature Configuration";
        list prepaid {
          key "prepaid-name";
          description
            "Subscriber Prepaid Feature Configuration";
          leaf prepaid-name {
            type xr:Cisco-ios-xr-string {
              length "1..64" {
                description
                  "Prepaid configuration name or default";
              }
            }
            description
              "Subscriber Prepaid Feature Configuration";
          }
          container method-list {
            description
              "Method list config";
            leaf authorization {
              type xr:Cisco-ios-xr-string {
                length "1..64" {
                  description
                    "Method list name";
                }
              }
              description
                "Author method list; 'aaa accounting network <name>' must also be created";
            }
          }
          container quota-validity {
            description
              "Quota-validity";
            leaf time {
              type uint32 {
                range "0..99000" {
                  description
                    "duration in seconds";
                }
              }
              description
                "time";
            }
          }
          container quota-holding {
            description
              "Quota-Holding";
            leaf time {
              type uint32 {
                range "0..99000" {
                  description
                    "duration in seconds";
                }
              }
              description
                "time";
            }
          }
          container traffic {
            description
              "Traffic direction to consider while deriving volume";
            container inbound {
              must 'not(../outbound or ../both)';
              presence "Indicates a inbound node is configured.";
              description
                "Consider Inbound traffic while deriving volume(Default)";
            }
            container outbound {
              must 'not(../inbound or ../both)';
              presence "Indicates a outbound node is configured.";
              description
                "Consider outbound traffic while deriving volume";
            }
            container both {
              must 'not(../inbound or ../outbound)';
              presence "Indicates a both node is configured.";
              description
                "Consider both inbound and outbound traffic while deriving volume";
            }
          }
          leaf password {
            type xr:Cisco-ios-xr-string {
              length "1..64" {
                description
                  "Password to be used when placing prepaid (re)author requests";
              }
            }
            description
              "Password config";
          }
          container threshold {
            description
              "Threshold config";
            leaf time {
              type uint32 {
                range "0..4294967295" {
                  description
                    "Time threshold in seconds";
                }
              }
              description
                "Time threshold";
            }
            leaf volume {
              type uint32 {
                range "1..100" {
                  description
                    "Volume threshold in %(percentage)";
                }
              }
              description
                "Volume threshold";
            }
          }
        }
      }
    }
  }

  augment "/a2:dynamic-template/a2:type/a2:ppp/a2:template" {
    description
      "This augment extends dynamic-template ppp nodes
       configuration";
    uses TEMPLATE-BODY;
  }

  augment "/a2:dynamic-template/a2:type/a2:ipsubscriber/a2:template" {
    description
      "This augment extends dynamic-template ipsubscriber nodes
       configuration";
    uses TEMPLATE-BODY;
  }

  augment "/a2:dynamic-template/a2:type/a2:service/a2:template" {
    description
      "This augment extends dynamic-template service nodes
       configuration";
    uses TEMPLATE-BODY;
  }
}
