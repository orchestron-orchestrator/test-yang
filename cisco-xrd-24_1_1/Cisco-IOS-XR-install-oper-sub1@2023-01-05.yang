submodule Cisco-IOS-XR-install-oper-sub1 {

  belongs-to Cisco-IOS-XR-install-oper {
    prefix Cisco-IOS-XR-install-oper;
  }

  /*** LINKAGE (IMPORTS / INCLUDES) ***/

  import Cisco-IOS-XR-types { prefix "xr"; }

  import cisco-semver { prefix "semver"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR install package operational data.

     Copyright (c) 2013-2023 by Cisco Systems, Inc.
     All rights reserved.";

  revision "2023-01-05" {
    description
      "Add optional reimage_info field to install_upgrade_matrix_details.
       2022-11-29
         Add target fix checks to the compatibility matrix feature.
       2022-11-09
         Add reimage errors bag.
       2022-10-19
         Add more detail to BEGIN_REIMAGE activity.
       2022-09-12
         Added reimage history bag as part of the reimage from disk feature.
       2022-08-26
         Added matrix version to upgrade matrix bag
       2022-05-05
         Add warning to inst_request_bag.
       2022-03-09
         Added support for show install profile
       2022-01-12
         Added feature information for transaction locking.
       2021-09-21
         Add new states for ISO download and extracting main ISO contents.
       2021-08-10
         Add force option to package abort.";
    semver:module-version "1.5.0";
  }

  revision "2021-07-15" {
    description
      "Add pre-commit check support.
      2021-05-18
          Modified oper path for upgrade compatibility matrix with iso input
      2021-05-13
          Added optional hash into all package queries.
      2021-04-14
          Add system reload reason and config replace info
      2021-03-22
          Added support for upgrade compatibility matrix feature";
    semver:module-version "1.4.0";
  }

  revision "2021-01-14" {
    description
      "Add DDTS info to rollback queries.
      2020-07-23
           Added optional label into inst_packages_bag.
      2020-07-22
           Update Inst-provides-match-type with additional provide value
      2020-05-27
           Add install and runtime fingerprint
      2020-05-27
           Add install and runtime fingerprint
      2020-05-27
           Add install and runtime fingerprint
      2020-05-13
           Updated version information to add hostname and disk space
      2020-05-13
           Updated version information to add hostname and disk space
      2020-05-13
           Updated version information to add hostname and disk space";
    semver:module-version "1.3.0";
  }

  revision "2020-04-23" {
    description
      "Add categorization of installed software packages into Cisco and Non-Cisco
      2020-04-23
         Add categorization of installed software packages into Cisco and Non-Cisco
      2020-04-23
         Add categorization of installed software packages into Cisco and Non-Cisco
      2020-02-05
         Updated version information to add a GISO label
      2020-02-05
         Updated version information to add a GISO label
      2020-02-05
         Updated version information to add a GISO label
      2020-01-09
         Added optional label into inst_summary_packages_bag.
      2019-10-14
         Combined platform updates including updates to show install rollback list-ids";
    semver:module-version "1.2.0";
  }

  revision "2019-10-13" {
    description
      "NCS540L 7.1.1 release
      2019-10-12
      8000 series 7.0.11 release
      2019-08-13
         Common yang oper model for lindt and eXR install.";
    semver:module-version "1.1.0";
  }

  revision "2019-04-05" {
    description
      "Establish semantic version baseline.";
    semver:module-version "1.0.0";
  }

  revision "2015-11-09" {
    description
      "IOS XR 6.0 revision.";
  }

  typedef Inst-req-state {
    type enumeration {
      enum in-progress {
        value 0;
        description "In progress";
      }
      enum success {
        value 1;
        description "Success";
      }
      enum failure {
        value 2;
        description "Failure";
      }
    }
    description "Install request state type";
  }
  typedef Inst-fp-request-status {
    type enumeration {
      enum generation-up-to-date {
        value 0;
        description "Runtime fingerprint generation up to date.";
      }
      enum generation-in-progress {
        value 1;
        description "Runtime fingerprint generation in progress";
      }
      enum to-be-regenerated-at-apply {
        value 2;
        description
          "Runtime fingerprints will be regenerated on
          apply";
      }
    }
    description "package Fingerprint request status";
  }
  typedef Inst-profile-action {
    type enumeration {
      enum unknown {
        value 0;
        description "Unknown";
      }
      enum error-on-failure {
        value 1;
        description "error on failure";
      }
      enum warn-on-failure {
        value 2;
        description "warn on failure";
      }
      enum revert-on-failure {
        value 3;
        description
          "revert-on-failure (only supported for
          postchecks)";
      }
    }
    description "Install profile metric action type";
  }
  typedef Inst-profile-metric-name {
    type enumeration {
      enum communication-timeout {
        value 0;
        description "communication-timeout metric";
      }
      enum config-inconsistency {
        value 1;
        description "config-inconsistency metric";
      }
      enum process-resource {
        value 2;
        description "process-resource metric";
      }
      enum process-status {
        value 3;
        description "process-status metric";
      }
      enum system-clock {
        value 4;
        description "system-clock metric";
      }
      enum hw-monitoring {
        value 5;
        description "hw-monitoring metric";
      }
      enum lc-monitoring {
        value 6;
        description "lc-monitoring metric";
      }
      enum pci-monitoring {
        value 7;
        description "pci-monitoring metric";
      }
      enum wd-monitoring {
        value 8;
        description "wd-monitoring metric";
      }
      enum disk-space {
        value 9;
        description "disk-space metric";
      }
      enum upgrade-matrix {
        value 10;
        description "upgrade-matrix metric";
      }
      enum core-cleanup {
        value 11;
        description "core-cleanup metric";
      }
      enum file-cleanup {
        value 12;
        description "file-cleanup metric";
      }
    }
    description "Install profile metric names";
  }
  typedef Inst-profile-state {
    type enumeration {
      enum unknown {
        value 0;
        description "Unknown/Error";
      }
      enum enabled {
        value 1;
        description "Enabled";
      }
      enum disabled {
        value 2;
        description "Disabled";
      }
    }
    description "Install profile / metric state type";
  }
  typedef Caveat {
    type string;
    description "Caveat";
  }
  typedef Fix {
    type string;
    description "DDTS or fix ID";
  }
  typedef Install-opt-string {
    type string;
    description "Install opt string";
  }

  grouping INST-REQUEST-BAG {
    description "Request result bag";
    leaf request {
      type string;
      description "The last user request";
    }
    leaf state {
      xr:event-telemetry "Subscribe Telemetry Event";
      type Inst-req-state;
      description
        "The state of the last user request. Added
        telemetry event for operation state";
    }
    leaf timestamp {
      type string;
      description "The time the current state was entered";
    }
    leaf error {
      type string;
      description "String describing the error, if any";
    }
    leaf operation-id {
      xr:event-telemetry "Subscribe Telemetry Event";
      type Install-opt-string;
      description
        "Operation ID of the ongoing or  previous
        completed install operation.            Added
        telemetry event for install operation id";
    }
    leaf warning {
      type Install-opt-string;
      description "String describing a warning, if any";
    }
  }

  grouping INST-TOP-LEVEL-PKG-TYPE {
    description "Install user-installable package type";

    container rpm-fingerprint {
      description "RPM Fingerprint at install and run time";
      uses INST-RPM-FINGER-PRINT;
    }
    leaf name {
      type string;
      description "Package name";
    }
    leaf architecture {
      type string;
      description "Architecture";
    }
    leaf version {
      type string;
      description "Version";
    }
    leaf release {
      type string;
      description "Release";
    }
    leaf epoch {
      type Install-opt-string;
      description "Epoch";
    }
    leaf xr-mandatory {
      type boolean;
      description "XR Mandatory";
    }
    leaf xr-optional {
      type boolean;
      description "XR Optional";
    }
    leaf gpg-key-id {
      type Install-opt-string;
      description
        "The GPG key ID at install time. A key ID of '0'
        indicates a package with no GPG signature.";
    }
  }

  grouping INST-SUMMARY-PACKAGES-BAG {
    description "Summary packages result bag";
    leaf xr-packages-hash {
      type string;
      description "Hash of XR packages";
    }
    leaf label {
      type Install-opt-string;
      description "Label of image";
    }
    leaf rpm-fingerprint-status {
      type Inst-fp-request-status;
      description "Package Fingerprint request status";
    }
    leaf rpm-fingerprint-timestamp {
      type Install-opt-string;
      description "Package run time fingerprint collection time";
    }

    list package {
      description "Added telemetry event at packages level";
      uses INST-TOP-LEVEL-PKG-TYPE;
    }
  }

  grouping INST-PACKAGES-BAG {
    description "Package result bag";
    leaf rpm-fingerprint-status {
      type Inst-fp-request-status;
      description "Package Fingerprint request status";
    }
    leaf rpm-fingerprint-timestamp {
      type Install-opt-string;
      description "Package run time fingerprint collection time";
    }
    leaf label {
      type Install-opt-string;
      description "Label of image";
    }
    leaf xr-packages-hash {
      type Install-opt-string;
      description "Hash of XR packages in this bag";
    }

    list package {
      description "Packages";
      uses INST-PKG-TYPE;
    }
  }

  grouping INST-RPM-FINGER-PRINT {
    description "Install package fingerprint type";
    leaf rpm-fingerprint-install-time {
      type Install-opt-string;
      description "Package fingerprint at install time.";
    }
    leaf rpm-fingerprint-run-time {
      type Install-opt-string;
      description
        "Package fingerprint at run time. A runtime
        fingerprint of '0' indicates that the runtime
        fingerprint for this package has not yet been
        calculated.";
    }
  }

  grouping INST-PKG-TYPE {
    description "Install package type";

    container rpm-fingerprint {
      description "RPM Fingerprint at install and run time";
      uses INST-RPM-FINGER-PRINT;
    }
    leaf name {
      type string;
      description "Package name";
    }
    leaf architecture {
      type string;
      description "Architecture";
    }
    leaf version {
      type string;
      description "Version";
    }
    leaf release {
      type string;
      description "Release";
    }
    leaf epoch {
      type Install-opt-string;
      description "Epoch";
    }
    leaf gpg-key-id {
      type Install-opt-string;
      description
        "The GPG key ID at install time. A key ID of '0'
        indicates a package with no GPG signature.";
    }
  }

  grouping INST-FIX-TYPE {
    description "INST FIX TYPE";
    leaf ddts {
      type string;
      description "DDTS id";
    }

    list package {
      description "Packages";
      uses INST-PKG-TYPE;
    }
  }

  grouping INST-FIXES-BAG {
    description
      "Install bag containing details of
      active/committed fixes";

    list fixes {
      description "Fixes";
      uses INST-FIX-TYPE;
    }
  }

  grouping INST-VER-PKG-TYPE {
    description "Install package type";
    leaf name {
      type string;
      description "Name";
    }
    leaf version {
      type string;
      description "Version";
    }
    leaf built-by {
      type string;
      description "User built by";
    }
    leaf built-on {
      type string;
      description "Time built";
    }
    leaf workspace {
      type string;
      description "Workspace built in";
    }
    leaf build-host {
      type string;
      description "Build host";
    }
  }

  grouping INST-VERSION-BAG {
    description "Install version bag";
    leaf label {
      xr:event-telemetry "Subscribe Telemetry Event";
      type string;
      description "Added telemetry event on Label field";
    }
    leaf copyright-info {
      type string;
      description "Copyright information";
    }
    leaf hardware-info {
      type string;
      description "Hardware information";
    }
    leaf uptime {
      type string;
      description "System uptime";
    }
    leaf location {
      type Install-opt-string;
      description
        "Prefix for the path where packages will be
        installed";
    }
    leaf processor {
      type Install-opt-string;
      description "Processor";
    }
    leaf chassis-pid {
      type Install-opt-string;
      description "Chassis PID";
    }
    leaf chassis-description {
      type Install-opt-string;
      description "Chassis Unique Device Identifier description";
    }
    leaf xr-host-name {
      type Install-opt-string;
      description "Configured XR hostname";
    }
    leaf total-ram {
      type uint64;
      description "Total physical memory in GB";
    }

    list package {
      description "Packages";
      uses INST-VER-PKG-TYPE;
    }
  }

  grouping INST-POSTCHECKS-METRICS-DATA {
    description "Metric data";
    leaf name {
      type Inst-profile-metric-name;
      description "Name of the metric";
    }
    leaf state {
      type Inst-profile-state;
      description "State of the metric";
    }
    leaf action {
      type Inst-profile-action;
      description "Postcheck action for the metric";
    }
  }

  grouping INST-PROFILE-POSTCHECKS-DATA {
    description "Postchecks data";
    leaf state {
      type Inst-profile-state;
      description "State of postchecks";
    }

    list metric {
      description "Metrics settings";
      uses INST-POSTCHECKS-METRICS-DATA;
    }
  }

  grouping INST-PRECHECKS-METRICS-DATA {
    description "Metric data";
    leaf name {
      type Inst-profile-metric-name;
      description "Name of the metric";
    }
    leaf state {
      type Inst-profile-state;
      description "State of the metric";
    }
    leaf action {
      type Inst-profile-action;
      description "Precheck action for the metric";
    }
  }

  grouping INST-PROFILE-PRECHECKS-DATA {
    description "Prechecks data";
    leaf state {
      type Inst-profile-state;
      description "State of prechecks";
    }

    list metric {
      description "Metrics settings";
      uses INST-PRECHECKS-METRICS-DATA;
    }
  }

  grouping INST-PROFILE {
    description "Install profile bag";

    container prechecks {
      description "Prechecks settings";
      uses INST-PROFILE-PRECHECKS-DATA;
    }

    container postchecks {
      description "Postchecks settings";
      uses INST-PROFILE-POSTCHECKS-DATA;
    }
    leaf profile {
      type string;
      description "Name of the profile";
    }
    leaf state {
      type Inst-profile-state;
      description "The state of the profile (enabled/disabled)";
    }
    leaf error {
      type Install-opt-string;
      description "String describing the error, if any";
    }
  }

  grouping INSTALL-UPGRADE-MATRIX-ISO {
    description "Upgrade matrix info for the input ISO";
    leaf info {
      type Install-opt-string;
      description "Info";
    }
    leaf matrix-version {
      type Install-opt-string;
      description "Matrix file version";
    }

    list upgrade-matrix-info {
      description "Upgrade matrix table";
      uses INSTALL-UPGRADE-MATRIX-DATA;
    }
  }

  grouping INST-UPGRADE-MATRIX-RPM {
    description "Upgrade matrix RPM details";
    leaf name {
      type string;
      description "RPM name";
    }
    leaf version {
      type string;
      description "RPM version";
    }
  }

  grouping INST-UPGRADE-MATRIX-FIX {
    description "Upgrade matrix fix";
    leaf fix {
      type Fix;
      description "DDTS or fix ID";
    }

    list rpms {
      description "RPMs";
      uses INST-UPGRADE-MATRIX-RPM;
    }
  }

  grouping INST-REIMAGE-INFO {
    description "Reimage Info";
    leaf reimage-only {
      type boolean;
      description "Upgrade requires a reimage";
    }
  }

  grouping INST-UPGRADE-MATRIX-HW {
    description "Upgrade matrix hardware data";
    leaf pid {
      type Install-opt-string;
      description "PID";
    }
    leaf reason {
      type Install-opt-string;
      description "Reason for the hardware being unsupported";
    }
  }

  grouping INSTALL-UPGRADE-MATRIX-DETAILS {
    description "Upgrade matrix details";

    container reimage-info {
      description "Reimage info";
      uses INST-REIMAGE-INFO;
    }
    leaf-list bridging-fixes {
      type Fix;
      description "Bridging Fixes List";
    }
    leaf-list target-fixe {
      type Fix;
      description "Target Fixes List";
    }
    leaf-list caveats {
      type Caveat;
      description "Caveats list";
    }
    leaf-list blocklisted-fixe {
      type Fix;
      description "Blocklisted Fixes List";
    }

    list unsupported-hardware {
      description "Unsupported hardware list";
      uses INST-UPGRADE-MATRIX-HW;
    }

    list bridging-fixess-rpm {
      description
        "Bridging Fixes, list of DDTS (and associated
        RPMs)";
      uses INST-UPGRADE-MATRIX-FIX;
    }

    list target-fixes-rpm {
      description
        "Target Fixes, list of DDTS (and associated RPMs)";
      uses INST-UPGRADE-MATRIX-FIX;
    }

    list blocklisted-fixes-rpm {
      description
        "List of DDTS (and associated RPMs) which must
        not be installed";
      uses INST-UPGRADE-MATRIX-FIX;
    }
  }

  grouping INSTALL-UPGRADE-MATRIX-RELEASE-DATA {
    description "Upgrade matrix version data";
    leaf from {
      type string;
      description "From version";
    }
    leaf to {
      type string;
      description "To version";
    }
  }

  grouping INSTALL-UPGRADE-MATRIX-DATA {
    description "Upgrade matrix data";

    container versions {
      description "Versions";
      uses INSTALL-UPGRADE-MATRIX-RELEASE-DATA;
    }

    container details {
      description "Details";
      uses INSTALL-UPGRADE-MATRIX-DETAILS;
    }
  }

  grouping INSTALL-UPGRADE-MATRIX-RUNNING {
    description "Upgrade matrix info for current running image";
    leaf info {
      type Install-opt-string;
      description "Info";
    }
    leaf matrix-version {
      type Install-opt-string;
      description "Matrix file version";
    }

    list upgrade-matrix-info {
      description "Upgrade matrix table";
      uses INSTALL-UPGRADE-MATRIX-DATA;
    }
  }
}
