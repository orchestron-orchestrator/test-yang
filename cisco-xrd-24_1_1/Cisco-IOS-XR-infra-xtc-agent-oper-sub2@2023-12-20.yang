submodule Cisco-IOS-XR-infra-xtc-agent-oper-sub2 {

  belongs-to Cisco-IOS-XR-infra-xtc-agent-oper {
    prefix Cisco-IOS-XR-infra-xtc-agent-oper;
  }

  /*** LINKAGE (IMPORTS / INCLUDES) ***/

  import ietf-inet-types { prefix "inet"; }

  import cisco-semver { prefix "semver"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR infra-xtc-agent package operational data.

     Copyright (c) 2013-2023 by Cisco Systems, Inc.
     All rights reserved.";

  revision "2023-12-20" {
    description
      "new policy path type for mixed paths.
       2023-10-17
         Display of adj sids in topo for ipv6 links.
       2023-10-12
         Added fields for path-type of a policy and candidate path
       2023-08-07
         Display of associated resource lists for policies.
       2023-05-10
         Added conn-initiated, is-holddown-timer-running, is-dead-timer-running, and is-pce-initiated-redelegation-timer-running flags inside pcep-conn. Furthermore, added is-delegation-fallback-timer-running and is-state-timer-running inside plsp.
       2023-05-04
         Display Flex-Algo information for P2MP policies.
       2023-01-24
         Added fields for Flex-algo ASLA attributes on IPv4 and IPv6 links
       2022-11-07
         SR MPLS UCMP IGP weights addition.
       2022-10-26
         Dynamic CS Persistent PM and LSP, added fields for CP,LSP state and new SM transitions.
       2022-06-15
         Removed obsolete srv6-prefix container.
       2022-06-08
         Dynamic CS, added summary fields for standby CP and LSP
       2022-06-03
         Removed prefix-metric entry from the topology node.
       2022-05-17
         Renamed srv6usid to srv6-sid since all SRv6 SIDs are not micro SIDs
       2022-05-12
         Added checkpoint id in policy lsp segment list bag.
       2022-03-03
         Added is-srv6-local and is-srv6-remote in peer container.
       2022-03-03
         Added SID length and SID format for explicit path policy.
       2022-01-17
         Change the type of extended-value leaf from leaf-list to list.
       2021-11-21
         Added prefix-metric entry in the topology node.
       2021-11-09
         Added unreliable flag and update drop count in topology summary bag.
       2021-10-21
         Adding algorithm and computation time to path query results
       2021-09-27
         Added leaf max-install-standby-cpaths under grouping XTC-POLICY-BAG. Added leaf max-install-standby-cpaths under grouping XTC-GLOBAL-INFO-BAG.
       2021-08-31
         Added leaf segment-algorithm-set under grouping XTC-SEGMENTS-BAG.";
    semver:module-version "5.0.0";
  }

  revision "2021-07-27" {
    description
      "Added invalid reason leaf under segment-list container
      2021-06-14
          Added SL First Label and Start Index field in LSP SL MOI bag. Added NH Seperation enabled field in Global info bag. IosSetYangSchemaRev Cisco-IOS-XR-infra-xtc-agent-oper";
    semver:module-version "4.1.0";
  }

  revision "2021-05-21" {
    description
      "Added path invalidation drop flag in policy bag.
      2021-04-22
           Added TE metric field for Flex-algo ASLA.
      2021-02-18
           Remove deprecated performance-measurement oper bag and renamed pm config field name in xtc_pm_lsp_info. Added performance-measurement config data bag in lsp bag.
      2021-02-08
           Added performance-measurement config data bag in lsp bag.
      2020-12-13
           Added performance-measurement liveness-detection oper schema.
      2020-10-27
           Added A flag set field in show command to support A flag sent from PM side
      2020-09-16
           Adding operational nodes for new features path invalidation drop protected and unprotected path
      2020-09-04
           Modified the Extended-Affinities and ASLA-Extended-Affinities to be list instead of a leaf-list
      2020-05-12
           Add SRv6TE policy operational data
      2020-05-05
           changes related to treat SRv6 and SID as well-known when parsing XML for yang";
    semver:module-version "4.0.0";
  }

  revision "2020-01-16" {
    description
      "Removed event buffer from SR-TE policy model. Implement new statistic info for policy performance-measurement session. Added support for per-flow policy output. Added additional filter for policy type i.e. per-flow and per-destination.";
    semver:module-version "3.0.0";
  }

  revision "2019-09-09" {
    description
      "PCE/SRTE topology should display P-flag set for OSPF prefix-SID with explicit-null";
    semver:module-version "2.0.0";
  }

  revision "2019-05-01" {
    description
      "Added operational models for interface database.";
    semver:module-version "1.0.0";
  }

  revision "2019-04-15" {
    description
      "Hierarchical changes to policy forwarding model to organize the paths under the proper segment lists and LSPs.";
  }

  revision "2019-04-05" {
    description
      "Establish semantic version baseline.";
  }

  revision "2018-11-28" {
    description
      "Various modifications to policy-related models for better compatibility with the IETF policy draft.";
  }

  revision "2017-09-11" {
    description
      "Initial version";
  }

  revision "2015-11-09" {
    description
      "IOS XR 6.0 revision.";
  }

  typedef Xtc-srv6-sid {
    type inet:ipv6-address;
    description "Xtc srv6 sid";
  }
  typedef Xtc-sid {
    type enumeration {
      enum none {
        value 0;
        description "None";
      }
      enum mpls {
        value 1;
        description "MPLS";
      }
      enum ipv6 {
        value 2;
        description "IPv6";
      }
      enum srv6 {
        value 3;
        description "SRv6";
      }
    }
    description "Xtc sid";
  }
  typedef Xtc-ipv6-address {
    type inet:ipv6-address;
    description "Xtc ipv6 address";
  }
  typedef Xtc-ipv4-address {
    type inet:ipv4-address;
    description "Xtc ipv4 address";
  }

  grouping XTC-PREFIX-SID-TYPE {
    description "XTC PREFIX SID TYPE";
    leaf sid-type {
      type Xtc-sid;
      description "SIDType";
    }
    leaf label {
      when "../sid-type = 'mpls'" {
        description "../SIDType = 'MPLS'";
      }
      type uint32;
      description "MPLS label";
    }
    leaf ipv6 {
      when "../sid-type = 'ipv6'" {
        description "../SIDType = 'IPv6'";
      }
      type Xtc-ipv6-address;
      description "IPv6 address";
    }
    leaf srv6sid {
      when "../sid-type = 'srv6'" {
        description "../SIDType = 'SRV6'";
      }
      type Xtc-srv6-sid;
      description "SRv6 SID";
    }
  }
}
