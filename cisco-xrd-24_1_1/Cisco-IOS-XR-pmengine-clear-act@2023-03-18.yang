module Cisco-IOS-XR-pmengine-clear-act {
  namespace "http://cisco.com/ns/yang/Cisco-IOS-XR-pmengine-clear-act";
  prefix pmengine-clear-act;

  import cisco-semver {
    prefix semver;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR clear statistics for pm-engine module.

     Copyright (c) 2018-2020, 2023 by Cisco Systems, Inc.
     All rights reserved.";

  revision 2023-03-18 {
    description
      "mandatory true";
    semver:module-version "2.0.0";
  }

  revision "2020-09-13" {
    description
      "Clear per layer support for otu controllers";
    semver:module-version "1.2.0";
  }

  revision "2019-10-15" {
    description
      "Added support for flexible interval";
    semver:module-version "1.1.0";
  }

  revision "2019-10-01" {
    description
      "Made changes to be RFC6087 compliant";
    semver:module-version "1.0.1";
  }

  revision "2019-04-05" {
    description
      "Establish semantic version baseline.";
    semver:module-version "1.0.0";
  }

  revision "2018-01-09" {
    description
      "IOS XR 6.5.1 revision.";
  }

  rpc clear-controller-pm {
    description
      "Clear pm-engine statistics";
    input {
      leaf controller {
        type string;
        mandatory true;
        description
          "Controller name in R/S/I/P format";
      }
      leaf pm {
        type empty;
        mandatory true;
        description
          "clear pm counters";
      }
      leaf interval {
        type uint8 {
          range "0..4";
        }
        description
          "Clear 24-hour(0)/15-min(1)/30-sec(2)/Flexible-Interval(3)/all(4) pm statistics";
      }
      leaf layer {
        type string;
        description
          "Layer name to clear PM counter for specific layer";
      }
    }
  }
}
