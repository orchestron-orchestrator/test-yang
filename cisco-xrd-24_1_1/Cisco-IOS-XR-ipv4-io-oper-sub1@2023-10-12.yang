submodule Cisco-IOS-XR-ipv4-io-oper-sub1 {

  belongs-to Cisco-IOS-XR-ipv4-io-oper {
    prefix Cisco-IOS-XR-ipv4-io-oper;
  }

  /*** LINKAGE (IMPORTS / INCLUDES) ***/

  import cisco-semver { prefix "semver"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ipv4-io package operational data.

     Copyright (c) 2013-2023 by Cisco Systems, Inc.
     All rights reserved.";

  revision "2023-10-12" {
    description
      "Renamed line-state leaf to protocol-state, state-recvd-frm-im leaf removed
       2021-12-09
         Added few items in the bag related to ip address.";
    semver:module-version "2.0.0";
  }

  revision "2021-03-26" {
    description
      "Added few items in the bag.";
    semver:module-version "1.2.0";
  }

  revision "2019-10-01" {
    description
      "Updated brief and detail containers for node related interfaces.";
    semver:module-version "1.1.0";
  }

  revision "2019-04-05" {
    description
      "Establish semantic version baseline.";
    semver:module-version "1.0.1";
  }

  revision "2018-08-01" {
    description
      "Removed empty groupings.";
  }

  revision "2015-10-20" {
    description
      "this schema file has all the latest changes.";
  }

  revision "2015-01-07" {
    description
      "IOS XR 5.3.1 revision.";
  }

  grouping IPV4-IO-ICMP-TRAFFIC {
    description "ICMP Traffic Information";
    leaf received {
      type uint32;
      description "ICMP Received";
    }
    leaf checksum-error {
      type uint32;
      description "ICMP Checksum Errors";
    }
    leaf unknown {
      type uint32;
      description "ICMP Unknown";
    }
    leaf output {
      type uint32;
      description "ICMP Transmitted";
    }
    leaf admin-unreachable-sent {
      type uint32;
      description "ICMP Admin Unreachable Sent";
    }
    leaf network-unreachable-sent {
      type uint32;
      description "ICMP Network Unreachable Sent";
    }
    leaf host-unreachable-sent {
      type uint32;
      description "ICMP Host Unreachable Sent";
    }
    leaf protocol-unreachable-sent {
      type uint32;
      description "ICMP Protocol Unreachable Sent";
    }
    leaf port-unreachable-sent {
      type uint32;
      description "ICMP Port Unreachable Sent";
    }
    leaf fragment-unreachable-sent {
      type uint32;
      description "ICMP Fragment Unreachable Sent";
    }
    leaf admin-unreachable-received {
      type uint32;
      description "ICMP Recieved Admin Unreachable";
    }
    leaf network-unreachable-received {
      type uint32;
      description "ICMP Recieved Network Unreachable";
    }
    leaf host-unreachable-received {
      type uint32;
      description "ICMP Host Unreachable Received";
    }
    leaf protocol-unreachable-received {
      type uint32;
      description "ICMP protocol is unreachable";
    }
    leaf port-unreachable-received {
      type uint32;
      description "ICMP Port Unreachable Received";
    }
    leaf fragment-unreachable-received {
      type uint32;
      description "ICMP fragment is unreachable";
    }
    leaf hopcount-sent {
      type uint32;
      description "ICMP Hopcount Sent";
    }
    leaf reassembly-sent {
      type uint32;
      description "ICMP Reassembly Sent";
    }
    leaf hopcount-received {
      type uint32;
      description "ICMP Hopcount Received";
    }
    leaf reassebly-received {
      type uint32;
      description "ICMP Reassembly Received";
    }
    leaf param-error-received {
      type uint32;
      description "ICMP Parameter Error Received";
    }
    leaf param-error-send {
      type uint32;
      description "ICMP Parameter Error Sent";
    }
    leaf echo-request-sent {
      type uint32;
      description "ICMP Echo Request Sent";
    }
    leaf echo-request-received {
      type uint32;
      description "ICMP Echo Request Sent";
    }
    leaf echo-reply-sent {
      type uint32;
      description "ICMP Echo Reply Sent";
    }
    leaf echo-reply-received {
      type uint32;
      description "ICMP Echo Reply Received";
    }
    leaf mask-request-sent {
      type uint32;
      description "ICMP Mask Sent";
    }
    leaf mask-request-received {
      type uint32;
      description "ICMP Mask Received";
    }
    leaf mask-reply-sent {
      type uint32;
      description "ICMP Mask Sent";
    }
    leaf mask-reply-received {
      type uint32;
      description "ICMP Mask Received";
    }
    leaf source-quench-received {
      type uint32;
      description "ICMP Source Quench";
    }
    leaf redirect-received {
      type uint32;
      description "ICMP Redirect Received";
    }
    leaf redirect-send {
      type uint32;
      description "ICMP Redirect Sent";
    }
    leaf timestamp-received {
      type uint32;
      description "ICMP Timestamp Received";
    }
    leaf timestamp-reply-received {
      type uint32;
      description "ICMP Timestamp Reply Received";
    }
    leaf router-advert-received {
      type uint32;
      description "ICMP Router Advertisement Received";
    }
    leaf router-solicit-received {
      type uint32;
      description "ICMP Router Solicited Received";
    }
  }

  grouping IPV4-IO-TRAFFIC {
    description "IP Traffic Information";
    leaf input-packets {
      type uint32;
      description "Input packets for ipv4 io traffic";
    }
    leaf received-packets {
      type uint32;
      description "Ipv4 packets recieved for ipv4 io traffic";
    }
    leaf format-errors {
      type uint32;
      description "Format errors for ipv4 io traffic";
    }
    leaf bad-hop-count {
      type uint32;
      description "Bad Hop Count";
    }
    leaf bad-source-address {
      type uint32;
      description
        "Ipv4 source address for ipv4 io traffic is
        corrupted";
    }
    leaf bad-header {
      type uint32;
      description "Bad Header";
    }
    leaf no-protocol {
      type uint32;
      description "Protocol is not present";
    }
    leaf no-gateway {
      type uint32;
      description "No Gateway";
    }
    leaf reassemble-input {
      type uint32;
      description "RaInput";
    }
    leaf reassembled {
      type uint32;
      description "Fragment reassembled";
    }
    leaf reassemble-timeout {
      type uint32;
      description "Timeout for fragment reassembly";
    }
    leaf reassemble-max-drop {
      type uint32;
      description "Reassembly Max Drop";
    }
    leaf reassemble-failed {
      type uint32;
      description "Failure observed during fragment reassembly";
    }
    leaf options-present {
      type uint32;
      description "Ipv4 options are present";
    }
    leaf bad-option {
      type uint32;
      description "Bad Option";
    }
    leaf unknown-option {
      type uint32;
      description "Option for Unknown";
    }
    leaf bad-security-option {
      type uint32;
      description "Option for Bad Security";
    }
    leaf basic-security-option {
      type uint32;
      description "Option for Basic Security";
    }
    leaf extended-security-option {
      type uint32;
      description "Security option is extended for ipv4 io traffic";
    }
    leaf cipso-option {
      type uint32;
      description "Option for cipso";
    }
    leaf strict-source-route-option {
      type uint32;
      description "Option for strict source route";
    }
    leaf loose-source-route-option {
      type uint32;
      description "Option for loose source route";
    }
    leaf record-route-option {
      type uint32;
      description "Option for record route";
    }
    leaf sid-option {
      type uint32;
      description "Option for SID";
    }
    leaf timestamp-option {
      type uint32;
      description "Option for time stamp";
    }
    leaf router-alert-option {
      type uint32;
      description "Option for router alert";
    }
    leaf noop-option {
      type uint32;
      description "Option for no operation";
    }
    leaf end-option {
      type uint32;
      description "Option to end";
    }
    leaf packets-output {
      type uint32;
      description "Ipv4 packets output for ipv4 io traffic";
    }
    leaf packets-forwarded {
      type uint32;
      description "Ipv4 packets are forwarded";
    }
    leaf packets-fragmented {
      type uint32;
      description "ipv4 packets are fragmented";
    }
    leaf fragment-count {
      type uint32;
      description "Count for fragments";
    }
    leaf encapsulation-failed {
      type uint32;
      description "Observed failure during encapsulation";
    }
    leaf no-router {
      type uint32;
      description "No Router";
    }
    leaf packet-too-big {
      type uint32;
      description "Size of packet is too big";
    }
    leaf multicast-in {
      type uint32;
      description "Recieved multicast packets";
    }
    leaf multicast-out {
      type uint32;
      description "Sent multicast packets";
    }
    leaf broadcast-in {
      type uint32;
      description "Recieved broadcast packets";
    }
    leaf broadcast-out {
      type uint32;
      description "Sent broadcast packets";
    }
    leaf lisp-v4-encap {
      type uint32;
      description "Lisp IPv4 encapped packets";
    }
    leaf lisp-v4-decap {
      type uint32;
      description "Lisp IPv4 decapped packets";
    }
    leaf lisp-v6-encap {
      type uint32;
      description "Lisp IPv6 encapped packets";
    }
    leaf lisp-v6-decap {
      type uint32;
      description "Lisp IPv6 decapped packets";
    }
    leaf lisp-encap-error {
      type uint32;
      description "Lisp encapsulation errors";
    }
    leaf lisp-decap-error {
      type uint32;
      description "Lisp decapsulation errors";
    }
  }

  grouping IP-TRAFFIC {
    description "IP and ICMP Traffic Information";

    container ipv4-stats {
      description "IPv4 Network Stats";
      uses IPV4-IO-TRAFFIC;
    }

    container icmp-stats {
      description "ICMP Stats";
      uses IPV4-IO-ICMP-TRAFFIC;
    }
  }
}
