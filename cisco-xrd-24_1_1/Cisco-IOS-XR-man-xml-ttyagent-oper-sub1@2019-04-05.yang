submodule Cisco-IOS-XR-man-xml-ttyagent-oper-sub1 {

  belongs-to Cisco-IOS-XR-man-xml-ttyagent-oper {
    prefix Cisco-IOS-XR-man-xml-ttyagent-oper;
  }

  /*** LINKAGE (IMPORTS / INCLUDES) ***/

  import cisco-semver { prefix "semver"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR man-xml-ttyagent package operational data.

     Copyright (c) 2013-2019 by Cisco Systems, Inc.
     All rights reserved.";

  revision "2019-04-05" {
    description
      "Establish semantic version baseline.";
    semver:module-version "1.0.1";
  }

  revision "2018-12-13" {
    description
      "Fixing Yang Usability Issues.";
  }

  revision "2017-09-07" {
    description
      "Fixed type translation error.";
  }

  revision "2015-07-30" {
    description
      "Descriptions updated.";
  }

  revision "2015-01-07" {
    description
      "IOS XR 5.3.1 revision.";
  }

  typedef Xr-xml-session-alarm-register {
    type enumeration {
      enum registered {
        value 1;
        description "Registered";
      }
      enum not-registered {
        value 2;
        description "NotRegistered";
      }
    }
    description "AlarmNotify";
  }
  typedef Xr-xml-session-state {
    type enumeration {
      enum idle {
        value 1;
        description "Idle";
      }
      enum busy {
        value 2;
        description "Busy";
      }
    }
    description "SessionState";
  }

  grouping XR-XML-SESSION-INFO {
    description "XML SESSION INFO";
    leaf username {
      type string;
      description "Username";
    }
    leaf state {
      type Xr-xml-session-state;
      description "state of the session idle/busy";
    }
    leaf client-address {
      type string;
      description "ip address of the client";
    }
    leaf client-port {
      type uint32;
      description "client's port";
    }
    leaf config-session-id {
      type string;
      description "Config session ID";
    }
    leaf admin-config-session-id {
      type string;
      description "Admin config session ID";
    }
    leaf alarm-notification {
      type Xr-xml-session-alarm-register;
      description
        "is the session registered for alarm
        notifications";
    }
    leaf vrf-name {
      type string;
      description "VRF name ";
    }
    leaf start-time {
      type uint32;
      units "second";
      description
        "session start time in seconds since the Unix
        Epoch";
    }
    leaf elapsed-time {
      type uint32;
      units "second";
      description
        " Elapsed time(seconds) since a session is
        created";
    }
    leaf last-state-change {
      type uint32;
      units "second";
      description
        "Time(seconds) since last session state change
        happened ";
    }
  }
}
