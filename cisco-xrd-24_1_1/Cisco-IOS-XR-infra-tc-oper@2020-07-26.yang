module Cisco-IOS-XR-infra-tc-oper {

  /*** NAMESPACE / PREFIX DEFINITION ***/

  namespace "http://cisco.com/ns/yang/Cisco-IOS-XR-infra-tc-oper";


  prefix "infra-tc-oper";

  /*** LINKAGE (IMPORTS / INCLUDES) ***/

  import Cisco-IOS-XR-types { prefix "xr"; }

  import cisco-semver { prefix "semver"; }

  include Cisco-IOS-XR-infra-tc-oper-sub1 {
    revision-date 2020-07-26;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR infra-tc package operational data.

     This module contains definitions
     for the following management objects:
       traffic-collector: Global Traffic Collector configuration
         commands

     Copyright (c) 2013-2020 by Cisco Systems, Inc.
     All rights reserved.";

  revision "2020-07-26" {
    description
      "Added is OCAFT/OCSR enabled to track TC FSM modes and has SR flag to track label flag";
    semver:module-version "1.1.0";
  }

  revision "2019-06-17" {
    description
      "Change type of tunnel interface name to string";
    semver:module-version "1.0.0";
  }

  revision "2019-05-30" {
    description
      "Fix to extend range of valid OC-AFT Labels";
  }

  revision "2019-04-05" {
    description
      "Establish semantic version baseline.";
  }

  revision "2019-01-01" {
    description
      "Yang evaluator: updates to schema descriptions.";
  }

  revision "2018-11-30" {
    description
      "Adding label data and total count stats for OC-AFT.";
  }

  revision "2018-10-05" {
    description
      "Removed stat collection message statistics. LDP label is provided in prefix info if present.";
  }

  revision "2015-11-09" {
    description
      "IOS XR 6.0 revision.";
  }

  typedef Tc-oper-af-name {
    type enumeration {
      enum ipv4 {
        value 0;
        description "IPv4";
      }
      enum ipv6 {
        value 1;
        description "IPv6";
      }
    }
    description "Tc oper af name";
  }
  typedef Tc-oper-ocaft-label {
    type uint32 {
      range "0..1048575";
    }
    description "Tc oper ocaft label";
  }
  typedef Tc-oper-local-label {
    type uint32 {
      range "16..1048575";
    }
    description "Tc oper local label";
  }

  grouping AF-TABLE {
    description "Common node of default-vrf, traffic-collector";

    container afs {
      description "Address Family specific operational data";

      list af {
        key "af-name";
        description "Operational data for given Address Family";

        container counters {
          description "Show Counters";

          container labels {
            description "Label Database";

            list label {
              key "label";
              description "Show Label Counter";
              leaf label {
                type Tc-oper-ocaft-label;
                description "Local Label";
              }
              uses TC-MGMT-LABEL-DATA;
            }
          }

          container prefixes {
            description "Prefix Database";

            list prefix {
              description "Show Prefix Counter";
              leaf ipaddr {
                type xr:Cisco-ios-xr-string;
                description "IP Address";
              }
              leaf mask {
                type xr:Cisco-ios-xr-string;
                description "Prefix Mask";
              }
              leaf label {
                type Tc-oper-local-label;
                description "Local Label";
              }
              uses TC-MGMT-PREFIX-DATA;
            }
          }

          container tunnels {
            description
              "List of tunnels in the traffic collector
              tunnel database";

            list tunnel {
              key "interface-name";
              description "Information about a specific tunnel";
              leaf interface-name {
                type xr:Cisco-ios-xr-string;
                description "The Interface Name";
              }
              uses TC-MGMT-TUNNEL-DATA;
            }
          }
        }
        leaf af-name {
          type Tc-oper-af-name;
          description "Address Family name";
        }
      }
    }
  }

  container traffic-collector {
    config false;
    description "Global Traffic Collector configuration commands";

    container summary-oc-aft {
      description "Traffic Collector summary for oc-aft";
      uses TC-MGMT-OCAFT-SUMMARY;
    }

    container external-interfaces {
      description
        "List of interfaces in the traffic collector
        external interface database";

      list external-interface {
        key "interface-name";
        description
          "Information about a specific external interface";
        leaf interface-name {
          type xr:Interface-name;
          description "The Interface Name";
        }
        uses TC-MGMT-EXT-IF-DATA;
      }
    }

    container summary {
      description "Traffic Collector summary";
      uses TC-MGMT-SUMMARY;
    }

    container vrf-table {
      description "VRF specific operational data";

      container default-vrf {
        description "DefaultVRF specific operational data";
        uses AF-TABLE;
      }
    }
    uses AF-TABLE;
  }
}
