module Cisco-IOS-XR-um-cont-odu-otu-dwdm-optics-pm-cfg {

  /*** NAMESPACE / PREFIX DEFINITION ***/

  namespace "http://cisco.com/ns/yang/Cisco-IOS-XR-um-cont-odu-otu-dwdm-optics-pm-cfg";
  prefix um-cont-odu-otu-dwdm-optics-pm-cfg;

  /*** LINKAGE (IMPORTS / INCLUDES) ***/

  import Cisco-IOS-XR-types {
    prefix xr;
  }
  import Cisco-IOS-XR-um-interface-cfg {
    prefix a1;
  }
  import tailf-common {
    prefix tailf;
  }

  import cisco-semver { prefix "semver"; }

  /*** META INFORMATION ***/

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR cont-odu-otu-dwdm-optics-pm package configuration.

     This YANG module augments the
     modules with configuration data.

     Copyright (c) 2021-2022 by Cisco Systems, Inc.
     All rights reserved.";

  revision 2022-07-11 {
    description
      "Added missing description statement to nodes
       2022-06-01
         Adjusted controller augmentation hierarchy";
    semver:module-version "1.1.0";
  }

  revision "2021-10-14" {
    description
      "Initial release";
    semver:module-version "1.0.0";
  }

  feature optics {
    description
      "optics";
  }

  feature optics_cli_supp_check {
    description
      "optics cli supp check";
  }

  grouping CONT-BODY {
    description
      "Grouping for controller";
    container pm {
      when "../a1:controller-name[starts-with(text(),'ODU')] or "
         + "../a1:controller-name[starts-with(text(),'OTU')] or "
         + "../a1:controller-name[starts-with(text(),'dwdm')] or "
         + "../a1:controller-name[starts-with(text(),'Optics')]" {
        tailf:dependency "../a1:controller-name";
      }
      if-feature "optics";
      description
        "Configure pm parameters";
      container interval-15-min {
        if-feature "optics_cli_supp_check";
        description
          "Configure pm parameters of 15 minute interval";
        container otn {
          description
            "configure otn g709 performance monitoring";
          container threshold {
            description
              "Configure threshold on otn parameters";
            leaf es-pm-ne {
              type uint32 {
                range "0..900" {
                  description
                    "ES-PM threshold (seconds)";
                }
              }
              description
                "set ES-PM threshold";
            }
            leaf es-sm-ne {
              type uint32 {
                range "0..900" {
                  description
                    "ES-SM threshold (seconds)";
                }
              }
              description
                "set ES-SM threshold";
            }
            leaf esr-pm-ne {
              type uint32 {
                range "0..100000" {
                  description
                    "ESR-PM threshold";
                }
              }
              description
                "set ESR-PM threshold";
            }
            leaf esr-sm-ne {
              type uint32 {
                range "0..100000" {
                  description
                    "ESR-SM threshold";
                }
              }
              description
                "set ESR-SM threshold";
            }
            leaf ses-pm-ne {
              type uint32 {
                range "0..900" {
                  description
                    "SES-PM threshold (seconds)";
                }
              }
              description
                "set SES-PM threshold";
            }
            leaf ses-sm-ne {
              type uint32 {
                range "0..900" {
                  description
                    "SES-SM threshold (seconds)";
                }
              }
              description
                "set SES-SM threshold";
            }
            leaf sesr-pm-ne {
              type uint32 {
                range "0..100000" {
                  description
                    "SESR-PM threshold";
                }
              }
              description
                "set SESR-PM threshold";
            }
            leaf sesr-sm-ne {
              type uint32 {
                range "0..100000" {
                  description
                    "SESR-SM threshold";
                }
              }
              description
                "set SESR-PM threshold";
            }
            leaf uas-pm-ne {
              type uint32 {
                range "0..900" {
                  description
                    "UAS_PM threshold (seconds)";
                }
              }
              description
                "set UAS-PM threshold";
            }
            leaf uas-sm-ne {
              type uint32 {
                range "0..900" {
                  description
                    "UAS_SM threshold (seconds)";
                }
              }
              description
                "set UAS-SM threshold";
            }
            leaf bbe-pm-ne {
              type uint32 {
                range "0..8850600" {
                  description
                    "BBE_PM threshold";
                }
              }
              description
                "set BBE-PM threshold";
            }
            leaf bbe-sm-ne {
              type uint32 {
                range "0..8850600" {
                  description
                    "BBE_SM threshold";
                }
              }
              description
                "set BBE-SM threshold";
            }
            leaf bber-pm-ne {
              type uint32 {
                range "0..100000" {
                  description
                    "BBER_PM threshold";
                }
              }
              description
                "set BBER-PM threshold";
            }
            leaf bber-sm-ne {
              type uint32 {
                range "1..100000" {
                  description
                    "BBER_SM threshold";
                }
              }
              description
                "set BBER-SM threshold";
            }
            leaf fc-pm-ne {
              type uint32 {
                range "0..72" {
                  description
                    "FC_PM threshold";
                }
              }
              description
                "set FC-PM threshold";
            }
            leaf fc-sm-ne {
              type uint32 {
                range "0..72" {
                  description
                    "FC_SM threshold";
                }
              }
              description
                "set FC-SM threshold";
            }
            leaf es-pm-fe {
              type uint32 {
                range "0..900" {
                  description
                    "ES-PM threshold (seconds)";
                }
              }
              description
                "set ES-PM threshold";
            }
            leaf es-sm-fe {
              type uint32 {
                range "0..900" {
                  description
                    "ES-SM threshold (seconds)";
                }
              }
              description
                "set ES-SM threshold";
            }
            leaf esr-pm-fe {
              type uint32 {
                range "0..100000" {
                  description
                    "ESR-PM threshold";
                }
              }
              description
                "set ESR-PM threshold";
            }
            leaf esr-sm-fe {
              type uint32 {
                range "0..100000" {
                  description
                    "ESR-SM threshold";
                }
              }
              description
                "set ESR-SM threshold";
            }
            leaf ses-pm-fe {
              type uint32 {
                range "0..900" {
                  description
                    "SES-PM threshold (seconds)";
                }
              }
              description
                "set SES-PM threshold";
            }
            leaf ses-sm-fe {
              type uint32 {
                range "0..900" {
                  description
                    "SES-SM threshold (seconds)";
                }
              }
              description
                "set SES-SM threshold";
            }
            leaf sesr-pm-fe {
              type uint32 {
                range "0..100000" {
                  description
                    "SESR-PM threshold";
                }
              }
              description
                "set SESR-PM threshold";
            }
            leaf sesr-sm-fe {
              type uint32 {
                range "0..100000" {
                  description
                    "SESR-SM threshold";
                }
              }
              description
                "set SESR-PM threshold";
            }
            leaf uas-pm-fe {
              type uint32 {
                range "0..900" {
                  description
                    "UAS_PM threshold (seconds)";
                }
              }
              description
                "set UAS-PM threshold";
            }
            leaf uas-sm-fe {
              type uint32 {
                range "0..900" {
                  description
                    "UAS_SM threshold (seconds)";
                }
              }
              description
                "set UAS-SM threshold";
            }
            leaf bbe-pm-fe {
              type uint32 {
                range "0..8850600" {
                  description
                    "BBE_PM threshold";
                }
              }
              description
                "set BBE-PM threshold";
            }
            leaf bbe-sm-fe {
              type uint32 {
                range "0..8850600" {
                  description
                    "BBE_SM threshold";
                }
              }
              description
                "set BBE-SM threshold";
            }
            leaf bber-pm-fe {
              type uint32 {
                range "0..100000" {
                  description
                    "BBER_PM threshold";
                }
              }
              description
                "set BBER-PM threshold";
            }
            leaf bber-sm-fe {
              type uint32 {
                range "1..100000" {
                  description
                    "BBER_SM threshold";
                }
              }
              description
                "set BBER-SM threshold";
            }
            leaf fc-pm-fe {
              type uint32 {
                range "0..72" {
                  description
                    "FC_PM threshold";
                }
              }
              description
                "set FC-PM threshold";
            }
            leaf fc-sm-fe {
              type uint32 {
                range "0..72" {
                  description
                    "FC_SM threshold";
                }
              }
              description
                "set FC-SM threshold";
            }
            leaf es-ne {
              type uint32 {
                range "0..900" {
                  description
                    "ES-NE threshold (seconds)";
                }
              }
              description
                "set ES-NE threshold";
            }
            leaf esr-ne {
              type uint32 {
                range "0..100000" {
                  description
                    "ESR-NE threshold[Ratio parameters range(0-1),eg. 75000 corresponds to 0.75]";
                }
              }
              description
                "set ESR-NE threshold";
            }
            leaf ses-ne {
              type uint32 {
                range "0..900" {
                  description
                    "SES-NE threshold (seconds)";
                }
              }
              description
                "set SES-NE threshold";
            }
            leaf sesr-ne {
              type uint32 {
                range "0..100000" {
                  description
                    "SESR-NE threshold[Ratio parameters range(0-1),eg. 75000 corresponds to 0.75]";
                }
              }
              description
                "set SESR-NE threshold";
            }
            leaf uas-ne {
              type uint32 {
                range "0..900" {
                  description
                    "UAS-NE threshold (seconds)";
                }
              }
              description
                "set UAS-NE threshold";
            }
            leaf bbe-ne {
              type uint32 {
                range "0..8850600" {
                  description
                    "BBE-NE threshold";
                }
              }
              description
                "set BBE-NE threshold";
            }
            leaf bber-ne {
              type uint32 {
                range "1..100000" {
                  description
                    "BBER-NE threshold[Ratio parameters range(0-1),eg. 75000 corresponds to 0.75]";
                }
              }
              description
                "set BBER-NE threshold";
            }
            leaf fc-ne {
              type uint32 {
                range "0..72" {
                  description
                    "FC-NE threshold";
                }
              }
              description
                "set FC-NE threshold";
            }
            leaf es-fe {
              type uint32 {
                range "0..900" {
                  description
                    "ES-FE threshold (seconds)";
                }
              }
              description
                "set ES-FE threshold";
            }
            leaf esr-fe {
              type uint32 {
                range "0..100000" {
                  description
                    "es-fe threshold[Ratio parameters range(0-1),eg. 75000 corresponds to 0.75]";
                }
              }
              description
                "set ESR-FE threshold";
            }
            leaf ses-fe {
              type uint32 {
                range "0..900" {
                  description
                    "SES-FE threshold (seconds)";
                }
              }
              description
                "set SES-FE threshold";
            }
            leaf sesr-fe {
              type uint32 {
                range "0..100000" {
                  description
                    "SESR-FE threshold[Ratio parameters range(0-1),eg. 75000 corresponds to 0.75]";
                }
              }
              description
                "set SESR-FE threshold";
            }
            leaf uas-fe {
              type uint32 {
                range "0..900" {
                  description
                    "UAS-FE threshold (seconds)";
                }
              }
              description
                "set UAS-FE threshold";
            }
            leaf bbe-fe {
              type uint32 {
                range "0..8850600" {
                  description
                    "BBE-FE threshold";
                }
              }
              description
                "set BBE-FE threshold";
            }
            leaf bber-fe {
              type uint32 {
                range "1..100000" {
                  description
                    "BBER-FE threshold[Ratio parameters range(0-1),eg. 75000 corresponds to 0.75]";
                }
              }
              description
                "set BBER-FE threshold";
            }
            leaf fc-fe {
              type uint32 {
                range "0..72" {
                  description
                    "FC-FE threshold";
                }
              }
              description
                "set FC-FE threshold";
            }
          }
          container report {
            description
              "set otn TCA reporting status";
            container es-sm-ne {
              description
                "set es-sm TCA reporting status";
              container enable {
                presence "Indicates a enable node is configured.";
                description
                  "Enable TCA reporting";
              }
            }
            container ses-sm-ne {
              description
                "set ses-sm TCA reporting status";
              container enable {
                presence "Indicates a enable node is configured.";
                description
                  "Enable TCA reporting";
              }
            }
            container uas-sm-ne {
              description
                "set uas-sm TCA reporting status";
              container enable {
                presence "Indicates a enable node is configured.";
                description
                  "Enable TCA reporting";
              }
            }
            container bbe-sm-ne {
              description
                "set bbe-sm TCA reporting status";
              container enable {
                presence "Indicates a enable node is configured.";
                description
                  "Enable TCA reporting";
              }
            }
            container fc-sm-ne {
              description
                "set fc-sm TCA reporting status";
              container enable {
                presence "Indicates a enable node is configured.";
                description
                  "Enable TCA reporting";
              }
            }
            container esr-sm-ne {
              description
                "set esr-sm TCA reporting status";
              container enable {
                presence "Indicates a enable node is configured.";
                description
                  "Enable TCA reporting";
              }
            }
            container sesr-sm-ne {
              description
                "set sesr-sm TCA reporting status";
              container enable {
                presence "Indicates a enable node is configured.";
                description
                  "Enable TCA reporting";
              }
            }
            container bber-sm-ne {
              description
                "set bber-sm TCA reporting status";
              container enable {
                presence "Indicates a enable node is configured.";
                description
                  "Enable TCA reporting";
              }
            }
            container es-pm-ne {
              description
                "set es-pm TCA reporting status";
              container enable {
                presence "Indicates a enable node is configured.";
                description
                  "Enable TCA reporting";
              }
            }
            container ses-pm-ne {
              description
                "set ses-pm TCA reporting status";
              container enable {
                presence "Indicates a enable node is configured.";
                description
                  "Enable TCA reporting";
              }
            }
            container uas-pm-ne {
              description
                "set uas-pm TCA reporting status";
              container enable {
                presence "Indicates a enable node is configured.";
                description
                  "Enable TCA reporting";
              }
            }
            container bbe-pm-ne {
              description
                "set bbe-pm TCA reporting status";
              container enable {
                presence "Indicates a enable node is configured.";
                description
                  "Enable TCA reporting";
              }
            }
            container fc-pm-ne {
              description
                "set fc-pm TCA reporting status";
              container enable {
                presence "Indicates a enable node is configured.";
                description
                  "Enable TCA reporting";
              }
            }
            container esr-pm-ne {
              description
                "set esr-pm TCA reporting status";
              container enable {
                presence "Indicates a enable node is configured.";
                description
                  "Enable TCA reporting";
              }
            }
            container sesr-pm-ne {
              description
                "set sesr-pm TCA reporting status";
              container enable {
                presence "Indicates a enable node is configured.";
                description
                  "Enable TCA reporting";
              }
            }
            container bber-pm-ne {
              description
                "set bber-pm TCA reporting status";
              container enable {
                presence "Indicates a enable node is configured.";
                description
                  "Enable TCA reporting";
              }
            }
            container es-sm-fe {
              description
                "set es-sm TCA reporting status";
              container enable {
                presence "Indicates a enable node is configured.";
                description
                  "Enable TCA reporting";
              }
            }
            container ses-sm-fe {
              description
                "set ses-sm TCA reporting status";
              container enable {
                presence "Indicates a enable node is configured.";
                description
                  "Enable TCA reporting";
              }
            }
            container uas-sm-fe {
              description
                "set uas-sm TCA reporting status";
              container enable {
                presence "Indicates a enable node is configured.";
                description
                  "Enable TCA reporting";
              }
            }
            container bbe-sm-fe {
              description
                "set bbe-sm TCA reporting status";
              container enable {
                presence "Indicates a enable node is configured.";
                description
                  "Enable TCA reporting";
              }
            }
            container fc-sm-fe {
              description
                "set fc-sm TCA reporting status";
              container enable {
                presence "Indicates a enable node is configured.";
                description
                  "Enable TCA reporting";
              }
            }
            container esr-sm-fe {
              description
                "set esr-sm TCA reporting status";
              container enable {
                presence "Indicates a enable node is configured.";
                description
                  "Enable TCA reporting";
              }
            }
            container sesr-sm-fe {
              description
                "set sesr-sm TCA reporting status";
              container enable {
                presence "Indicates a enable node is configured.";
                description
                  "Enable TCA reporting";
              }
            }
            container bber-sm-fe {
              description
                "set bber-sm TCA reporting status";
              container enable {
                presence "Indicates a enable node is configured.";
                description
                  "Enable TCA reporting";
              }
            }
            container es-pm-fe {
              description
                "set es-pm TCA reporting status";
              container enable {
                presence "Indicates a enable node is configured.";
                description
                  "Enable TCA reporting";
              }
            }
            container ses-pm-fe {
              description
                "set ses-pm TCA reporting status";
              container enable {
                presence "Indicates a enable node is configured.";
                description
                  "Enable TCA reporting";
              }
            }
            container uas-pm-fe {
              description
                "set uas-pm TCA reporting status";
              container enable {
                presence "Indicates a enable node is configured.";
                description
                  "Enable TCA reporting";
              }
            }
            container bbe-pm-fe {
              description
                "set bbe-pm TCA reporting status";
              container enable {
                presence "Indicates a enable node is configured.";
                description
                  "Enable TCA reporting";
              }
            }
            container fc-pm-fe {
              description
                "set fc-pm TCA reporting status";
              container enable {
                presence "Indicates a enable node is configured.";
                description
                  "Enable TCA reporting";
              }
            }
            container esr-pm-fe {
              description
                "set esr-pm TCA reporting status";
              container enable {
                presence "Indicates a enable node is configured.";
                description
                  "Enable TCA reporting";
              }
            }
            container sesr-pm-fe {
              description
                "set sesr-pm TCA reporting status";
              container enable {
                presence "Indicates a enable node is configured.";
                description
                  "Enable TCA reporting";
              }
            }
            container bber-pm-fe {
              description
                "set bber-pm TCA reporting status";
              container enable {
                presence "Indicates a enable node is configured.";
                description
                  "Enable TCA reporting";
              }
            }
          }
          container pathmonitor {
            description
              "configure otn g709 performance monitoring";
            container threshold {
              description
                "Configure threshold on otn parameters";
              leaf es-ne {
                type uint32 {
                  range "0..900" {
                    description
                      "ES-NE threshold (seconds)";
                  }
                }
                description
                  "set ES-NE threshold";
              }
              leaf esr-ne {
                type uint32 {
                  range "0..100000" {
                    description
                      "ESR-NE threshold[Ratio parameters range(0-1),eg. 75000 corresponds to 0.75]";
                  }
                }
                description
                  "set ESR-NE threshold";
              }
              leaf ses-ne {
                type uint32 {
                  range "0..900" {
                    description
                      "SES-NE threshold (seconds)";
                  }
                }
                description
                  "set SES-NE threshold";
              }
              leaf sesr-ne {
                type uint32 {
                  range "0..100000" {
                    description
                      "SESR-NE threshold[Ratio parameters range(0-1),eg. 75000 corresponds to 0.75]";
                  }
                }
                description
                  "set SESR-NE threshold";
              }
              leaf uas-ne {
                type uint32 {
                  range "0..900" {
                    description
                      "UAS-NE threshold (seconds)";
                  }
                }
                description
                  "set UAS-NE threshold";
              }
              leaf bbe-ne {
                type uint32 {
                  range "0..8850600" {
                    description
                      "BBE-NE threshold";
                  }
                }
                description
                  "set BBE-NE threshold";
              }
              leaf bber-ne {
                type uint32 {
                  range "0..100000" {
                    description
                      "BBER-NE threshold[Ratio parameters range(0-1),eg. 75000 corresponds to 0.75]";
                  }
                }
                description
                  "set BBER-NE threshold";
              }
              leaf fc-ne {
                type uint32 {
                  range "0..72" {
                    description
                      "FC-NE threshold";
                  }
                }
                description
                  "set FC-NE threshold";
              }
              leaf es-fe {
                type uint32 {
                  range "0..900" {
                    description
                      "ES-FE threshold (seconds)";
                  }
                }
                description
                  "set ES-FE threshold";
              }
              leaf esr-fe {
                type uint32 {
                  range "0..100000" {
                    description
                      "ESR-FE threshold[Ratio parameters range(0-1),eg. 75000 corresponds to 0.75]";
                  }
                }
                description
                  "set ESR-FE threshold";
              }
              leaf ses-fe {
                type uint32 {
                  range "0..900" {
                    description
                      "SES-FE threshold (seconds)";
                  }
                }
                description
                  "set SES-FE threshold";
              }
              leaf sesr-fe {
                type uint32 {
                  range "0..100000" {
                    description
                      "SESR-FE threshold[Ratio parameters range(0-1),eg. 75000 corresponds to 0.75]";
                  }
                }
                description
                  "set SESR-FE threshold";
              }
              leaf uas-fe {
                type uint32 {
                  range "0..900" {
                    description
                      "UAS-FE threshold (seconds)";
                  }
                }
                description
                  "set UAS-FE threshold";
              }
              leaf bbe-fe {
                type uint32 {
                  range "0..8850600" {
                    description
                      "BBE-FE threshold";
                  }
                }
                description
                  "set BBE-FE threshold";
              }
              leaf bber-fe {
                type uint32 {
                  range "0..100000" {
                    description
                      "BBER-FE threshold[Ratio parameters range(0-1),eg. 75000 corresponds to 0.75]";
                  }
                }
                description
                  "set BBER-FE threshold";
              }
              leaf fc-fe {
                type uint32 {
                  range "0..72" {
                    description
                      "FC-FE threshold";
                  }
                }
                description
                  "set FC-FE threshold";
              }
            }
            container report {
              description
                "set otn TCA reporting status";
              container es-ne {
                description
                  "set es-ne TCA reporting status";
                container disable {
                  presence "Indicates a disable node is configured.";
                  description
                    "Disable TCA reporting";
                }
              }
              container ses-ne {
                description
                  "set ses-ne TCA reporting status";
                container disable {
                  presence "Indicates a disable node is configured.";
                  description
                    "Disable TCA reporting";
                }
              }
              container uas-ne {
                description
                  "set uas-ne TCA reporting status";
                container disable {
                  presence "Indicates a disable node is configured.";
                  description
                    "Disable TCA reporting";
                }
              }
              container bbe-ne {
                description
                  "set bbe-ne TCA reporting status";
                container disable {
                  presence "Indicates a disable node is configured.";
                  description
                    "Disable TCA reporting";
                }
              }
              container fc-ne {
                description
                  "set fc-ne TCA reporting status";
                container disable {
                  presence "Indicates a disable node is configured.";
                  description
                    "Disable TCA reporting";
                }
              }
              container esr-ne {
                description
                  "set esr-ne TCA reporting status";
                container disable {
                  presence "Indicates a disable node is configured.";
                  description
                    "Disable TCA reporting";
                }
              }
              container sesr-ne {
                description
                  "set sesr-ne TCA reporting status";
                container disable {
                  presence "Indicates a disable node is configured.";
                  description
                    "Disable TCA reporting";
                }
              }
              container bber-ne {
                description
                  "set bber-ne TCA reporting status";
                container disable {
                  presence "Indicates a disable node is configured.";
                  description
                    "Disable TCA reporting";
                }
              }
              container es-fe {
                description
                  "set es-fe TCA reporting status";
                container disable {
                  presence "Indicates a disable node is configured.";
                  description
                    "Disable TCA reporting";
                }
              }
              container ses-fe {
                description
                  "set ses-fe TCA reporting status";
                container disable {
                  presence "Indicates a disable node is configured.";
                  description
                    "Disable TCA reporting";
                }
              }
              container uas-fe {
                description
                  "set uas-fe TCA reporting status";
                container disable {
                  presence "Indicates a disable node is configured.";
                  description
                    "Disable TCA reporting";
                }
              }
              container bbe-fe {
                description
                  "set bbe-fe TCA reporting status";
                container disable {
                  presence "Indicates a disable node is configured.";
                  description
                    "Disable TCA reporting";
                }
              }
              container fc-fe {
                description
                  "set fc-fe TCA reporting status";
                container disable {
                  presence "Indicates a disable node is configured.";
                  description
                    "Disable TCA reporting";
                }
              }
              container esr-fe {
                description
                  "set esr-fe TCA reporting status";
                container disable {
                  presence "Indicates a disable node is configured.";
                  description
                    "Disable TCA reporting";
                }
              }
              container sesr-fe {
                description
                  "set sesr-fe TCA reporting status";
                container disable {
                  presence "Indicates a disable node is configured.";
                  description
                    "Disable TCA reporting";
                }
              }
              container bber-fe {
                description
                  "set bber-fe TCA reporting status";
                container disable {
                  presence "Indicates a disable node is configured.";
                  description
                    "Disable TCA reporting";
                }
              }
            }
          }
          container tcms {
            description
              "configure tcm performance monitoring";
            list tcm {
              key "channel-number";
              description
                "configure tcm performance monitoring";
              leaf channel-number {
                type uint32 {
                  range "1..6" {
                    description
                      " Channel Number";
                  }
                }
                description
                  "configure tcm performance monitoring";
              }
              container threshold {
                description
                  "Configure threshold on otn parameters";
                leaf es-ne {
                  type uint32 {
                    range "0..900" {
                      description
                        "ES-NE threshold (seconds)";
                    }
                  }
                  description
                    "set ES-NE threshold";
                }
                leaf esr-ne {
                  type uint32 {
                    range "0..100000" {
                      description
                        "ESR-NE threshold[Ratio parameters range(0-1),eg. 75000 corresponds to 0.75]";
                    }
                  }
                  description
                    "set ESR-NE threshold";
                }
                leaf ses-ne {
                  type uint32 {
                    range "0..900" {
                      description
                        "SES-NE threshold (seconds)";
                    }
                  }
                  description
                    "set SES-NE threshold";
                }
                leaf sesr-ne {
                  type uint32 {
                    range "0..100000" {
                      description
                        "SESR-NE threshold[Ratio parameters range(0-1),eg. 75000 corresponds to 0.75]";
                    }
                  }
                  description
                    "set SESR-NE threshold";
                }
                leaf uas-ne {
                  type uint32 {
                    range "0..900" {
                      description
                        "UAS-NE threshold (seconds)";
                    }
                  }
                  description
                    "set UAS-NE threshold";
                }
                leaf bbe-ne {
                  type uint32 {
                    range "0..8850600" {
                      description
                        "BBE-NE threshold";
                    }
                  }
                  description
                    "set BBE-NE threshold";
                }
                leaf bber-ne {
                  type uint32 {
                    range "0..100000" {
                      description
                        "BBER-NE threshold[Ratio parameters range(0-1),eg. 75000 corresponds to 0.75]";
                    }
                  }
                  description
                    "set BBER-NE threshold";
                }
                leaf fc-ne {
                  type uint32 {
                    range "0..72" {
                      description
                        "FC-NE threshold";
                    }
                  }
                  description
                    "set FC-NE threshold";
                }
                leaf es-fe {
                  type uint32 {
                    range "0..900" {
                      description
                        "ES-FE threshold (seconds)";
                    }
                  }
                  description
                    "set ES-FE threshold";
                }
                leaf esr-fe {
                  type uint32 {
                    range "0..100000" {
                      description
                        "ESR-FE threshold[Ratio parameters range(0-1),eg. 75000 corresponds to 0.75]";
                    }
                  }
                  description
                    "set ESR-FE threshold";
                }
                leaf ses-fe {
                  type uint32 {
                    range "0..900" {
                      description
                        "SES-FE threshold (seconds)";
                    }
                  }
                  description
                    "set SES-FE threshold";
                }
                leaf sesr-fe {
                  type uint32 {
                    range "0..100000" {
                      description
                        "SESR-FE threshold[Ratio parameters range(0-1),eg. 75000 corresponds to 0.75]";
                    }
                  }
                  description
                    "set SESR-FE threshold";
                }
                leaf uas-fe {
                  type uint32 {
                    range "0..900" {
                      description
                        "UAS-FE threshold (seconds)";
                    }
                  }
                  description
                    "set UAS-FE threshold";
                }
                leaf bbe-fe {
                  type uint32 {
                    range "0..8850600" {
                      description
                        "BBE-FE threshold";
                    }
                  }
                  description
                    "set BBE-FE threshold";
                }
                leaf bber-fe {
                  type uint32 {
                    range "0..100000" {
                      description
                        "BBER-FE threshold[Ratio parameters range(0-1),eg. 75000 corresponds to 0.75]";
                    }
                  }
                  description
                    "set BBER-FE threshold";
                }
                leaf fc-fe {
                  type uint32 {
                    range "0..72" {
                      description
                        "FC-FE threshold";
                    }
                  }
                  description
                    "set FC-FE threshold";
                }
              }
              container report {
                description
                  "set otn TCA reporting status";
                container es-fe {
                  description
                    "set es-fe TCA reporting status";
                  container disable {
                    presence "Indicates a disable node is configured.";
                    description
                      "Disable TCA reporting";
                  }
                }
                container ses-fe {
                  description
                    "set ses-fe TCA reporting status";
                  container disable {
                    presence "Indicates a disable node is configured.";
                    description
                      "Disable TCA reporting";
                  }
                }
                container uas-fe {
                  description
                    "set uas-fe TCA reporting status";
                  container disable {
                    presence "Indicates a disable node is configured.";
                    description
                      "Disable TCA reporting";
                  }
                }
                container bbe-fe {
                  description
                    "set bbe-fe TCA reporting status";
                  container disable {
                    presence "Indicates a disable node is configured.";
                    description
                      "Disable TCA reporting";
                  }
                }
                container fc-fe {
                  description
                    "set fc-fe TCA reporting status";
                  container disable {
                    presence "Indicates a disable node is configured.";
                    description
                      "Disable TCA reporting";
                  }
                }
                container esr-fe {
                  description
                    "set esr-fe TCA reporting status";
                  container disable {
                    presence "Indicates a disable node is configured.";
                    description
                      "Disable TCA reporting";
                  }
                }
                container sesr-fe {
                  description
                    "set sesr-fe TCA reporting status";
                  container disable {
                    presence "Indicates a disable node is configured.";
                    description
                      "Disable TCA reporting";
                  }
                }
                container bber-fe {
                  description
                    "set bber-fe TCA reporting status";
                  container disable {
                    presence "Indicates a disable node is configured.";
                    description
                      "Disable TCA reporting";
                  }
                }
                container es-ne {
                  description
                    "set es-ne TCA reporting status";
                  container disable {
                    presence "Indicates a disable node is configured.";
                    description
                      "Disable TCA reporting";
                  }
                }
                container ses-ne {
                  description
                    "set ses-ne TCA reporting status";
                  container disable {
                    presence "Indicates a disable node is configured.";
                    description
                      "Disable TCA reporting";
                  }
                }
                container uas-ne {
                  description
                    "set uas-ne TCA reporting status";
                  container disable {
                    presence "Indicates a disable node is configured.";
                    description
                      "Disable TCA reporting";
                  }
                }
                container bbe-ne {
                  description
                    "set bbe-ne TCA reporting status";
                  container disable {
                    presence "Indicates a disable node is configured.";
                    description
                      "Disable TCA reporting";
                  }
                }
                container fc-ne {
                  description
                    "set fc-ne TCA reporting status";
                  container disable {
                    presence "Indicates a disable node is configured.";
                    description
                      "Disable TCA reporting";
                  }
                }
                container esr-ne {
                  description
                    "set esr-ne TCA reporting status";
                  container disable {
                    presence "Indicates a disable node is configured.";
                    description
                      "Disable TCA reporting";
                  }
                }
                container sesr-ne {
                  description
                    "set sesr-ne TCA reporting status";
                  container disable {
                    presence "Indicates a disable node is configured.";
                    description
                      "Disable TCA reporting";
                  }
                }
                container bber-ne {
                  description
                    "set bber-ne TCA reporting status";
                  container disable {
                    presence "Indicates a disable node is configured.";
                    description
                      "Disable TCA reporting";
                  }
                }
              }
            }
          }
        }
        container optics {
          description
            "Configure optics performance monitoring";
          container threshold {
            description
              "Configure threshold on optics parameters";
            container lbc {
              description
                "set lbc threshold";
              leaf min {
                type uint32 {
                  range "1..4294967294" {
                    description
                      "lbc min threshold (mA)";
                  }
                }
                description
                  "set lbc min threshold";
              }
              leaf max {
                type uint32 {
                  range "1..4294967294" {
                    description
                      "lbc max threshold (mA)";
                  }
                }
                description
                  "set lbc max threshold";
              }
            }
            container opt {
              description
                "set opt threshold in uW";
              leaf min {
                type uint32 {
                  range "1..4294967294" {
                    description
                      "opt min threshold (uW) ";
                  }
                }
                description
                  "set opt min threshold in uW";
              }
              leaf max {
                type uint32 {
                  range "1..4294967294" {
                    description
                      "opt max threshold (uW) ";
                  }
                }
                description
                  "set opt max threshold in uW";
              }
            }
            container opr {
              description
                "set opr threshold in uW";
              leaf max {
                type uint32 {
                  range "1..4294967294" {
                    description
                      "opr max threshold (uW) ";
                  }
                }
                description
                  "set opr max threshold in uW";
              }
              leaf min {
                type uint32 {
                  range "1..4294967294" {
                    description
                      "opr min threshold (uW) ";
                  }
                }
                description
                  " set opr min threshold in uW";
              }
            }
            container dgd {
              description
                "set differential group delay threshold";
              leaf min {
                type uint32 {
                  range "1..4294967294" {
                    description
                      "differential group delay min threshold (1/100th of ps)";
                  }
                }
                description
                  "set differential group delay min threshold";
              }
              leaf max {
                type uint32 {
                  range "1..4294967294" {
                    description
                      "differential delay group max threshold (1/100th of ps)";
                  }
                }
                description
                  "set differential group delay max threshold";
              }
            }
            container pmd {
              description
                "set polarization mode dispersion threshold";
              leaf min {
                type uint32 {
                  range "1..4294967294" {
                    description
                      "polarization mode dispersion min threshold (ps^2)";
                  }
                }
                description
                  "set polarization mode dispersion min threshold";
              }
              leaf max {
                type uint32 {
                  range "1..4294967294" {
                    description
                      "polarization mode dispersion max threshold (ps^2)";
                  }
                }
                description
                  "set polarization mode dispersion max threshold";
              }
            }
            container osnr {
              description
                "set optical signal to noise ratio threshold";
              leaf min {
                type uint32 {
                  range "1..4294967294" {
                    description
                      "optical signal to noise ratio min threshold (1/100th of dB)";
                  }
                }
                description
                  "set optical signal to noise ratio min threshold";
              }
              leaf max {
                type uint32 {
                  range "1..4294967294" {
                    description
                      "optical signal to noise ratio max threshold (1/100th of dB)";
                  }
                }
                description
                  "set optical siganl to noise max threshold";
              }
            }
            container pdl {
              description
                "set polarization dependent loss threshold";
              leaf min {
                type uint32 {
                  range "1..4294967294" {
                    description
                      "polarization dependent loss min threshold (1/100th of dB)";
                  }
                }
                description
                  "set polarization dependent loss min threshold";
              }
              leaf max {
                type uint32 {
                  range "1..4294967294" {
                    description
                      "polarization dependent loss max threshold (1/100th of dB)";
                  }
                }
                description
                  "set polarization dependent loss max threshold";
              }
            }
            container pcr {
              description
                "set polarization change rate threshold";
              leaf min {
                type uint32 {
                  range "1..4294967294" {
                    description
                      "polarization change rate min threshold (rad/s)";
                  }
                }
                description
                  "set polarization change rate min threshold";
              }
              leaf max {
                type uint32 {
                  range "1..4294967294" {
                    description
                      "polarization change rate max threshold (rad/s)";
                  }
                }
                description
                  "set polarization change rate max threshold";
              }
            }
            container pn {
              description
                "set phase noise threshold";
              leaf min {
                type uint32 {
                  range "1..4294967294" {
                    description
                      "phase noise min threshold (dB)";
                  }
                }
                description
                  "set phase noise min threshold";
              }
              leaf max {
                type uint32 {
                  range "1..4294967290" {
                    description
                      "phase noise max threshold (dB)";
                  }
                }
                description
                  "set phase noise max threshold";
              }
            }
            container cd {
              description
                "set chromatic dispersion threshold";
              leaf min {
                type union {
                  type int32 {
                    range "-70000..70000" {
                      description
                        "chromatic dispersion min threshold (ps/nm)";
                    }
                  }
                  type int32 {
                    range "-350000..350000" {
                      description
                        "chromatic dispersion min threshold (ps/nm)";
                    }
                  }
                }
                description
                  "set chromatic dispersion min threshold";
              }
              leaf max {
                type union {
                  type int32 {
                    range "-70000..70000" {
                      description
                        "chromatic dispersion max threshold (ps/nm)";
                    }
                  }
                  type int32 {
                    range "-350000..350000" {
                      description
                        "chromatic dispersion max threshold (ps/nm)";
                    }
                  }
                }
                description
                  "set chromatic dispersion max threshold";
              }
            }
            container opt-dbm {
              description
                "set opt threshold in dbm";
              leaf min {
                type int32 {
                  range "-3000..6633" {
                    description
                      "Enter 4 digit value ;Input value 3000 for 30.00dbm";
                  }
                }
                description
                  "Set opt min threshold in dbm";
              }
              leaf max {
                type int32 {
                  range "-3000..6633" {
                    description
                      "Enter 4 digit value ;Input value 3000 for 30.00dbm";
                  }
                }
                description
                  "set opt max threshold in dbm";
              }
            }
            container opr-dbm {
              description
                "set opr threshold value in dbm";
              leaf min {
                type int32 {
                  range "-3000..6633" {
                    description
                      "Enter 4 digit value ;Input value 3000 for 30.00dbm";
                  }
                }
                description
                  "set opr min threshold in dbm";
              }
              leaf max {
                type int32 {
                  range "-3000..6633" {
                    description
                      "Enter 4 digit value ;Input value 3000 for 30.00dbm";
                  }
                }
                description
                  "set opr max threshold in dbm";
              }
            }
            container lbc-pc {
              description
                "set lbc % threshold";
              leaf min {
                type uint32 {
                  range "0..1000" {
                    description
                      "lbc min threshold (in units of 0.1%)";
                  }
                }
                description
                  "set lbc % min threshold";
              }
              leaf max {
                type uint32 {
                  range "0..1000" {
                    description
                      "lbc max threshold (in units of 0.1%)";
                  }
                }
                description
                  "set lbc % max threshold";
              }
            }
            container sopmd {
              description
                "set second order polarization mode dispersion threshold";
              leaf min {
                type uint32 {
                  range "1..4294967294" {
                    description
                      "polarization mode dispersion min threshold (in units of 0.01 ps^2)";
                  }
                }
                description
                  "set polarization mode dispersion min threshold";
              }
              leaf max {
                type uint32 {
                  range "1..4294967294" {
                    description
                      "polarization mode dispersion max threshold ( in units of 0.01  ps^2)";
                  }
                }
                description
                  "set polarization mode dispersion max threshold";
              }
            }
            container rx-sig-pow {
              description
                "set rx sig power threshold in uW";
              leaf min {
                type uint32 {
                  range "1..4294967290" {
                    description
                      " rx sig power threshold in uW";
                  }
                }
                description
                  "rx sig power min threshold in uW ";
              }
              leaf max {
                type uint32 {
                  range "1..4294967290" {
                    description
                      "rx sig power max threshold in uW";
                  }
                }
                description
                  "set rx sig power max threshold in uW";
              }
            }
            container snr {
              description
                "set SNR threshold";
              leaf min {
                type uint32 {
                  range "1..2147483646" {
                    description
                      "SNR min threshold";
                  }
                }
                description
                  "set SNR min threshold ";
              }
              leaf max {
                type uint32 {
                  range "1..2147483646" {
                    description
                      "SNR max threshold ";
                  }
                }
                description
                  "set SNR max threshold ";
              }
            }
            container snr-ax {
              description
                "set SNR AX threshold";
              leaf min {
                type uint32 {
                  range "1..2147483646" {
                    description
                      "SNR AX min threshold";
                  }
                }
                description
                  "set SNR AX min threshold ";
              }
              leaf max {
                type uint32 {
                  range "1..2147483646" {
                    description
                      "SNR AX max threshold ";
                  }
                }
                description
                  "set SNR AX max threshold ";
              }
            }
            container snr-bx {
              description
                "set SNR BX threshold";
              leaf min {
                type uint32 {
                  range "1..2147483646" {
                    description
                      "SNR BX min threshold";
                  }
                }
                description
                  "set SNR BX min threshold ";
              }
              leaf max {
                type uint32 {
                  range "1..2147483646" {
                    description
                      "SNR BX max threshold ";
                  }
                }
                description
                  "set SNR BX max threshold ";
              }
            }
            container snr-ay {
              description
                "set SNR AY threshold";
              leaf min {
                type uint32 {
                  range "1..2147483646" {
                    description
                      "SNR AY min threshold";
                  }
                }
                description
                  "set SNR AY min threshold ";
              }
              leaf max {
                type uint32 {
                  range "1..2147483646" {
                    description
                      "SNR AY max threshold ";
                  }
                }
                description
                  "set SNR AY max threshold ";
              }
            }
            container snr-by {
              description
                "set SNR BY threshold";
              leaf min {
                type uint32 {
                  range "1..2147483646" {
                    description
                      "SNR BY min threshold";
                  }
                }
                description
                  "set SNR BY min threshold ";
              }
              leaf max {
                type uint32 {
                  range "1..2147483646" {
                    description
                      "SNR BY max threshold ";
                  }
                }
                description
                  "set SNR BY max threshold ";
              }
            }
            container rx-sig-pow-dbm {
              description
                "set rx-sig-pow threshold in dbm";
              leaf min {
                type int32 {
                  range "-3000..6633" {
                    description
                      "Enter 4 digit value ;Input value 3000 for 30.00dbm";
                  }
                }
                description
                  "set rx-sig-pow min threshold in dbm";
              }
              leaf max {
                type int32 {
                  range "-3000..6633" {
                    description
                      "Enter 4 digit value ;Input value 3000 for 30.00dbm";
                  }
                }
                description
                  "set rx-sig-pow max threshold in dbm";
              }
            }
            container low-freq-off {
              description
                "set low signal freq offset threshold in Mhz";
              leaf min {
                type int32 {
                  range "-1500..1500" {
                    description
                      "low signal freq offset min threshold in Mhz";
                  }
                }
                description
                  "set low signal freq offset min threshold in Mhz";
              }
              leaf max {
                type int32 {
                  range "-1500..1500" {
                    description
                      "low signal freq offset max threshold in Mhz";
                  }
                }
                description
                  "set low signal freq offset max threshold in Mhz";
              }
            }
            container sop-s1 {
              description
                "set SOP S1 threshold ";
              leaf min {
                type int32 {
                  range "-100..100" {
                    description
                      "SOP S1 threshold ";
                  }
                }
                description
                  "set SOP S1 min threshold ";
              }
              leaf max {
                type int32 {
                  range "-100..100" {
                    description
                      "SOP S1 max threshold ";
                  }
                }
                description
                  "set SOP S1 max threshold ";
              }
            }
            container sop-s2 {
              description
                "set SOP S2 threshold ";
              leaf min {
                type int32 {
                  range "-100..100" {
                    description
                      "SOP S2 threshold ";
                  }
                }
                description
                  "set SOP S2 min threshold ";
              }
              leaf max {
                type int32 {
                  range "-100..100" {
                    description
                      "SOP S2 max threshold ";
                  }
                }
                description
                  "set SOP S2 max threshold ";
              }
            }
            container sop-s3 {
              description
                "set SOP S3 threshold ";
              leaf min {
                type int32 {
                  range "-100..100" {
                    description
                      "SOP S3 threshold ";
                  }
                }
                description
                  "set SOP S3 min threshold ";
              }
              leaf max {
                type int32 {
                  range "-100..100" {
                    description
                      "SOP S3 max threshold ";
                  }
                }
                description
                  "set SOP S3 max threshold ";
              }
            }
          }
          container report {
            description
              "set optics TCA reporting status";
            container lbc {
              description
                "set lbc TCA reporting status";
              container min-tca {
                description
                  "set lbc min TCA reporting status";
                container enable {
                  presence "Indicates a enable node is configured.";
                  description
                    "Enable TCA reporting";
                }
              }
              container max-tca {
                description
                  "set lbc max TCA reporting status";
                container enable {
                  presence "Indicates a enable node is configured.";
                  description
                    "Enable TCA reporting";
                }
              }
            }
            container opt {
              description
                "set opt TCA reporting status";
              container min-tca {
                description
                  "set opt min TCA reporting status";
                container enable {
                  presence "Indicates a enable node is configured.";
                  description
                    "Enable TCA reporting";
                }
              }
              container max-tca {
                description
                  "set opt max TCA reporting status";
                container enable {
                  presence "Indicates a enable node is configured.";
                  description
                    "Enable TCA reporting";
                }
              }
            }
            container opr {
              description
                "set opr TCA reporting status";
              container min-tca {
                description
                  "set opr min TCA reporting status";
                container enable {
                  presence "Indicates a enable node is configured.";
                  description
                    "Enable TCA reporting";
                }
              }
              container max-tca {
                description
                  "set opr max TCA reporting status";
                container enable {
                  presence "Indicates a enable node is configured.";
                  description
                    "Enable TCA reporting";
                }
              }
            }
            container cd {
              description
                "set chromatic dispersion TCA reporting status";
              container min-tca {
                description
                  "set chromatic dispersion min TCA reporting status";
                container enable {
                  presence "Indicates a enable node is configured.";
                  description
                    "Enable TCA reporting";
                }
              }
              container max-tca {
                description
                  "set chromatic dispersion max TCA reporting status";
                container enable {
                  presence "Indicates a enable node is configured.";
                  description
                    "Enable TCA reporting";
                }
              }
            }
            container dgd {
              description
                "set differential group delay TCA reporting status";
              container min-tca {
                description
                  "set differentail group delay min TCA reporting status";
                container enable {
                  presence "Indicates a enable node is configured.";
                  description
                    "Enable TCA reporting";
                }
              }
              container max-tca {
                description
                  "set differential group delay max TCA reporting status";
                container enable {
                  presence "Indicates a enable node is configured.";
                  description
                    "Enable TCA reporting";
                }
              }
            }
            container pmd {
              description
                "set polarization mode dispersion TCA reporting status";
              container min-tca {
                description
                  "set polarization mode dispersion min TCA reporting status";
                container enable {
                  presence "Indicates a enable node is configured.";
                  description
                    "Enable TCA reporting";
                }
              }
              container max-tca {
                description
                  "set polarization mode dispersion max TCA reporting status";
                container enable {
                  presence "Indicates a enable node is configured.";
                  description
                    "Enable TCA reporting";
                }
              }
            }
            container osnr {
              description
                "set optical signal to noise ratio TCA reporting status";
              container min-tca {
                description
                  "set optical signal to noise ratio min TCA reporting status";
                container enable {
                  presence "Indicates a enable node is configured.";
                  description
                    "Enable TCA reporting";
                }
              }
              container max-tca {
                description
                  "set optical signal to noise ratio max TCA reporting status";
                container enable {
                  presence "Indicates a enable node is configured.";
                  description
                    "Enable TCA reporting";
                }
              }
            }
            container pdl {
              description
                "set polarization dependent loss TCA reporting status";
              container min-tca {
                description
                  "set polarization dependent loss min TCA reporting status";
                container enable {
                  presence "Indicates a enable node is configured.";
                  description
                    "Enable TCA reporting";
                }
              }
              container max-tca {
                description
                  "set polarization dependent loss max TCA reporting status";
                container enable {
                  presence "Indicates a enable node is configured.";
                  description
                    "Enable TCA reporting";
                }
              }
            }
            container pcr {
              description
                "set polarization change rate TCA reporting status";
              container min-tca {
                description
                  "set polarization change rate min TCA reporting status";
                container enable {
                  presence "Indicates a enable node is configured.";
                  description
                    "Enable TCA reporting";
                }
              }
              container max-tca {
                description
                  "set polarization change rate max TCA reporting status";
                container enable {
                  presence "Indicates a enable node is configured.";
                  description
                    "Enable TCA reporting";
                }
              }
            }
            container pn {
              description
                "set phase noise TCA reporting status";
              container min-tca {
                description
                  "set phase noise min TCA reporting status";
                container enable {
                  presence "Indicates a enable node is configured.";
                  description
                    "Enable TCA reporting";
                }
              }
              container max-tca {
                description
                  "set phase noise max TCA reporting status";
                container enable {
                  presence "Indicates a enable node is configured.";
                  description
                    "Enable TCA reporting";
                }
              }
            }
            container lbc-pc {
              description
                "set lbc % TCA reporting status";
              container min-tca {
                description
                  "set lbc min % TCA reporting status";
                container enable {
                  presence "Indicates a enable node is configured.";
                  description
                    "Enable TCA reporting";
                }
              }
              container max-tca {
                description
                  "set lbc max % TCA reporting status";
                container enable {
                  presence "Indicates a enable node is configured.";
                  description
                    "Enable TCA reporting";
                }
              }
            }
            container sopmd {
              description
                "set second order polarization mode dispersion TCA reporting status";
              container min-tca {
                description
                  "set polarization mode dispersion min TCA reporting status";
                container enable {
                  presence "Indicates a enable node is configured.";
                  description
                    "Enable TCA reporting";
                }
              }
              container max-tca {
                description
                  "set polarization mode dispersion max TCA reporting status";
                container enable {
                  presence "Indicates a enable node is configured.";
                  description
                    "Enable TCA reporting";
                }
              }
            }
            container rx-sig-pow {
              description
                "set rx sig power TCA reporting status";
              container min-tca {
                description
                  "set rx sig power(uW/dBm) min TCA reporting status";
                container enable {
                  presence "Indicates a enable node is configured.";
                  description
                    "Enable TCA reporting";
                }
              }
              container max-tca {
                description
                  "set rx sig power(uW/dBm) max TCA reporting status";
                container enable {
                  presence "Indicates a enable node is configured.";
                  description
                    "Enable TCA reporting";
                }
              }
            }
            container low-freq-off {
              description
                "set low signal freq offset TCA reporting status";
              container min-tca {
                description
                  "set low signal freq offset min TCA reporting status";
                container enable {
                  presence "Indicates a enable node is configured.";
                  description
                    "Enable TCA reporting";
                }
              }
              container max-tca {
                description
                  "set low signal freq offset max TCA reporting status";
                container enable {
                  presence "Indicates a enable node is configured.";
                  description
                    "Enable TCA reporting";
                }
              }
            }
            container snr {
              description
                "set SNR TCA reporting status";
              container min-tca {
                description
                  "set SNR min TCA reporting status";
                container enable {
                  presence "Indicates a enable node is configured.";
                  description
                    "Enable TCA reporting";
                }
              }
              container max-tca {
                description
                  "set SNR max TCA reporting status";
                container enable {
                  presence "Indicates a enable node is configured.";
                  description
                    "Enable TCA reporting";
                }
              }
            }
            container snr-ax {
              description
                "set SNR-AX TCA reporting status";
              container min-tca {
                description
                  "set SNR-AX min TCA reporting status";
                container enable {
                  presence "Indicates a enable node is configured.";
                  description
                    "Enable TCA reporting";
                }
              }
              container max-tca {
                description
                  "set SNR-AX max TCA reporting status";
                container enable {
                  presence "Indicates a enable node is configured.";
                  description
                    "Enable TCA reporting";
                }
              }
            }
            container snr-bx {
              description
                "set SNR-BX TCA reporting status";
              container min-tca {
                description
                  "set SNR-BX min TCA reporting status";
                container enable {
                  presence "Indicates a enable node is configured.";
                  description
                    "Enable TCA reporting";
                }
              }
              container max-tca {
                description
                  "set SNR-BX max TCA reporting status";
                container enable {
                  presence "Indicates a enable node is configured.";
                  description
                    "Enable TCA reporting";
                }
              }
            }
            container snr-ay {
              description
                "set SNR-AY TCA reporting status";
              container min-tca {
                description
                  "set SNR-AY min TCA reporting status";
                container enable {
                  presence "Indicates a enable node is configured.";
                  description
                    "Enable TCA reporting";
                }
              }
              container max-tca {
                description
                  "set SNR-AY max TCA reporting status";
                container enable {
                  presence "Indicates a enable node is configured.";
                  description
                    "Enable TCA reporting";
                }
              }
            }
            container snr-by {
              description
                "set SNR-BY TCA reporting status";
              container min-tca {
                description
                  "set SNR-BY min TCA reporting status";
                container enable {
                  presence "Indicates a enable node is configured.";
                  description
                    "Enable TCA reporting";
                }
              }
              container max-tca {
                description
                  "set SNR-BY max TCA reporting status";
                container enable {
                  presence "Indicates a enable node is configured.";
                  description
                    "Enable TCA reporting";
                }
              }
            }
            container sop-s1 {
              description
                "set SOP-S1 TCA reporting status";
              container min-tca {
                description
                  "set SOP-S1 min TCA reporting status";
                container enable {
                  presence "Indicates a enable node is configured.";
                  description
                    "Enable TCA reporting";
                }
              }
              container max-tca {
                description
                  "set SOP-S1 max TCA reporting status";
                container enable {
                  presence "Indicates a enable node is configured.";
                  description
                    "Enable TCA reporting";
                }
              }
            }
            container sop-s2 {
              description
                "set SOP-S2 TCA reporting status";
              container min-tca {
                description
                  "set SOP-S2 min TCA reporting status";
                container enable {
                  presence "Indicates a enable node is configured.";
                  description
                    "Enable TCA reporting";
                }
              }
              container max-tca {
                description
                  "set SOP-S2 max TCA reporting status";
                container enable {
                  presence "Indicates a enable node is configured.";
                  description
                    "Enable TCA reporting";
                }
              }
            }
            container sop-s3 {
              description
                "set SOP-S3 TCA reporting status";
              container min-tca {
                description
                  "set SOP-S3 min TCA reporting status";
                container enable {
                  presence "Indicates a enable node is configured.";
                  description
                    "Enable TCA reporting";
                }
              }
              container max-tca {
                description
                  "set SOP-S3 max TCA reporting status";
                container enable {
                  presence "Indicates a enable node is configured.";
                  description
                    "Enable TCA reporting";
                }
              }
            }
          }
        }
        container fec {
          description
            "Configure fec g709 performance monitoring";
          container threshold {
            description
              "Configure fec threshold";
            leaf ec-bits {
              type xr:Cisco-ios-xr-string {
                length "1..20" {
                  description
                    "ec-bits threshold  <range:0-75279974400>";
                }
              }
              description
                "set EC-BITS threshold";
            }
            leaf uc-words {
              type xr:Cisco-ios-xr-string {
                length "1..20" {
                  description
                    "uc-words threshold <range:0-4724697600>";
                }
              }
              description
                "set UC-WORDS threshold";
            }
            container pre-fec-ber {
              description
                "Set PRE-FEC-BER Thresholds";
              leaf min {
                type xr:Cisco-ios-xr-string {
                  length "1..20" {
                    description
                      "pre-fec-ber min threshold range : <1-18446744073709551615>. BER is based on E-15, set value = 150, equivalent BER = 1.5E-13";
                  }
                }
                description
                  "set pre-fec-ber min threshold";
              }
              leaf max {
                type xr:Cisco-ios-xr-string {
                  length "1..20" {
                    description
                      "pre-fec-ber max threshold range : <1-18446744073709551615>. BER is based on E-15, set value = 150, equivalent BER = 1.5E-13";
                  }
                }
                description
                  "set pre-fec-ber max threshold";
              }
            }
            container post-fec-ber {
              description
                "Set POST-FEC-BER Thresholds";
              leaf min {
                type xr:Cisco-ios-xr-string {
                  length "1..20" {
                    description
                      "post-fec-ber min threshold range : <1-18446744073709551615>. BER is based on E-15, set value = 150, equivalent BER = 1.5E-13";
                  }
                }
                description
                  "set post-fec-ber min threshold";
              }
              leaf max {
                type xr:Cisco-ios-xr-string {
                  length "1..20" {
                    description
                      "post-fec-ber max threshold range : <1-18446744073709551615>. BER is based on E-15, set value = 150, equivalent BER = 1.5E-13";
                  }
                }
                description
                  "set post-fec-ber max threshold";
              }
            }
            container q {
              description
                "set Q threshold";
              leaf min {
                type xr:Cisco-ios-xr-string {
                  length "1..20" {
                    description
                      "Q min threshold <1-18446744073709551615>set value = 150, equivalent value = 1.5";
                  }
                }
                description
                  "set Q min threshold";
              }
              leaf max {
                type xr:Cisco-ios-xr-string {
                  length "1..20" {
                    description
                      "Q max threshold <1-18446744073709551615>set value = 150, equivalent value = 1.5";
                  }
                }
                description
                  "set Q max threshold";
              }
            }
            container q-margin {
              description
                "set Q margin threshold";
              leaf min {
                type xr:Cisco-ios-xr-string {
                  length "1..20" {
                    description
                      "Q margin min threshold <1-18446744073709551615>set value = 150, equivalent value = 1.5";
                  }
                }
                description
                  "set Q margin min threshold";
              }
              leaf max {
                type xr:Cisco-ios-xr-string {
                  length "1..20" {
                    description
                      "Q margin max threshold <1-18446744073709551615>set value = 150, equivalent value = 1.5";
                  }
                }
                description
                  "set Q margin max threshold";
              }
            }
            container inst-q-margin {
              description
                "set Instantaneous Q margin threshold";
              leaf min {
                type xr:Cisco-ios-xr-string {
                  length "1..20" {
                    description
                      "Instantaneous Q margin min threshold <1-18446744073709551615>set value = 150, equivalent value = 1.5";
                  }
                }
                description
                  "set Instantaneous Q margin min threshold";
              }
              leaf max {
                type xr:Cisco-ios-xr-string {
                  length "1..20" {
                    description
                      "Instantaneous Q margin max threshold <1-18446744073709551615>set value = 150, equivalent value = 1.5";
                  }
                }
                description
                  "set Instantaneous Q margin max threshold";
              }
            }
          }
          container report {
            description
              "set fec TCA reporting status";
            container ec-bits {
              description
                "set ec-bits TCA reporting status";
              container enable {
                presence "Indicates a enable node is configured.";
                description
                  "Enable TCA reporting";
              }
            }
            container uc-words {
              description
                "set uc-words TCA reporting status";
              container enable {
                presence "Indicates a enable node is configured.";
                description
                  "Enable TCA reporting";
              }
            }
          }
        }
        container otnsec {
          description
            "configure otnsec pm parameters";
          container threshold {
            description
              "configure threshold for otnsec pm parameters";
            leaf in-blocks {
              type xr:Cisco-ios-xr-string {
                length "1..20" {
                  description
                    "range : <1-18446744073709551615>";
                }
              }
              description
                "Configure threshold for total no. of odu blocks processed";
            }
            leaf in-blocks-enc {
              type xr:Cisco-ios-xr-string {
                length "1..20" {
                  description
                    "range : <1-18446744073709551615>";
                }
              }
              description
                "Configure threshold for total no. of encrypted blocks processed";
            }
            leaf in-blocks-un-encrypted {
              type xr:Cisco-ios-xr-string {
                length "1..20" {
                  description
                    "range : <1-18446744073709551615>";
                }
              }
              description
                "Configure threshold for total no. of un-encrypted blocks processed";
            }
            leaf in-blocks-protected {
              type xr:Cisco-ios-xr-string {
                length "1..20" {
                  description
                    "range : <1-18446744073709551615>";
                }
              }
              description
                "Configure threshold for total no. of Authenticated blocks processed";
            }
            leaf in-blocks-un-protected {
              type xr:Cisco-ios-xr-string {
                length "1..20" {
                  description
                    "range : <1-18446744073709551615>";
                }
              }
              description
                "Configure threshold for total no. of unAuthenticated blocks processed";
            }
            leaf in-blocks-sequence-errors {
              type xr:Cisco-ios-xr-string {
                length "1..20" {
                  description
                    "range : <1-18446744073709551615>";
                }
              }
              description
                "Configure threshold for Sequence Errors";
            }
            leaf in-blocks-replay-errors {
              type xr:Cisco-ios-xr-string {
                length "1..20" {
                  description
                    "range : <1-18446744073709551615>";
                }
              }
              description
                "Configure threshold for Replay Errors";
            }
            leaf in-blocks-auth-errors {
              type xr:Cisco-ios-xr-string {
                length "1..20" {
                  description
                    "range : <1-18446744073709551615>";
                }
              }
              description
                "Configure threshold for blocks which failed authentication check";
            }
            leaf in-blocks-zeroed {
              type xr:Cisco-ios-xr-string {
                length "1..20" {
                  description
                    "range : <1-18446744073709551615>";
                }
              }
              description
                "Configure threshold for Blocks which were zeroed due to some errors";
            }
            leaf out-blocks {
              type xr:Cisco-ios-xr-string {
                length "1..20" {
                  description
                    "range : <1-18446744073709551615>";
                }
              }
              description
                "Configure threshold for total number of ODU blocks processed";
            }
            leaf out-blocks-enc {
              type xr:Cisco-ios-xr-string {
                length "1..20" {
                  description
                    "range : <1-18446744073709551615>";
                }
              }
              description
                "Configure threshold for no. of encrypted blocks processed";
            }
            leaf out-blocks-un-encrypted {
              type xr:Cisco-ios-xr-string {
                length "1..20" {
                  description
                    "range : <1-18446744073709551615>";
                }
              }
              description
                "Configure threshold for no. of unencrypted blocks processed";
            }
            leaf out-blocks-sequence-errors {
              type xr:Cisco-ios-xr-string {
                length "1..20" {
                  description
                    "range : <1-18446744073709551615>";
                }
              }
              description
                "Configure threshold for sequence errors";
            }
            leaf out-blocks-zeroed {
              type xr:Cisco-ios-xr-string {
                length "1..20" {
                  description
                    "range : <1-18446744073709551615>";
                }
              }
              description
                "Configure threshold for blocks that were zeroed due to some errors";
            }
            leaf out-blocks-protected {
              type xr:Cisco-ios-xr-string {
                length "1..20" {
                  description
                    "range : <1-18446744073709551615>";
                }
              }
              description
                "Configure threshold for total no. of Authenticated blocks processed";
            }
            leaf out-blocks-un-protected {
              type xr:Cisco-ios-xr-string {
                length "1..20" {
                  description
                    "range : <1-18446744073709551615>";
                }
              }
              description
                "Configure threshold for total no. of unAuthenticated blocks processed";
            }
          }
          container report {
            description
              "Configure TCA report for otnsec parameters";
            container in-blocks {
              description
                "Set TCA report for Inblocks";
              container enable {
                presence "Indicates a enable node is configured.";
                description
                  "Enable TCA reporting";
              }
            }
            container in-blocks-enc {
              description
                "Set TCA report for InBlocksEnc";
              container enable {
                presence "Indicates a enable node is configured.";
                description
                  "Enable TCA reporting";
              }
            }
            container in-blocks-un-encrypted {
              description
                "Set TCA report for InBlocksUnEncrypted";
              container enable {
                presence "Indicates a enable node is configured.";
                description
                  "Enable TCA reporting";
              }
            }
            container in-blocks-protected {
              description
                "Set TCA report for InBlocksProtected";
              container enable {
                presence "Indicates a enable node is configured.";
                description
                  "Enable TCA reporting";
              }
            }
            container in-blocks-un-portected {
              description
                "Set TCA report for InBlocksUnPortected";
              container enable {
                presence "Indicates a enable node is configured.";
                description
                  "Enable TCA reporting";
              }
            }
            container in-blocks-sequence-errors {
              description
                "Set TCA report for InBlocksSequenceErrors";
              container enable {
                presence "Indicates a enable node is configured.";
                description
                  "Enable TCA reporting";
              }
            }
            container in-blocks-replay-errors {
              description
                "Set TCA report for InBlocksReplayErrors";
              container enable {
                presence "Indicates a enable node is configured.";
                description
                  "Enable TCA reporting";
              }
            }
            container in-blocks-auth-errors {
              description
                "Set TCA report for InBlocksAuthErrors";
              container enable {
                presence "Indicates a enable node is configured.";
                description
                  "Enable TCA reporting";
              }
            }
            container in-blocks-zeroed {
              description
                "Set TCA report for InBlocksZeroed";
              container enable {
                presence "Indicates a enable node is configured.";
                description
                  "Enable TCA reporting";
              }
            }
            container out-blocks {
              description
                "Set TCA report for OutBlocks";
              container enable {
                presence "Indicates a enable node is configured.";
                description
                  "Enable TCA reporting";
              }
            }
            container out-blocks-enc {
              description
                "Set TCA report for OutBlocksEnc";
              container enable {
                presence "Indicates a enable node is configured.";
                description
                  "Enable TCA reporting";
              }
            }
            container out-blocks-un-encrypted {
              description
                "Set TCA report for OutBlocksUnEncrypted";
              container enable {
                presence "Indicates a enable node is configured.";
                description
                  "Enable TCA reporting";
              }
            }
            container out-blocks-sequence-errors {
              description
                "Set TCA report for OutBlocksSequenceErrors";
              container enable {
                presence "Indicates a enable node is configured.";
                description
                  "Enable TCA reporting";
              }
            }
            container out-blocks-zeroed {
              description
                "Set TCA report for OutBlocksZeroed";
              container enable {
                presence "Indicates a enable node is configured.";
                description
                  "Enable TCA reporting";
              }
            }
            container out-blocks-protected {
              description
                "Set TCA report for OutBlocksProtected";
              container enable {
                presence "Indicates a enable node is configured.";
                description
                  "Enable TCA reporting";
              }
            }
            container out-blocks-un-portected {
              description
                "Set TCA report for OutBlocksUnPortected";
              container enable {
                presence "Indicates a enable node is configured.";
                description
                  "Enable TCA reporting";
              }
            }
          }
        }
        container gfp {
          description
            "Configure gfp performance monitoring";
          container threshold {
            description
              "Configure gfp threshold";
            leaf rx-bit-err {
              type uint32 {
                range "1..4294967295" {
                  description
                    "RX-BIT-ERR threshold";
                }
              }
              description
                "set RX-BIT-ERR threshold";
            }
            leaf rx-inv-type {
              type uint32 {
                range "1..4294967295" {
                  description
                    "RX-INV-TYP threshold";
                }
              }
              description
                "set RX-INV-TYP threshold";
            }
            leaf rx-crc-err {
              type uint32 {
                range "1..4294967295" {
                  description
                    "RX-CRC threshold";
                }
              }
              description
                "set RX-CRC threshold";
            }
            leaf rx-lfd-stats {
              type uint32 {
                range "1..4294967295" {
                  description
                    "RX-LFD threshold";
                }
              }
              description
                "set RX-LFD threshold";
            }
            leaf rx-csf-stats {
              type uint32 {
                range "1..4294967295" {
                  description
                    "RX-CSF threshold";
                }
              }
              description
                "set RX-CSF threshold";
            }
          }
          container report {
            description
              "set gfp TCA reporting status";
            container rx-bit-err {
              description
                "set rx-bit-err TCA reporting status";
              container enable {
                presence "Indicates a enable node is configured.";
                description
                  "Enable TCA reporting";
              }
            }
            container rx-inv-type {
              description
                "set rx-inv-type TCA reporting status";
              container enable {
                presence "Indicates a enable node is configured.";
                description
                  "Enable TCA reporting";
              }
            }
            container rx-crc-err {
              description
                "set rx-crc-err TCA reporting status";
              container enable {
                presence "Indicates a enable node is configured.";
                description
                  "Enable TCA reporting";
              }
            }
            container rx-lfd-stats {
              description
                "set rx-lfd-stats TCA reporting status";
              container enable {
                presence "Indicates a enable node is configured.";
                description
                  "Enable TCA reporting";
              }
            }
            container rx-csf-stats {
              description
                "set rx-csf-stats TCA reporting status";
              container enable {
                presence "Indicates a enable node is configured.";
                description
                  "Enable TCA reporting";
              }
            }
          }
        }
        container prbs {
          description
            "Configure prbs performance monitoring";
          container threshold {
            description
              "Configure prbs threshold";
            leaf ebc {
              type xr:Cisco-ios-xr-string {
                length "1..20" {
                  description
                    "ebc threshold <1-18446744073709551615>";
                }
              }
              description
                "set EBC threshold";
            }
            leaf found-count {
              type xr:Cisco-ios-xr-string {
                length "1..10" {
                  description
                    "found-count threshold <1-4294967295>";
                }
              }
              description
                "set FOUND-COUNT threshold";
            }
            leaf lost-count {
              type xr:Cisco-ios-xr-string {
                length "1..10" {
                  description
                    "lost-count threshold <1-4294967295>";
                }
              }
              description
                "set LOST-COUNT threshold";
            }
          }
          container report {
            description
              "set prbs TCA reporting status";
            container ebc {
              description
                "set ebc TCA reporting status";
              container enable {
                presence "Indicates a enable node is configured.";
                description
                  "Enable TCA reporting";
              }
            }
            container found-count {
              description
                "set found-count TCA reporting status";
              container enable {
                presence "Indicates a enable node is configured.";
                description
                  "Enable TCA reporting";
              }
            }
            container lost-count {
              description
                "set lost-count TCA reporting status";
              container enable {
                presence "Indicates a enable node is configured.";
                description
                  "Enable TCA reporting";
              }
            }
          }
        }
      }
      container interval-24-hour {
        if-feature "optics_cli_supp_check";
        description
          "Configure pm parameters of 24 hour interval";
        container otn {
          description
            "configure otn g709 performance monitoring";
          container threshold {
            description
              "Configure threshold on otn parameters";
            leaf es-pm-ne {
              type uint32 {
                range "0..86400" {
                  description
                    "es-pm threshold (seconds)";
                }
              }
              description
                "set ES-PM threshold";
            }
            leaf es-sm-ne {
              type uint32 {
                range "0..86400" {
                  description
                    "es-pm threshold (seconds)";
                }
              }
              description
                "set ES-SM threshold";
            }
            leaf esr-pm-ne {
              type uint32 {
                range "0..100000" {
                  description
                    "esr-pm threshold";
                }
              }
              description
                "set ESR-PM threshold";
            }
            leaf esr-sm-ne {
              type uint32 {
                range "0..100000" {
                  description
                    "esr-sm threshold";
                }
              }
              description
                "set ESR-SM threshold";
            }
            leaf ses-pm-ne {
              type uint32 {
                range "0..86400" {
                  description
                    "ses-pm threshold (seconds)";
                }
              }
              description
                "set SES-PM threshold";
            }
            leaf ses-sm-ne {
              type uint32 {
                range "0..86400" {
                  description
                    "ses-sm threshold (seconds)";
                }
              }
              description
                "set SES-SM threshold";
            }
            leaf sesr-pm-ne {
              type uint32 {
                range "0..100000" {
                  description
                    "sesr-pm threshold";
                }
              }
              description
                "set SESR-PM threshold";
            }
            leaf sesr-sm-ne {
              type uint32 {
                range "0..100000" {
                  description
                    "sesr-sm threshold";
                }
              }
              description
                "set SESR-PM threshold";
            }
            leaf uas-pm-ne {
              type uint32 {
                range "0..86400" {
                  description
                    "uas-pm threshold (seconds)";
                }
              }
              description
                "set UAS-PM threshold";
            }
            leaf uas-sm-ne {
              type uint32 {
                range "0..86400" {
                  description
                    "uas-sm threshold (seconds)";
                }
              }
              description
                "set UAS-SM threshold";
            }
            leaf bbe-pm-ne {
              type uint32 {
                range "0..849657600" {
                  description
                    "bbe-pm threshold";
                }
              }
              description
                "set BBE-PM threshold";
            }
            leaf bbe-sm-ne {
              type uint32 {
                range "0..849657600" {
                  description
                    "bbe-sm threshold";
                }
              }
              description
                "set BBE-SM threshold";
            }
            leaf bber-pm-ne {
              type uint32 {
                range "0..100000" {
                  description
                    "bber-pm threshold";
                }
              }
              description
                "set BBER-PM threshold";
            }
            leaf bber-sm-ne {
              type uint32 {
                range "0..100000" {
                  description
                    "bber-sm threshold";
                }
              }
              description
                "set BBER-SM threshold";
            }
            leaf fc-pm-ne {
              type uint32 {
                range "0..6912" {
                  description
                    "fc-pm threshold";
                }
              }
              description
                "set FC-PM threshold";
            }
            leaf fc-sm-ne {
              type uint32 {
                range "0..6912" {
                  description
                    "fc-pm threshold";
                }
              }
              description
                "set FC-SM threshold";
            }
            leaf es-pm-fe {
              type uint32 {
                range "0..86400" {
                  description
                    "es-pm threshold (seconds)";
                }
              }
              description
                "set ES-PM threshold";
            }
            leaf es-sm-fe {
              type uint32 {
                range "0..86400" {
                  description
                    "es-pm threshold (seconds)";
                }
              }
              description
                "set ES-SM threshold";
            }
            leaf esr-pm-fe {
              type uint32 {
                range "0..100000" {
                  description
                    "esr-pm threshold";
                }
              }
              description
                "set ESR-PM threshold";
            }
            leaf esr-sm-fe {
              type uint32 {
                range "0..100000" {
                  description
                    "esr-sm threshold";
                }
              }
              description
                "set ESR-SM threshold";
            }
            leaf ses-pm-fe {
              type uint32 {
                range "0..86400" {
                  description
                    "ses-pm threshold (seconds)";
                }
              }
              description
                "set SES-PM threshold";
            }
            leaf ses-sm-fe {
              type uint32 {
                range "0..86400" {
                  description
                    "ses-sm threshold (seconds)";
                }
              }
              description
                "set SES-SM threshold";
            }
            leaf sesr-pm-fe {
              type uint32 {
                range "0..100000" {
                  description
                    "sesr-pm threshold";
                }
              }
              description
                "set SESR-PM threshold";
            }
            leaf sesr-sm-fe {
              type uint32 {
                range "0..100000" {
                  description
                    "sesr-sm threshold";
                }
              }
              description
                "set SESR-PM threshold";
            }
            leaf uas-pm-fe {
              type uint32 {
                range "0..86400" {
                  description
                    "uas-pm threshold (seconds)";
                }
              }
              description
                "set UAS-PM threshold";
            }
            leaf uas-sm-fe {
              type uint32 {
                range "0..86400" {
                  description
                    "uas-sm threshold (seconds)";
                }
              }
              description
                "set UAS-SM threshold";
            }
            leaf bbe-pm-fe {
              type uint32 {
                range "0..849657600" {
                  description
                    "bbe-pm threshold";
                }
              }
              description
                "set BBE-PM threshold";
            }
            leaf bbe-sm-fe {
              type uint32 {
                range "0..849657600" {
                  description
                    "bbe-sm threshold";
                }
              }
              description
                "set BBE-SM threshold";
            }
            leaf bber-pm-fe {
              type uint32 {
                range "0..100000" {
                  description
                    "bber-pm threshold";
                }
              }
              description
                "set BBER-PM threshold";
            }
            leaf bber-sm-fe {
              type uint32 {
                range "0..100000" {
                  description
                    "bber-sm threshold";
                }
              }
              description
                "set BBER-SM threshold";
            }
            leaf fc-pm-fe {
              type uint32 {
                range "0..6912" {
                  description
                    "fc-pm threshold";
                }
              }
              description
                "set FC-PM threshold";
            }
            leaf fc-sm-fe {
              type uint32 {
                range "0..6912" {
                  description
                    "fc-pm threshold";
                }
              }
              description
                "set FC-SM threshold";
            }
            leaf es-ne {
              type uint32 {
                range "0..86400" {
                  description
                    "es-ne threshold (seconds)";
                }
              }
              description
                "set ES-NE threshold";
            }
            leaf esr-ne {
              type uint32 {
                range "0..100000" {
                  description
                    "esr-ne threshold[Ratio parameters range(0-1),eg. 75000 corresponds to 0.75]";
                }
              }
              description
                "set ESR-NE threshold";
            }
            leaf ses-ne {
              type uint32 {
                range "0..86400" {
                  description
                    "ses-ne threshold (seconds)";
                }
              }
              description
                "set SES-NE threshold";
            }
            leaf sesr-ne {
              type uint32 {
                range "0..100000" {
                  description
                    "sesr-ne threshold[Ratio parameters range(0-1),eg. 75000 corresponds to 0.75]";
                }
              }
              description
                "set SESR-NE threshold";
            }
            leaf uas-ne {
              type uint32 {
                range "0..86400" {
                  description
                    "uas-ne threshold (seconds)";
                }
              }
              description
                "set UAS-NE threshold";
            }
            leaf bbe-ne {
              type uint32 {
                range "0..849657600" {
                  description
                    "bbe-ne threshold";
                }
              }
              description
                "set BBE-NE threshold";
            }
            leaf bber-ne {
              type uint32 {
                range "0..100000" {
                  description
                    "bber-ne threshold[Ratio parameters range(0-1),eg. 75000 corresponds to 0.75]";
                }
              }
              description
                "set BBER-NE threshold";
            }
            leaf fc-ne {
              type uint32 {
                range "0..6912" {
                  description
                    "fc-ne threshold";
                }
              }
              description
                "set FC-NE threshold";
            }
            leaf es-fe {
              type uint32 {
                range "0..86400" {
                  description
                    "es-fe threshold (seconds)";
                }
              }
              description
                "set ES-FE threshold";
            }
            leaf esr-fe {
              type uint32 {
                range "0..100000" {
                  description
                    "esr-fe threshold[Ratio parameters range(0-1),eg. 75000 corresponds to 0.75]";
                }
              }
              description
                "set ESR-FE threshold";
            }
            leaf ses-fe {
              type uint32 {
                range "0..86400" {
                  description
                    "ses-fe threshold (seconds)";
                }
              }
              description
                "set SES-FE threshold";
            }
            leaf sesr-fe {
              type uint32 {
                range "0..100000" {
                  description
                    "sesr-fe threshold[Ratio parameters range(0-1),eg. 75000 corresponds to 0.75]";
                }
              }
              description
                "set SESR-FE threshold";
            }
            leaf uas-fe {
              type uint32 {
                range "0..86400" {
                  description
                    "uas-fe threshold (seconds)";
                }
              }
              description
                "set UAS-FE threshold";
            }
            leaf bbe-fe {
              type uint32 {
                range "0..849657600" {
                  description
                    "bbe-fe threshold";
                }
              }
              description
                "set BBE-FE threshold";
            }
            leaf bber-fe {
              type uint32 {
                range "0..100000" {
                  description
                    "bber-fe threshold[Ratio parameters range(0-1),eg. 75000 corresponds to 0.75]";
                }
              }
              description
                "set BBER-FE threshold";
            }
            leaf fc-fe {
              type uint32 {
                range "0..6912" {
                  description
                    "fc-fe threshold";
                }
              }
              description
                "set FC-FE threshold";
            }
          }
          container report {
            description
              "set otn TCA reporting status";
            container es-sm-ne {
              description
                "set es-sm TCA reporting status";
              container enable {
                presence "Indicates a enable node is configured.";
                description
                  "Enable TCA reporting";
              }
            }
            container ses-sm-ne {
              description
                "set ses-sm TCA reporting status";
              container enable {
                presence "Indicates a enable node is configured.";
                description
                  "Enable TCA reporting";
              }
            }
            container uas-sm-ne {
              description
                "set uas-sm TCA reporting status";
              container enable {
                presence "Indicates a enable node is configured.";
                description
                  "Enable TCA reporting";
              }
            }
            container bbe-sm-ne {
              description
                "set bbe-sm TCA reporting status";
              container enable {
                presence "Indicates a enable node is configured.";
                description
                  "Enable TCA reporting";
              }
            }
            container fc-sm-ne {
              description
                "set fc-sm TCA reporting status";
              container enable {
                presence "Indicates a enable node is configured.";
                description
                  "Enable TCA reporting";
              }
            }
            container esr-sm-ne {
              description
                "set esr-sm TCA reporting status";
              container enable {
                presence "Indicates a enable node is configured.";
                description
                  "Enable TCA reporting";
              }
            }
            container sesr-sm-ne {
              description
                "set sesr-sm TCA reporting status";
              container enable {
                presence "Indicates a enable node is configured.";
                description
                  "Enable TCA reporting";
              }
            }
            container bber-sm-ne {
              description
                "set bber-sm TCA reporting status";
              container enable {
                presence "Indicates a enable node is configured.";
                description
                  "Enable TCA reporting";
              }
            }
            container es-pm-ne {
              description
                "set es-pm TCA reporting status";
              container enable {
                presence "Indicates a enable node is configured.";
                description
                  "Enable TCA reporting";
              }
            }
            container ses-pm-ne {
              description
                "set ses-pm TCA reporting status";
              container enable {
                presence "Indicates a enable node is configured.";
                description
                  "Enable TCA reporting";
              }
            }
            container uas-pm-ne {
              description
                "set uas-pm TCA reporting status";
              container enable {
                presence "Indicates a enable node is configured.";
                description
                  "Enable TCA reporting";
              }
            }
            container bbe-pm-ne {
              description
                "set bbe-pm TCA reporting status";
              container enable {
                presence "Indicates a enable node is configured.";
                description
                  "Enable TCA reporting";
              }
            }
            container fc-pm-ne {
              description
                "set fc-pm TCA reporting status";
              container enable {
                presence "Indicates a enable node is configured.";
                description
                  "Enable TCA reporting";
              }
            }
            container esr-pm-ne {
              description
                "set esr-pm TCA reporting status";
              container enable {
                presence "Indicates a enable node is configured.";
                description
                  "Enable TCA reporting";
              }
            }
            container sesr-pm-ne {
              description
                "set sesr-pm TCA reporting status";
              container enable {
                presence "Indicates a enable node is configured.";
                description
                  "Enable TCA reporting";
              }
            }
            container bber-pm-ne {
              description
                "set bber-pm TCA reporting status";
              container enable {
                presence "Indicates a enable node is configured.";
                description
                  "Enable TCA reporting";
              }
            }
            container es-sm-fe {
              description
                "set es-sm TCA reporting status";
              container enable {
                presence "Indicates a enable node is configured.";
                description
                  "Enable TCA reporting";
              }
            }
            container ses-sm-fe {
              description
                "set ses-sm TCA reporting status";
              container enable {
                presence "Indicates a enable node is configured.";
                description
                  "Enable TCA reporting";
              }
            }
            container uas-sm-fe {
              description
                "set uas-sm TCA reporting status";
              container enable {
                presence "Indicates a enable node is configured.";
                description
                  "Enable TCA reporting";
              }
            }
            container bbe-sm-fe {
              description
                "set bbe-sm TCA reporting status";
              container enable {
                presence "Indicates a enable node is configured.";
                description
                  "Enable TCA reporting";
              }
            }
            container fc-sm-fe {
              description
                "set fc-sm TCA reporting status";
              container enable {
                presence "Indicates a enable node is configured.";
                description
                  "Enable TCA reporting";
              }
            }
            container esr-sm-fe {
              description
                "set esr-sm TCA reporting status";
              container enable {
                presence "Indicates a enable node is configured.";
                description
                  "Enable TCA reporting";
              }
            }
            container sesr-sm-fe {
              description
                "set sesr-sm TCA reporting status";
              container enable {
                presence "Indicates a enable node is configured.";
                description
                  "Enable TCA reporting";
              }
            }
            container bber-sm-fe {
              description
                "set bber-sm TCA reporting status";
              container enable {
                presence "Indicates a enable node is configured.";
                description
                  "Enable TCA reporting";
              }
            }
            container es-pm-fe {
              description
                "set es-pm TCA reporting status";
              container enable {
                presence "Indicates a enable node is configured.";
                description
                  "Enable TCA reporting";
              }
            }
            container ses-pm-fe {
              description
                "set ses-pm TCA reporting status";
              container enable {
                presence "Indicates a enable node is configured.";
                description
                  "Enable TCA reporting";
              }
            }
            container uas-pm-fe {
              description
                "set uas-pm TCA reporting status";
              container enable {
                presence "Indicates a enable node is configured.";
                description
                  "Enable TCA reporting";
              }
            }
            container bbe-pm-fe {
              description
                "set bbe-pm TCA reporting status";
              container enable {
                presence "Indicates a enable node is configured.";
                description
                  "Enable TCA reporting";
              }
            }
            container fc-pm-fe {
              description
                "set fc-pm TCA reporting status";
              container enable {
                presence "Indicates a enable node is configured.";
                description
                  "Enable TCA reporting";
              }
            }
            container esr-pm-fe {
              description
                "set esr-pm TCA reporting status";
              container enable {
                presence "Indicates a enable node is configured.";
                description
                  "Enable TCA reporting";
              }
            }
            container sesr-pm-fe {
              description
                "set sesr-pm TCA reporting status";
              container enable {
                presence "Indicates a enable node is configured.";
                description
                  "Enable TCA reporting";
              }
            }
            container bber-pm-fe {
              description
                "set bber-pm TCA reporting status";
              container enable {
                presence "Indicates a enable node is configured.";
                description
                  "Enable TCA reporting";
              }
            }
          }
          container pathmonitor {
            description
              "configure otn g709 performance monitoring";
            container threshold {
              description
                "Configure threshold on otn parameters";
              leaf es-ne {
                type uint32 {
                  range "0..86400" {
                    description
                      "es-pm threshold (seconds)";
                  }
                }
                description
                  "set ES-PM threshold";
              }
              leaf esr-ne {
                type uint32 {
                  range "0..100000" {
                    description
                      "esr-pm threshold[Ratio parameters range(0-1),eg. 75000 corresponds to 0.75]";
                  }
                }
                description
                  "set ESR-PM threshold";
              }
              leaf ses-ne {
                type uint32 {
                  range "0..86400" {
                    description
                      "ses-pm threshold (seconds)";
                  }
                }
                description
                  "set SES-PM threshold";
              }
              leaf sesr-ne {
                type uint32 {
                  range "0..100000" {
                    description
                      "sesr-pm threshold[Ratio parameters range(0-1),eg. 75000 corresponds to 0.75]";
                  }
                }
                description
                  "set SESR-PM threshold";
              }
              leaf uas-ne {
                type uint32 {
                  range "0..86400" {
                    description
                      "uas-pm threshold (seconds)";
                  }
                }
                description
                  "set UAS-PM threshold";
              }
              leaf bbe-ne {
                type uint32 {
                  range "0..849657600" {
                    description
                      "bbe-pm threshold";
                  }
                }
                description
                  "set BBE-PM threshold";
              }
              leaf bber-ne {
                type uint32 {
                  range "0..100000" {
                    description
                      "bber-pm threshold[Ratio parameters range(0-1),eg. 75000 corresponds to 0.75]";
                  }
                }
                description
                  "set BBER-PM threshold";
              }
              leaf fc-ne {
                type uint32 {
                  range "0..6912" {
                    description
                      "fc-pm threshold";
                  }
                }
                description
                  "set FC-PM threshold";
              }
              leaf es-fe {
                type uint32 {
                  range "0..86400" {
                    description
                      "es-pm threshold (seconds)";
                  }
                }
                description
                  "set ES-PM threshold";
              }
              leaf esr-fe {
                type uint32 {
                  range "0..100000" {
                    description
                      "esr-pm threshold[Ratio parameters range(0-1),eg. 75000 corresponds to 0.75]";
                  }
                }
                description
                  "set ESR-PM threshold";
              }
              leaf ses-fe {
                type uint32 {
                  range "0..86400" {
                    description
                      "ses-pm threshold (seconds)";
                  }
                }
                description
                  "set SES-PM threshold";
              }
              leaf sesr-fe {
                type uint32 {
                  range "0..100000" {
                    description
                      "sesr-pm threshold[Ratio parameters range(0-1),eg. 75000 corresponds to 0.75]";
                  }
                }
                description
                  "set SESR-PM threshold";
              }
              leaf uas-fe {
                type uint32 {
                  range "0..86400" {
                    description
                      "uas-pm threshold (seconds)";
                  }
                }
                description
                  "set UAS-PM threshold";
              }
              leaf bbe-fe {
                type uint32 {
                  range "0..849657600" {
                    description
                      "bbe-pm threshold";
                  }
                }
                description
                  "set BBE-PM threshold";
              }
              leaf bber-fe {
                type uint32 {
                  range "0..100000" {
                    description
                      "bber-pm threshold[Ratio parameters range(0-1),eg. 75000 corresponds to 0.75]";
                  }
                }
                description
                  "set BBER-PM threshold";
              }
              leaf fc-fe {
                type uint32 {
                  range "0..6912" {
                    description
                      "fc-pm threshold";
                  }
                }
                description
                  "set FC-PM threshold";
              }
            }
            container report {
              description
                "set otn TCA reporting status";
              container es-ne {
                description
                  "set es-pm TCA reporting status";
                container disable {
                  presence "Indicates a disable node is configured.";
                  description
                    "Disable TCA reporting";
                }
              }
              container ses-ne {
                description
                  "set ses-pm TCA reporting status";
                container disable {
                  presence "Indicates a disable node is configured.";
                  description
                    "Disable TCA reporting";
                }
              }
              container uas-ne {
                description
                  "set uas-pm TCA reporting status";
                container disable {
                  presence "Indicates a disable node is configured.";
                  description
                    "Disable TCA reporting";
                }
              }
              container bbe-ne {
                description
                  "set bbe-pm TCA reporting status";
                container disable {
                  presence "Indicates a disable node is configured.";
                  description
                    "Disable TCA reporting";
                }
              }
              container fc-ne {
                description
                  "set fc-pm TCA reporting status";
                container disable {
                  presence "Indicates a disable node is configured.";
                  description
                    "Disable TCA reporting";
                }
              }
              container esr-ne {
                description
                  "set esr-pm TCA reporting status";
                container disable {
                  presence "Indicates a disable node is configured.";
                  description
                    "Disable TCA reporting";
                }
              }
              container sesr-ne {
                description
                  "set sesr-pm TCA reporting status";
                container disable {
                  presence "Indicates a disable node is configured.";
                  description
                    "Disable TCA reporting";
                }
              }
              container bber-ne {
                description
                  "set bber-pm TCA reporting status";
                container disable {
                  presence "Indicates a disable node is configured.";
                  description
                    "Disable TCA reporting";
                }
              }
              container es-fe {
                description
                  "set es-pm TCA reporting status";
                container disable {
                  presence "Indicates a disable node is configured.";
                  description
                    "Disable TCA reporting";
                }
              }
              container ses-fe {
                description
                  "set ses-pm TCA reporting status";
                container disable {
                  presence "Indicates a disable node is configured.";
                  description
                    "Disable TCA reporting";
                }
              }
              container uas-fe {
                description
                  "set uas-pm TCA reporting status";
                container disable {
                  presence "Indicates a disable node is configured.";
                  description
                    "Disable TCA reporting";
                }
              }
              container bbe-fe {
                description
                  "set bbe-pm TCA reporting status";
                container disable {
                  presence "Indicates a disable node is configured.";
                  description
                    "Disable TCA reporting";
                }
              }
              container fc-fe {
                description
                  "set fc-pm TCA reporting status";
                container disable {
                  presence "Indicates a disable node is configured.";
                  description
                    "Disable TCA reporting";
                }
              }
              container esr-fe {
                description
                  "set esr-pm TCA reporting status";
                container disable {
                  presence "Indicates a disable node is configured.";
                  description
                    "Disable TCA reporting";
                }
              }
              container sesr-fe {
                description
                  "set sesr-pm TCA reporting status";
                container disable {
                  presence "Indicates a disable node is configured.";
                  description
                    "Disable TCA reporting";
                }
              }
              container bber-fe {
                description
                  "set bber-pm TCA reporting status";
                container disable {
                  presence "Indicates a disable node is configured.";
                  description
                    "Disable TCA reporting";
                }
              }
            }
          }
          container tcms {
            description
              "configure tcm performance monitoring";
            list tcm {
              key "channel-number";
              description
                "configure tcm performance monitoring";
              leaf channel-number {
                type uint32 {
                  range "1..6" {
                    description
                      " Channel Number";
                  }
                }
                description
                  "configure tcm performance monitoring";
              }
              container threshold {
                description
                  "Configure threshold on otn parameters";
                leaf es-ne {
                  type uint32 {
                    range "0..86400" {
                      description
                        "es-ne threshold (seconds)";
                    }
                  }
                  description
                    "set ES-NE threshold";
                }
                leaf esr-ne {
                  type uint32 {
                    range "0..100000" {
                      description
                        "esr-ne threshold[Ratio parameters range(0-1),eg. 75000 corresponds to 0.75]";
                    }
                  }
                  description
                    "set ESR-NE threshold";
                }
                leaf ses-ne {
                  type uint32 {
                    range "0..86400" {
                      description
                        "ses-ne threshold (seconds)";
                    }
                  }
                  description
                    "set SES-NE threshold";
                }
                leaf sesr-ne {
                  type uint32 {
                    range "0..100000" {
                      description
                        "sesr-ne threshold[Ratio parameters range(0-1),eg. 75000 corresponds to 0.75]";
                    }
                  }
                  description
                    "set SESR-NE threshold";
                }
                leaf uas-ne {
                  type uint32 {
                    range "0..86400" {
                      description
                        "uas-ne threshold (seconds)";
                    }
                  }
                  description
                    "set UAS-NE threshold";
                }
                leaf bbe-ne {
                  type uint32 {
                    range "0..849657600" {
                      description
                        "bbe-ne threshold";
                    }
                  }
                  description
                    "set BBE-NE threshold";
                }
                leaf bber-ne {
                  type uint32 {
                    range "0..100000" {
                      description
                        "bber-ne threshold[Ratio parameters range(0-1),eg. 75000 corresponds to 0.75]";
                    }
                  }
                  description
                    "set BBER-NE threshold";
                }
                leaf fc-ne {
                  type uint32 {
                    range "0..6912" {
                      description
                        "fc-ne threshold";
                    }
                  }
                  description
                    "set FC-NE threshold";
                }
                leaf es-fe {
                  type uint32 {
                    range "0..86400" {
                      description
                        "es-fe threshold (seconds)";
                    }
                  }
                  description
                    "set ES-FE threshold";
                }
                leaf esr-fe {
                  type uint32 {
                    range "0..100000" {
                      description
                        "esr-fe threshold[Ratio parameters range(0-1),eg. 75000 corresponds to 0.75]";
                    }
                  }
                  description
                    "set ESR-FE threshold";
                }
                leaf ses-fe {
                  type uint32 {
                    range "0..86400" {
                      description
                        "ses-fe threshold (seconds)";
                    }
                  }
                  description
                    "set SES-FE threshold";
                }
                leaf sesr-fe {
                  type uint32 {
                    range "0..100000" {
                      description
                        "sesr-fe threshold[Ratio parameters range(0-1),eg. 75000 corresponds to 0.75]";
                    }
                  }
                  description
                    "set SESR-FE threshold";
                }
                leaf uas-fe {
                  type uint32 {
                    range "0..86400" {
                      description
                        "uas-fe threshold (seconds)";
                    }
                  }
                  description
                    "set UAS-FE threshold";
                }
                leaf bbe-fe {
                  type uint32 {
                    range "0..849657600" {
                      description
                        "bbe-fe threshold";
                    }
                  }
                  description
                    "set BBE-FE threshold";
                }
                leaf bber-fe {
                  type uint32 {
                    range "0..100000" {
                      description
                        "bber-fe threshold[Ratio parameters range(0-1),eg. 75000 corresponds to 0.75]";
                    }
                  }
                  description
                    "set BBER-FE threshold";
                }
                leaf fc-fe {
                  type uint32 {
                    range "0..6912" {
                      description
                        "fc-fe threshold";
                    }
                  }
                  description
                    "set FC-FE threshold";
                }
              }
              container report {
                description
                  "set otn TCA reporting status";
                container es-fe {
                  description
                    "set es-fe TCA reporting status";
                  container disable {
                    presence "Indicates a disable node is configured.";
                    description
                      "Disable TCA reporting";
                  }
                }
                container ses-fe {
                  description
                    "set ses-fe TCA reporting status";
                  container disable {
                    presence "Indicates a disable node is configured.";
                    description
                      "Disable TCA reporting";
                  }
                }
                container uas-fe {
                  description
                    "set uas-fe TCA reporting status";
                  container disable {
                    presence "Indicates a disable node is configured.";
                    description
                      "Disable TCA reporting";
                  }
                }
                container bbe-fe {
                  description
                    "set bbe-fe TCA reporting status";
                  container disable {
                    presence "Indicates a disable node is configured.";
                    description
                      "Disable TCA reporting";
                  }
                }
                container fc-fe {
                  description
                    "set fc-fe TCA reporting status";
                  container disable {
                    presence "Indicates a disable node is configured.";
                    description
                      "Disable TCA reporting";
                  }
                }
                container esr-fe {
                  description
                    "set esr-fe TCA reporting status";
                  container disable {
                    presence "Indicates a disable node is configured.";
                    description
                      "Disable TCA reporting";
                  }
                }
                container sesr-fe {
                  description
                    "set sesr-fe TCA reporting status";
                  container disable {
                    presence "Indicates a disable node is configured.";
                    description
                      "Disable TCA reporting";
                  }
                }
                container bber-fe {
                  description
                    "set bber-fe TCA reporting status";
                  container disable {
                    presence "Indicates a disable node is configured.";
                    description
                      "Disable TCA reporting";
                  }
                }
                container es-ne {
                  description
                    "set es-ne TCA reporting status";
                  container disable {
                    presence "Indicates a disable node is configured.";
                    description
                      "Disable TCA reporting";
                  }
                }
                container ses-ne {
                  description
                    "set ses-ne TCA reporting status";
                  container disable {
                    presence "Indicates a disable node is configured.";
                    description
                      "Disable TCA reporting";
                  }
                }
                container uas-ne {
                  description
                    "set uas-ne TCA reporting status";
                  container disable {
                    presence "Indicates a disable node is configured.";
                    description
                      "Disable TCA reporting";
                  }
                }
                container bbe-ne {
                  description
                    "set bbe-ne TCA reporting status";
                  container disable {
                    presence "Indicates a disable node is configured.";
                    description
                      "Disable TCA reporting";
                  }
                }
                container fc-ne {
                  description
                    "set fc-ne TCA reporting status";
                  container disable {
                    presence "Indicates a disable node is configured.";
                    description
                      "Disable TCA reporting";
                  }
                }
                container esr-ne {
                  description
                    "set esr-ne TCA reporting status";
                  container disable {
                    presence "Indicates a disable node is configured.";
                    description
                      "Disable TCA reporting";
                  }
                }
                container sesr-ne {
                  description
                    "set sesr-ne TCA reporting status";
                  container disable {
                    presence "Indicates a disable node is configured.";
                    description
                      "Disable TCA reporting";
                  }
                }
                container bber-ne {
                  description
                    "set bber-ne TCA reporting status";
                  container disable {
                    presence "Indicates a disable node is configured.";
                    description
                      "Disable TCA reporting";
                  }
                }
              }
            }
          }
        }
        container optics {
          description
            "Configure optics performance monitoring";
          container threshold {
            description
              "Configure threshold on optics parameters";
            container lbc {
              description
                "set lbc threshold";
              leaf min {
                type uint32 {
                  range "1..4294967295" {
                    description
                      "lbc min threshold (mA)";
                  }
                }
                description
                  "set lbc min threshold";
              }
              leaf max {
                type uint32 {
                  range "1..4294967295" {
                    description
                      "lbc max threshold (mA)";
                  }
                }
                description
                  "set lbc max threshold";
              }
            }
            container opt {
              description
                "set opt threshold in uW";
              leaf min {
                type uint32 {
                  range "1..4294967295" {
                    description
                      "opt min threshold (uW) ";
                  }
                }
                description
                  "set opt min threshold in uW";
              }
              leaf max {
                type uint32 {
                  range "1..4294967295" {
                    description
                      "opt max threshold (uW) ";
                  }
                }
                description
                  "set opt max threshold in uW";
              }
            }
            container opr {
              description
                "set opr threshold in uW";
              leaf max {
                type uint32 {
                  range "1..4294967295" {
                    description
                      "opr max threshold (uW)";
                  }
                }
                description
                  "set opr max threshold in uW";
              }
              leaf min {
                type uint32 {
                  range "1..4294967295" {
                    description
                      "opr min threshold (uW)";
                  }
                }
                description
                  " set opr min threshold in uW";
              }
            }
            container dgd {
              description
                "set differential group delay threshold";
              leaf min {
                type uint32 {
                  range "1..4294967295" {
                    description
                      "differential group delay min threshold (1/100th of ps)";
                  }
                }
                description
                  "set differential group delay min threshold";
              }
              leaf max {
                type uint32 {
                  range "1..4294967295" {
                    description
                      "differential delay group max threshold (1/100th of ps)";
                  }
                }
                description
                  "set differential group delay max threshold";
              }
            }
            container pmd {
              description
                "set polarization mode dispersion threshold";
              leaf min {
                type uint32 {
                  range "1..4294967295" {
                    description
                      "polarization mode dispersion min threshold (ps^2)";
                  }
                }
                description
                  "set polarization mode dispersion min threshold";
              }
              leaf max {
                type uint32 {
                  range "1..4294967295" {
                    description
                      "polarization mode dispersion max threshold (ps^2)";
                  }
                }
                description
                  "set polarization mode dispersion max threshold";
              }
            }
            container osnr {
              description
                "set optical signal to noise ratio threshold";
              leaf min {
                type uint32 {
                  range "1..4294967295" {
                    description
                      "optical signal to noise ratio min threshold (1/100th of dB)";
                  }
                }
                description
                  "set optical signal to noise ratio min threshold";
              }
              leaf max {
                type uint32 {
                  range "1..4294967295" {
                    description
                      "optical signal to noise ratio max threshold (1/100th of dB)";
                  }
                }
                description
                  "set optical siganl to noise max threshold";
              }
            }
            container pdl {
              description
                "set polarization dependent loss threshold";
              leaf min {
                type uint32 {
                  range "1..4294967295" {
                    description
                      "polarization dependent loss min threshold (1/100th of dB)";
                  }
                }
                description
                  "set polarization dependent loss min threshold";
              }
              leaf max {
                type uint32 {
                  range "1..4294967295" {
                    description
                      "polarization dependent loss max threshold (1/100th of dB)";
                  }
                }
                description
                  "set polarization dependent loss max threshold";
              }
            }
            container pcr {
              description
                "set polarization change rate threshold";
              leaf min {
                type uint32 {
                  range "1..4294967295" {
                    description
                      "polarization change rate min threshold (rad/s)";
                  }
                }
                description
                  "set polarization change rate min threshold";
              }
              leaf max {
                type uint32 {
                  range "1..4294967295" {
                    description
                      "polarization change rate max threshold (rad/s)";
                  }
                }
                description
                  "set polarization change rate max threshold";
              }
            }
            container pn {
              description
                "set phase noise threshold";
              leaf min {
                type uint32 {
                  range "1..4294967295" {
                    description
                      "phase noise min threshold (dB)";
                  }
                }
                description
                  "set phase noise min threshold";
              }
              leaf max {
                type uint32 {
                  range "1..4294967295" {
                    description
                      "phase noise max threshold in (dB)";
                  }
                }
                description
                  "set phase noise max threshold";
              }
            }
            container cd {
              description
                "set chromatic dispersion threshold";
              leaf min {
                type union {
                  type int32 {
                    range "-70000..70000" {
                      description
                        "chromatic dispersion min threshold (ps/nm)";
                    }
                  }
                  type int32 {
                    range "-350000..350000" {
                      description
                        "chromatic dispersion min threshold (ps/nm)";
                    }
                  }
                }
                description
                  "set chromatic dispersion min threshold";
              }
              leaf max {
                type union {
                  type int32 {
                    range "-70000..70000" {
                      description
                        "chromatic dispersion max threshold (ps/nm)";
                    }
                  }
                  type int32 {
                    range "-350000..350000" {
                      description
                        "chromatic dispersion max threshold (ps/nm)";
                    }
                  }
                }
                description
                  "set chromatic dispersion max threshold";
              }
            }
            container opt-dbm {
              description
                "set opt min threshold value in dbm";
              leaf min {
                type int32 {
                  range "-3000..6633" {
                    description
                      "Enter 4 digit value ;Input value 3000 for 30.00dbm";
                  }
                }
                description
                  "Set opt min threshold in dbm";
              }
              leaf max {
                type int32 {
                  range "-3000..6633" {
                    description
                      "Enter 4 digit value ;Input value 3000 for 30.00dbm";
                  }
                }
                description
                  "set opt max threshold";
              }
            }
            container opr-dbm {
              description
                "set opr min threshold value in dbm";
              leaf min {
                type int32 {
                  range "-3000..6633" {
                    description
                      "Enter 4 digit value ;Input value 3000 for 30.00dbm";
                  }
                }
                description
                  "Set opr min threshold in dbm";
              }
              leaf max {
                type int32 {
                  range "-3000..6633" {
                    description
                      "Enter 4 digit value ;Input value 3000 for 30.00dbm";
                  }
                }
                description
                  "set opr max threshold in dbm";
              }
            }
            container lbc-pc {
              description
                "set lbc % threshold";
              leaf min {
                type uint32 {
                  range "0..1000" {
                    description
                      "lbc min threshold (in units of 0.1%)";
                  }
                }
                description
                  "set lbc % min threshold";
              }
              leaf max {
                type uint32 {
                  range "0..1000" {
                    description
                      "lbc max threshold (in units of 0.1%)";
                  }
                }
                description
                  "set lbc % max threshold";
              }
            }
            container sopmd {
              description
                "set second order polarization mode dispersion threshold";
              leaf min {
                type uint32 {
                  range "1..4294967295" {
                    description
                      "polarization mode dispersion min threshold (in units of 0.01 ps^2)";
                  }
                }
                description
                  "set polarization mode dispersion min threshold";
              }
              leaf max {
                type uint32 {
                  range "1..4294967295" {
                    description
                      "polarization mode dispersion max threshold (in units of 0.01 ps^2)";
                  }
                }
                description
                  "set polarization mode dispersion max threshold";
              }
            }
            container rx-sig-pow {
              description
                "set rx sig power threshold in uW";
              leaf min {
                type uint32 {
                  range "1..4294967295" {
                    description
                      " rx sig power threshold in uW";
                  }
                }
                description
                  "rx sig power min threshold in uW ";
              }
              leaf max {
                type uint32 {
                  range "1..4294967295" {
                    description
                      "rx sig power max threshold in uW";
                  }
                }
                description
                  "set rx sig power max threshold in uW";
              }
            }
            container snr {
              description
                "set SNR threshold";
              leaf min {
                type uint32 {
                  range "1..2147483646" {
                    description
                      "SNR min threshold";
                  }
                }
                description
                  "set SNR min threshold ";
              }
              leaf max {
                type uint32 {
                  range "1..2147483646" {
                    description
                      "SNR max threshold ";
                  }
                }
                description
                  "set SNR max threshold ";
              }
            }
            container snr-ax {
              description
                "set SNR AX threshold";
              leaf min {
                type uint32 {
                  range "1..2147483646" {
                    description
                      "SNR AX min threshold";
                  }
                }
                description
                  "set SNR AX min threshold ";
              }
              leaf max {
                type uint32 {
                  range "1..2147483646" {
                    description
                      "SNR AX max threshold ";
                  }
                }
                description
                  "set SNR AX max threshold ";
              }
            }
            container snr-bx {
              description
                "set SNR BX threshold";
              leaf min {
                type uint32 {
                  range "1..2147483646" {
                    description
                      "SNR BX min threshold";
                  }
                }
                description
                  "set SNR BX min threshold ";
              }
              leaf max {
                type uint32 {
                  range "1..2147483646" {
                    description
                      "SNR BX max threshold ";
                  }
                }
                description
                  "set SNR BX max threshold ";
              }
            }
            container snr-ay {
              description
                "set SNR AY threshold";
              leaf min {
                type uint32 {
                  range "1..2147483646" {
                    description
                      "SNR AY min threshold";
                  }
                }
                description
                  "set SNR AY min threshold ";
              }
              leaf max {
                type uint32 {
                  range "1..2147483646" {
                    description
                      "SNR AY max threshold ";
                  }
                }
                description
                  "set SNR AY max threshold ";
              }
            }
            container snr-by {
              description
                "set SNR BY threshold";
              leaf min {
                type uint32 {
                  range "1..2147483646" {
                    description
                      "SNR BY min threshold";
                  }
                }
                description
                  "set SNR BY min threshold ";
              }
              leaf max {
                type uint32 {
                  range "1..2147483646" {
                    description
                      "SNR BY max threshold ";
                  }
                }
                description
                  "set SNR BY max threshold ";
              }
            }
            container rx-sig-pow-dbm {
              description
                "set rx-sig-pow threshold in dbm";
              leaf min {
                type int32 {
                  range "-3000..6633" {
                    description
                      "Enter 4 digit value ;Input value 3000 for 30.00dbm";
                  }
                }
                description
                  "set rx-sig-pow min threshold in dbm";
              }
              leaf max {
                type int32 {
                  range "-3000..6633" {
                    description
                      "Enter 4 digit value ;Input value 3000 for 30.00dbm";
                  }
                }
                description
                  "set rx-sig-pow max threshold in dbm";
              }
            }
            container low-freq-off {
              description
                "set low signal freq offset threshold in Mhz";
              leaf min {
                type int32 {
                  range "-1500..1500" {
                    description
                      "low signal freq offset min threshold in Mhz";
                  }
                }
                description
                  "set low signal freq offset min threshold in Mhz";
              }
              leaf max {
                type int32 {
                  range "-1500..1500" {
                    description
                      "low signal freq offset max threshold in Mhz";
                  }
                }
                description
                  "set low signal freq offset max threshold in Mhz";
              }
            }
            container sop-s1 {
              description
                "set SOP S1 threshold ";
              leaf min {
                type int32 {
                  range "-100..100" {
                    description
                      "SOP S1 threshold ";
                  }
                }
                description
                  "set SOP S1 min threshold ";
              }
              leaf max {
                type int32 {
                  range "-100..100" {
                    description
                      "SOP S1 max threshold ";
                  }
                }
                description
                  "set SOP S1 max threshold ";
              }
            }
            container sop-s2 {
              description
                "set SOP S2 threshold ";
              leaf min {
                type int32 {
                  range "-100..100" {
                    description
                      "SOP S2 threshold ";
                  }
                }
                description
                  "set SOP S2 min threshold ";
              }
              leaf max {
                type int32 {
                  range "-100..100" {
                    description
                      "SOP S2 max threshold ";
                  }
                }
                description
                  "set SOP S2 max threshold ";
              }
            }
            container sop-s3 {
              description
                "set SOP S3 threshold ";
              leaf min {
                type int32 {
                  range "-100..100" {
                    description
                      "SOP S3 threshold ";
                  }
                }
                description
                  "set SOP S3 min threshold ";
              }
              leaf max {
                type int32 {
                  range "-100..100" {
                    description
                      "SOP S3 max threshold ";
                  }
                }
                description
                  "set SOP S3 max threshold ";
              }
            }
          }
          container report {
            description
              "set optics TCA reporting status";
            container lbc {
              description
                "set lbc TCA reporting status";
              container min-tca {
                description
                  "set lbc min TCA reporting status";
                container enable {
                  presence "Indicates a enable node is configured.";
                  description
                    "Enable TCA reporting";
                }
              }
              container max-tca {
                description
                  "set lbc max TCA reporting status";
                container enable {
                  presence "Indicates a enable node is configured.";
                  description
                    "Enable TCA reporting";
                }
              }
            }
            container opt {
              description
                "set opt TCA reporting status";
              container min-tca {
                description
                  "set opt min TCA reporting status";
                container enable {
                  presence "Indicates a enable node is configured.";
                  description
                    "Enable TCA reporting";
                }
              }
              container max-tca {
                description
                  "set opt max TCA reporting status";
                container enable {
                  presence "Indicates a enable node is configured.";
                  description
                    "Enable TCA reporting";
                }
              }
            }
            container opr {
              description
                "set opr TCA reporting status";
              container min-tca {
                description
                  "set opr min TCA reporting status";
                container enable {
                  presence "Indicates a enable node is configured.";
                  description
                    "Enable TCA reporting";
                }
              }
              container max-tca {
                description
                  "set opr max TCA reporting status";
                container enable {
                  presence "Indicates a enable node is configured.";
                  description
                    "Enable TCA reporting";
                }
              }
            }
            container cd {
              description
                "set chromatic dispersion TCA reporting status";
              container min-tca {
                description
                  "set chromatic dispersion min TCA reporting status";
                container enable {
                  presence "Indicates a enable node is configured.";
                  description
                    "Enable TCA reporting";
                }
              }
              container max-tca {
                description
                  "set chromatic dispersion max TCA reporting status";
                container enable {
                  presence "Indicates a enable node is configured.";
                  description
                    "Enable TCA reporting";
                }
              }
            }
            container dgd {
              description
                "set differential group delay TCA reporting status";
              container min-tca {
                description
                  "set differentail group delay min TCA reporting status";
                container enable {
                  presence "Indicates a enable node is configured.";
                  description
                    "Enable TCA reporting";
                }
              }
              container max-tca {
                description
                  "set differential group delay max TCA reporting status";
                container enable {
                  presence "Indicates a enable node is configured.";
                  description
                    "Enable TCA reporting";
                }
              }
            }
            container pmd {
              description
                "set polarization mode dispersion TCA reporting status";
              container min-tca {
                description
                  "set polarization mode dispersion min TCA reporting status";
                container enable {
                  presence "Indicates a enable node is configured.";
                  description
                    "Enable TCA reporting";
                }
              }
              container max-tca {
                description
                  "set polarization mode dispersion max TCA reporting status";
                container enable {
                  presence "Indicates a enable node is configured.";
                  description
                    "Enable TCA reporting";
                }
              }
            }
            container sopmd {
              description
                "set second order polarization mode dispersion TCA reporting status";
              container min-tca {
                description
                  "set second order polarization mode dispersion min TCA reporting status";
                container enable {
                  presence "Indicates a enable node is configured.";
                  description
                    "Enable TCA reporting";
                }
              }
              container max-tca {
                description
                  "set polarization mode dispersion max TCA reporting status";
                container enable {
                  presence "Indicates a enable node is configured.";
                  description
                    "Enable TCA reporting";
                }
              }
            }
            container osnr {
              description
                "set optical signal to noise ratio TCA reporting status";
              container min-tca {
                description
                  "set optical signal to noise ratio min TCA reporting status";
                container enable {
                  presence "Indicates a enable node is configured.";
                  description
                    "Enable TCA reporting";
                }
              }
              container max-tca {
                description
                  "set optical signal to noise ratio max TCA reporting status";
                container enable {
                  presence "Indicates a enable node is configured.";
                  description
                    "Enable TCA reporting";
                }
              }
            }
            container pdl {
              description
                "set polarization dependent loss TCA reporting status";
              container min-tca {
                description
                  "set polarization dependent loss min TCA reporting status";
                container enable {
                  presence "Indicates a enable node is configured.";
                  description
                    "Enable TCA reporting";
                }
              }
              container max-tca {
                description
                  "set polarization dependent loss max TCA reporting status";
                container enable {
                  presence "Indicates a enable node is configured.";
                  description
                    "Enable TCA reporting";
                }
              }
            }
            container pcr {
              description
                "set polarization state change TCA reporting status";
              container min-tca {
                description
                  "set polarization state change min TCA reporting status";
                container enable {
                  presence "Indicates a enable node is configured.";
                  description
                    "Enable TCA reporting";
                }
              }
              container max-tca {
                description
                  "set polarization state change max TCA reporting status";
                container enable {
                  presence "Indicates a enable node is configured.";
                  description
                    "Enable TCA reporting";
                }
              }
            }
            container pn {
              description
                "set phase noise TCA reporting status";
              container min-tca {
                description
                  "set phase noise min TCA reporting status";
                container enable {
                  presence "Indicates a enable node is configured.";
                  description
                    "Enable TCA reporting";
                }
              }
              container max-tca {
                description
                  "set phase noise max TCA reporting status";
                container enable {
                  presence "Indicates a enable node is configured.";
                  description
                    "Enable TCA reporting";
                }
              }
            }
            container lbc-pc {
              description
                "set lbc % TCA reporting status";
              container min-tca {
                description
                  "set lbc min % TCA reporting status";
                container enable {
                  presence "Indicates a enable node is configured.";
                  description
                    "Enable TCA reporting";
                }
              }
              container max-tca {
                description
                  "set lbc max % TCA reporting status";
                container enable {
                  presence "Indicates a enable node is configured.";
                  description
                    "Enable TCA reporting";
                }
              }
            }
            container rx-sig-pow {
              description
                "set rx sig power TCA reporting status";
              container min-tca {
                description
                  "set rx sig power(uW/dBm) min TCA reporting status";
                container enable {
                  presence "Indicates a enable node is configured.";
                  description
                    "Enable TCA reporting";
                }
              }
              container max-tca {
                description
                  "set rx sig power(uW/dBm) max TCA reporting status";
                container enable {
                  presence "Indicates a enable node is configured.";
                  description
                    "Enable TCA reporting";
                }
              }
            }
            container low-freq-off {
              description
                "set low signal freq offset TCA reporting status";
              container min-tca {
                description
                  "set low signal freq offset min TCA reporting status";
                container enable {
                  presence "Indicates a enable node is configured.";
                  description
                    "Enable TCA reporting";
                }
              }
              container max-tca {
                description
                  "set low signal freq offset max TCA reporting status";
                container enable {
                  presence "Indicates a enable node is configured.";
                  description
                    "Enable TCA reporting";
                }
              }
            }
            container snr {
              description
                "set SNR TCA reporting status";
              container min-tca {
                description
                  "set SNR min TCA reporting status";
                container enable {
                  presence "Indicates a enable node is configured.";
                  description
                    "Enable TCA reporting";
                }
              }
              container max-tca {
                description
                  "set SNR max TCA reporting status";
                container enable {
                  presence "Indicates a enable node is configured.";
                  description
                    "Enable TCA reporting";
                }
              }
            }
            container snr-ax {
              description
                "set SNR-AX TCA reporting status";
              container min-tca {
                description
                  "set SNR-AX min TCA reporting status";
                container enable {
                  presence "Indicates a enable node is configured.";
                  description
                    "Enable TCA reporting";
                }
              }
              container max-tca {
                description
                  "set SNR-AX max TCA reporting status";
                container enable {
                  presence "Indicates a enable node is configured.";
                  description
                    "Enable TCA reporting";
                }
              }
            }
            container snr-bx {
              description
                "set SNR-BX TCA reporting status";
              container min-tca {
                description
                  "set SNR-BX min TCA reporting status";
                container enable {
                  presence "Indicates a enable node is configured.";
                  description
                    "Enable TCA reporting";
                }
              }
              container max-tca {
                description
                  "set SNR-BX max TCA reporting status";
                container enable {
                  presence "Indicates a enable node is configured.";
                  description
                    "Enable TCA reporting";
                }
              }
            }
            container snr-ay {
              description
                "set SNR-AY TCA reporting status";
              container min-tca {
                description
                  "set SNR-AY min TCA reporting status";
                container enable {
                  presence "Indicates a enable node is configured.";
                  description
                    "Enable TCA reporting";
                }
              }
              container max-tca {
                description
                  "set SNR-AY max TCA reporting status";
                container enable {
                  presence "Indicates a enable node is configured.";
                  description
                    "Enable TCA reporting";
                }
              }
            }
            container snr-by {
              description
                "set SNR-BY TCA reporting status";
              container min-tca {
                description
                  "set SNR-BY min TCA reporting status";
                container enable {
                  presence "Indicates a enable node is configured.";
                  description
                    "Enable TCA reporting";
                }
              }
              container max-tca {
                description
                  "set SNR-BY max TCA reporting status";
                container enable {
                  presence "Indicates a enable node is configured.";
                  description
                    "Enable TCA reporting";
                }
              }
            }
            container sop-s1 {
              description
                "set SOP-S1 TCA reporting status";
              container min-tca {
                description
                  "set SOP-S1 min TCA reporting status";
                container enable {
                  presence "Indicates a enable node is configured.";
                  description
                    "Enable TCA reporting";
                }
              }
              container max-tca {
                description
                  "set SOP-S1 max TCA reporting status";
                container enable {
                  presence "Indicates a enable node is configured.";
                  description
                    "Enable TCA reporting";
                }
              }
            }
            container sop-s2 {
              description
                "set SOP-S2 TCA reporting status";
              container min-tca {
                description
                  "set SOP-S2 min TCA reporting status";
                container enable {
                  presence "Indicates a enable node is configured.";
                  description
                    "Enable TCA reporting";
                }
              }
              container max-tca {
                description
                  "set SOP-S2 max TCA reporting status";
                container enable {
                  presence "Indicates a enable node is configured.";
                  description
                    "Enable TCA reporting";
                }
              }
            }
            container sop-s3 {
              description
                "set SOP-S3 TCA reporting status";
              container min-tca {
                description
                  "set SOP-S3 min TCA reporting status";
                container enable {
                  presence "Indicates a enable node is configured.";
                  description
                    "Enable TCA reporting";
                }
              }
              container max-tca {
                description
                  "set SOP-S3 max TCA reporting status";
                container enable {
                  presence "Indicates a enable node is configured.";
                  description
                    "Enable TCA reporting";
                }
              }
            }
          }
        }
        container fec {
          description
            "Configure fec g709 performance monitoring";
          container threshold {
            description
              "Configure fec threshold";
            leaf ec-bits {
              type xr:Cisco-ios-xr-string {
                length "1..20" {
                  description
                    "ec-bits threshold  <range:0-75279974400>";
                }
              }
              description
                "set EC-BITS threshold";
            }
            leaf uc-words {
              type xr:Cisco-ios-xr-string {
                length "1..20" {
                  description
                    "uc-words threshold <range:0-453570969600>";
                }
              }
              description
                "set UC-WORDS threshold";
            }
            container pre-fec-ber {
              description
                "Set PRE-FEC-BER Thresholds";
              leaf min {
                type xr:Cisco-ios-xr-string {
                  length "1..20" {
                    description
                      "pre-fec-ber min threshold range : <1-18446744073709551615>. BER is based on E-15, set value = 150, equivalent BER = 1.5E-13";
                  }
                }
                description
                  "set pre-fec-ber min threshold";
              }
              leaf max {
                type xr:Cisco-ios-xr-string {
                  length "1..20" {
                    description
                      "pre-fec-ber max threshold range : <1-18446744073709551615>. BER is based on E-15, set value = 150, equivalent BER = 1.5E-13";
                  }
                }
                description
                  "set pre-fec-ber max threshold";
              }
            }
            container post-fec-ber {
              description
                "Set POST-FEC-BER Thresholds";
              leaf min {
                type xr:Cisco-ios-xr-string {
                  length "1..20" {
                    description
                      "post-fec-ber min threshold range : <1-18446744073709551615>. BER is based on E-15, set value = 150, equivalent BER = 1.5E-13";
                  }
                }
                description
                  "set post-fec-ber min threshold";
              }
              leaf max {
                type xr:Cisco-ios-xr-string {
                  length "1..20" {
                    description
                      "post-fec-ber max threshold range : <1-18446744073709551615>. BER is based on E-15, set value = 150, equivalent BER = 1.5E-13";
                  }
                }
                description
                  "set post-fec-ber max threshold";
              }
            }
            container q {
              description
                "set Q threshold";
              leaf min {
                type xr:Cisco-ios-xr-string {
                  length "1..20" {
                    description
                      "Q min threshold <1-18446744073709551615>set value = 150, equivalent value = 1.5";
                  }
                }
                description
                  "set Q min threshold";
              }
              leaf max {
                type xr:Cisco-ios-xr-string {
                  length "1..20" {
                    description
                      "Q max threshold <1-18446744073709551615>set value = 150, equivalent value = 1.5";
                  }
                }
                description
                  "set Q max threshold";
              }
            }
            container q-margin {
              description
                "set Q margin threshold";
              leaf min {
                type xr:Cisco-ios-xr-string {
                  length "1..20" {
                    description
                      "Q margin min threshold <1-18446744073709551615>set value = 150, equivalent value = 1.5";
                  }
                }
                description
                  "set Q margin min threshold";
              }
              leaf max {
                type xr:Cisco-ios-xr-string {
                  length "1..20" {
                    description
                      "Q margin max threshold <1-18446744073709551615>set value = 150, equivalent value = 1.5";
                  }
                }
                description
                  "set Q margin max threshold";
              }
            }
            container inst-q-margin {
              description
                "set Instantaneous Q margin threshold";
              leaf min {
                type xr:Cisco-ios-xr-string {
                  length "1..20" {
                    description
                      "Instantaneous Q margin min threshold <1-18446744073709551615>set value = 150, equivalent value = 1.5";
                  }
                }
                description
                  "set Instantaneous Q margin min threshold";
              }
              leaf max {
                type xr:Cisco-ios-xr-string {
                  length "1..20" {
                    description
                      "Instantaneous Q margin max threshold <1-18446744073709551615>set value = 150, equivalent value = 1.5";
                  }
                }
                description
                  "set Instantaneous Q margin max threshold";
              }
            }
          }
          container report {
            description
              "set fec TCA reporting status";
            container ec-bits {
              description
                "set ec-bits TCA reporting status";
              container enable {
                presence "Indicates a enable node is configured.";
                description
                  "Enable TCA reporting";
              }
            }
            container uc-words {
              description
                "set uc-words TCA reporting status";
              container enable {
                presence "Indicates a enable node is configured.";
                description
                  "Enable TCA reporting";
              }
            }
          }
        }
        container otnsec {
          description
            "configure otnsec pm parameters";
          container threshold {
            description
              "configure threshold for otnsec pm parameters";
            leaf in-blocks {
              type xr:Cisco-ios-xr-string {
                length "1..20" {
                  description
                    "range : <1-18446744073709551615>";
                }
              }
              description
                "Configure threshold for total no. of odu blocks processed";
            }
            leaf in-blocks-enc {
              type xr:Cisco-ios-xr-string {
                length "1..20" {
                  description
                    "range : <1-18446744073709551615>";
                }
              }
              description
                "Configure threshold for total no. of encrypted blocks processed";
            }
            leaf in-blocks-un-encrypted {
              type xr:Cisco-ios-xr-string {
                length "1..20" {
                  description
                    "range : <1-18446744073709551615>";
                }
              }
              description
                "Configure threshold for total no. of un-encrypted blocks processed";
            }
            leaf in-blocks-protected {
              type xr:Cisco-ios-xr-string {
                length "1..20" {
                  description
                    "range : <1-18446744073709551615>";
                }
              }
              description
                "Configure threshold for total no. of Authenticated blocks processed";
            }
            leaf in-blocks-un-protected {
              type xr:Cisco-ios-xr-string {
                length "1..20" {
                  description
                    "range : <1-18446744073709551615>";
                }
              }
              description
                "Configure threshold for total no. of unAuthenticated blocks processed";
            }
            leaf in-blocks-sequence-errors {
              type xr:Cisco-ios-xr-string {
                length "1..20" {
                  description
                    "range : <1-18446744073709551615>";
                }
              }
              description
                "Configure threshold for Sequence Errors";
            }
            leaf in-blocks-replay-errors {
              type xr:Cisco-ios-xr-string {
                length "1..20" {
                  description
                    "range : <1-18446744073709551615>";
                }
              }
              description
                "Configure threshold for Replay Errors";
            }
            leaf in-blocks-auth-errors {
              type xr:Cisco-ios-xr-string {
                length "1..20" {
                  description
                    "range : <1-18446744073709551615>";
                }
              }
              description
                "Configure threshold for blocks which failed authentication check";
            }
            leaf in-blocks-zeroed {
              type xr:Cisco-ios-xr-string {
                length "1..20" {
                  description
                    "range : <1-18446744073709551615>";
                }
              }
              description
                "Configure threshold for Blocks which were zeroed due to some errors";
            }
            leaf out-blocks {
              type xr:Cisco-ios-xr-string {
                length "1..20" {
                  description
                    "range : <1-18446744073709551615>";
                }
              }
              description
                "Configure threshold for total number of ODU blocks processed";
            }
            leaf out-blocks-enc {
              type xr:Cisco-ios-xr-string {
                length "1..20" {
                  description
                    "range : <1-18446744073709551615>";
                }
              }
              description
                "Configure threshold for no. of encrypted blocks processed";
            }
            leaf out-blocks-un-encrypted {
              type xr:Cisco-ios-xr-string {
                length "1..20" {
                  description
                    "range : <1-18446744073709551615>";
                }
              }
              description
                "Configure threshold for no. of unencrypted blocks processed";
            }
            leaf out-blocks-sequence-errors {
              type xr:Cisco-ios-xr-string {
                length "1..20" {
                  description
                    "range : <1-18446744073709551615>";
                }
              }
              description
                "Configure threshold for sequence errors";
            }
            leaf out-blocks-zeroed {
              type xr:Cisco-ios-xr-string {
                length "1..20" {
                  description
                    "range : <1-18446744073709551615>";
                }
              }
              description
                "Configure threshold for blocks that were zeroed due to some errors";
            }
            leaf out-blocks-protected {
              type xr:Cisco-ios-xr-string {
                length "1..20" {
                  description
                    "range : <1-18446744073709551615>";
                }
              }
              description
                "Configure threshold for total no. of Authenticated blocks processed";
            }
            leaf out-blocks-un-protected {
              type xr:Cisco-ios-xr-string {
                length "1..20" {
                  description
                    "range : <1-18446744073709551615>";
                }
              }
              description
                "Configure threshold for total no. of unAuthenticated blocks processed";
            }
          }
          container report {
            description
              "Configure TCA report for otnsec parameters";
            container in-blocks {
              description
                "Set TCA report for Inblocks";
              container enable {
                presence "Indicates a enable node is configured.";
                description
                  "Enable TCA reporting";
              }
            }
            container in-blocks-enc {
              description
                "Set TCA report for InBlocksEnc";
              container enable {
                presence "Indicates a enable node is configured.";
                description
                  "Enable TCA reporting";
              }
            }
            container in-blocks-un-encrypted {
              description
                "Set TCA report for InBlocksUnEncrypted";
              container enable {
                presence "Indicates a enable node is configured.";
                description
                  "Enable TCA reporting";
              }
            }
            container in-blocks-protected {
              description
                "Set TCA report for InBlocksProtected";
              container enable {
                presence "Indicates a enable node is configured.";
                description
                  "Enable TCA reporting";
              }
            }
            container in-blocks-un-portected {
              description
                "Set TCA report for InBlocksUnPortected";
              container enable {
                presence "Indicates a enable node is configured.";
                description
                  "Enable TCA reporting";
              }
            }
            container in-blocks-sequence-errors {
              description
                "Set TCA report for InBlocksSequenceErrors";
              container enable {
                presence "Indicates a enable node is configured.";
                description
                  "Enable TCA reporting";
              }
            }
            container in-blocks-replay-errors {
              description
                "Set TCA report for InBlocksReplayErrors";
              container enable {
                presence "Indicates a enable node is configured.";
                description
                  "Enable TCA reporting";
              }
            }
            container in-blocks-auth-errors {
              description
                "Set TCA report for InBlocksAuthErrors";
              container enable {
                presence "Indicates a enable node is configured.";
                description
                  "Enable TCA reporting";
              }
            }
            container in-blocks-zeroed {
              description
                "Set TCA report for InBlocksZeroed";
              container enable {
                presence "Indicates a enable node is configured.";
                description
                  "Enable TCA reporting";
              }
            }
            container out-blocks {
              description
                "Set TCA report for OutBlocks";
              container enable {
                presence "Indicates a enable node is configured.";
                description
                  "Enable TCA reporting";
              }
            }
            container out-blocks-enc {
              description
                "Set TCA report for OutBlocksEnc";
              container enable {
                presence "Indicates a enable node is configured.";
                description
                  "Enable TCA reporting";
              }
            }
            container out-blocks-un-encrypted {
              description
                "Set TCA report for OutBlocksUnEncrypted";
              container enable {
                presence "Indicates a enable node is configured.";
                description
                  "Enable TCA reporting";
              }
            }
            container out-blocks-sequence-errors {
              description
                "Set TCA report for OutBlocksSequenceErrors";
              container enable {
                presence "Indicates a enable node is configured.";
                description
                  "Enable TCA reporting";
              }
            }
            container out-blocks-zeroed {
              description
                "Set TCA report for OutBlocksZeroed";
              container enable {
                presence "Indicates a enable node is configured.";
                description
                  "Enable TCA reporting";
              }
            }
            container out-blocks-protected {
              description
                "Set TCA report for OutBlocksProtected";
              container enable {
                presence "Indicates a enable node is configured.";
                description
                  "Enable TCA reporting";
              }
            }
            container out-blocks-un-portected {
              description
                "Set TCA report for OutBlocksUnPortected";
              container enable {
                presence "Indicates a enable node is configured.";
                description
                  "Enable TCA reporting";
              }
            }
          }
        }
        container gfp {
          description
            "Configure gfp performance monitoring";
          container threshold {
            description
              "Configure gfp threshold";
            leaf rx-bit-err {
              type uint32 {
                range "1..4294967295" {
                  description
                    "RX-BIT-ERR threshold";
                }
              }
              description
                "set RX-BIT-ERR threshold";
            }
            leaf rx-inv-type {
              type uint32 {
                range "1..4294967295" {
                  description
                    "RX-INV-TYP threshold";
                }
              }
              description
                "set RX-INV-TYP threshold";
            }
            leaf rx-crc-err {
              type uint32 {
                range "1..4294967295" {
                  description
                    "RX-CRC threshold";
                }
              }
              description
                "set RX-CRC threshold";
            }
            leaf rx-lfd-stats {
              type uint32 {
                range "1..4294967295" {
                  description
                    "RX-LFD-STAT threshold";
                }
              }
              description
                "set RX-LFD threshold";
            }
            leaf rx-csf-stats {
              type uint32 {
                range "1..4294967295" {
                  description
                    "RX-CSF threshold";
                }
              }
              description
                "set RX-CSF threshold";
            }
          }
          container report {
            description
              "set gfp TCA reporting status";
            container rx-bit-err {
              description
                "set rx-bit-err TCA reporting status";
              container enable {
                presence "Indicates a enable node is configured.";
                description
                  "Enable TCA reporting";
              }
            }
            container rx-inv-type {
              description
                "set rx-inv-type TCA reporting status";
              container enable {
                presence "Indicates a enable node is configured.";
                description
                  "Enable TCA reporting";
              }
            }
            container rx-crc-err {
              description
                "set rx-crc-err TCA reporting status";
              container enable {
                presence "Indicates a enable node is configured.";
                description
                  "Enable TCA reporting";
              }
            }
            container rx-lfd-stats {
              description
                "set rx-lfd-stats TCA reporting status";
              container enable {
                presence "Indicates a enable node is configured.";
                description
                  "Enable TCA reporting";
              }
            }
            container rx-csf-stats {
              description
                "set rx-csf-stats TCA reporting status";
              container enable {
                presence "Indicates a enable node is configured.";
                description
                  "Enable TCA reporting";
              }
            }
          }
        }
        container prbs {
          description
            "Configure prbs performance monitoring";
          container threshold {
            description
              "Configure prbs threshold";
            leaf ebc {
              type xr:Cisco-ios-xr-string {
                length "1..20" {
                  description
                    "ebc threshold <1-18446744073709551615>";
                }
              }
              description
                "set EBC threshold";
            }
            leaf found-count {
              type xr:Cisco-ios-xr-string {
                length "1..10" {
                  description
                    "found-count threshold <1-4294967295>";
                }
              }
              description
                "set FOUND-COUNT threshold";
            }
            leaf lost-count {
              type xr:Cisco-ios-xr-string {
                length "1..10" {
                  description
                    "lost-count threshold <1-4294967295>";
                }
              }
              description
                "set LOST-COUNT threshold";
            }
          }
          container report {
            description
              "set prbs TCA reporting status";
            container ebc {
              description
                "set ebc TCA reporting status";
              container enable {
                presence "Indicates a enable node is configured.";
                description
                  "Enable TCA reporting";
              }
            }
            container found-count {
              description
                "set found-count TCA reporting status";
              container enable {
                presence "Indicates a enable node is configured.";
                description
                  "Enable TCA reporting";
              }
            }
            container lost-count {
              description
                "set lost-count TCA reporting status";
              container enable {
                presence "Indicates a enable node is configured.";
                description
                  "Enable TCA reporting";
              }
            }
          }
        }
      }
      container interval-30-sec {
        if-feature "optics_cli_supp_check";
        description
          "Configure 30-sec interval parameter";
        container otnsec {
          description
            "configure otnsec pm parameters";
          container threshold {
            description
              "configure threshold for otnsec pm parameters";
            leaf in-blocks {
              type xr:Cisco-ios-xr-string {
                length "1..20" {
                  description
                    "range : <1-18446744073709551615>";
                }
              }
              description
                "Configure threshold for total no. of odu blocks processed";
            }
            leaf in-blocks-enc {
              type xr:Cisco-ios-xr-string {
                length "1..20" {
                  description
                    "range : <1-18446744073709551615>";
                }
              }
              description
                "Configure threshold for total no. of encrypted blocks processed";
            }
            leaf in-blocks-un-encrypted {
              type xr:Cisco-ios-xr-string {
                length "1..20" {
                  description
                    "range : <1-18446744073709551615>";
                }
              }
              description
                "Configure threshold for total no. of un-encrypted blocks processed";
            }
            leaf in-blocks-protected {
              type xr:Cisco-ios-xr-string {
                length "1..20" {
                  description
                    "range : <1-18446744073709551615>";
                }
              }
              description
                "Configure threshold for total no. of Authenticated blocks processed";
            }
            leaf in-blocks-un-protected {
              type xr:Cisco-ios-xr-string {
                length "1..20" {
                  description
                    "range : <1-18446744073709551615>";
                }
              }
              description
                "Configure threshold for total no. of unAuthenticated blocks processed";
            }
            leaf in-blocks-sequence-errors {
              type xr:Cisco-ios-xr-string {
                length "1..20" {
                  description
                    "range : <1-18446744073709551615>";
                }
              }
              description
                "Configure threshold for Sequence Errors";
            }
            leaf in-blocks-replay-errors {
              type xr:Cisco-ios-xr-string {
                length "1..20" {
                  description
                    "range : <1-18446744073709551615>";
                }
              }
              description
                "Configure threshold for Replay Errors";
            }
            leaf in-blocks-auth-errors {
              type xr:Cisco-ios-xr-string {
                length "1..20" {
                  description
                    "range : <1-18446744073709551615>";
                }
              }
              description
                "Configure threshold for blocks which failed authentication check";
            }
            leaf in-blocks-zeroed {
              type xr:Cisco-ios-xr-string {
                length "1..20" {
                  description
                    "range : <1-18446744073709551615>";
                }
              }
              description
                "Configure threshold for Blocks which were zeroed due to some errors";
            }
            leaf out-blocks {
              type xr:Cisco-ios-xr-string {
                length "1..20" {
                  description
                    "range : <1-18446744073709551615>";
                }
              }
              description
                "Configure threshold for total number of ODU blocks processed";
            }
            leaf out-blocks-enc {
              type xr:Cisco-ios-xr-string {
                length "1..20" {
                  description
                    "range : <1-18446744073709551615>";
                }
              }
              description
                "Configure threshold for no. of encrypted blocks processed";
            }
            leaf out-blocks-un-encrypted {
              type xr:Cisco-ios-xr-string {
                length "1..20" {
                  description
                    "range : <1-18446744073709551615>";
                }
              }
              description
                "Configure threshold for no. of unencrypted blocks processed";
            }
            leaf out-blocks-sequence-errors {
              type xr:Cisco-ios-xr-string {
                length "1..20" {
                  description
                    "range : <1-18446744073709551615>";
                }
              }
              description
                "Configure threshold for sequence errors";
            }
            leaf out-blocks-zeroed {
              type xr:Cisco-ios-xr-string {
                length "1..20" {
                  description
                    "range : <1-18446744073709551615>";
                }
              }
              description
                "Configure threshold for blocks that were zeroed due to some errors";
            }
            leaf out-blocks-protected {
              type xr:Cisco-ios-xr-string {
                length "1..20" {
                  description
                    "range : <1-18446744073709551615>";
                }
              }
              description
                "Configure threshold for total no. of Authenticated blocks processed";
            }
            leaf out-blocks-un-protected {
              type xr:Cisco-ios-xr-string {
                length "1..20" {
                  description
                    "range : <1-18446744073709551615>";
                }
              }
              description
                "Configure threshold for total no. of unAuthenticated blocks processed";
            }
          }
          container report {
            description
              "Configure TCA report for otnsec parameters";
            container in-blocks {
              description
                "Set TCA report for Inblocks";
              container enable {
                presence "Indicates a enable node is configured.";
                description
                  "Enable TCA reporting";
              }
            }
            container in-blocks-enc {
              description
                "Set TCA report for InBlocksEnc";
              container enable {
                presence "Indicates a enable node is configured.";
                description
                  "Enable TCA reporting";
              }
            }
            container in-blocks-un-encrypted {
              description
                "Set TCA report for InBlocksUnEncrypted";
              container enable {
                presence "Indicates a enable node is configured.";
                description
                  "Enable TCA reporting";
              }
            }
            container in-blocks-protected {
              description
                "Set TCA report for InBlocksProtected";
              container enable {
                presence "Indicates a enable node is configured.";
                description
                  "Enable TCA reporting";
              }
            }
            container in-blocks-un-portected {
              description
                "Set TCA report for InBlocksUnPortected";
              container enable {
                presence "Indicates a enable node is configured.";
                description
                  "Enable TCA reporting";
              }
            }
            container in-blocks-sequence-errors {
              description
                "Set TCA report for InBlocksSequenceErrors";
              container enable {
                presence "Indicates a enable node is configured.";
                description
                  "Enable TCA reporting";
              }
            }
            container in-blocks-replay-errors {
              description
                "Set TCA report for InBlocksReplayErrors";
              container enable {
                presence "Indicates a enable node is configured.";
                description
                  "Enable TCA reporting";
              }
            }
            container in-blocks-auth-errors {
              description
                "Set TCA report for InBlocksAuthErrors";
              container enable {
                presence "Indicates a enable node is configured.";
                description
                  "Enable TCA reporting";
              }
            }
            container in-blocks-zeroed {
              description
                "Set TCA report for InBlocksZeroed";
              container enable {
                presence "Indicates a enable node is configured.";
                description
                  "Enable TCA reporting";
              }
            }
            container out-blocks {
              description
                "Set TCA report for OutBlocks";
              container enable {
                presence "Indicates a enable node is configured.";
                description
                  "Enable TCA reporting";
              }
            }
            container out-blocks-enc {
              description
                "Set TCA report for OutBlocksEnc";
              container enable {
                presence "Indicates a enable node is configured.";
                description
                  "Enable TCA reporting";
              }
            }
            container out-blocks-un-encrypted {
              description
                "Set TCA report for OutBlocksUnEncrypted";
              container enable {
                presence "Indicates a enable node is configured.";
                description
                  "Enable TCA reporting";
              }
            }
            container out-blocks-sequence-errors {
              description
                "Set TCA report for OutBlocksSequenceErrors";
              container enable {
                presence "Indicates a enable node is configured.";
                description
                  "Enable TCA reporting";
              }
            }
            container out-blocks-zeroed {
              description
                "Set TCA report for OutBlocksZeroed";
              container enable {
                presence "Indicates a enable node is configured.";
                description
                  "Enable TCA reporting";
              }
            }
            container out-blocks-protected {
              description
                "Set TCA report for OutBlocksProtected";
              container enable {
                presence "Indicates a enable node is configured.";
                description
                  "Enable TCA reporting";
              }
            }
            container out-blocks-un-portected {
              description
                "Set TCA report for OutBlocksUnPortected";
              container enable {
                presence "Indicates a enable node is configured.";
                description
                  "Enable TCA reporting";
              }
            }
          }
        }
        container otn {
          description
            "configure otn g709 performance monitoring";
          container pathmonitor {
            description
              "configure otn g709 performance monitoring";
            container threshold {
              description
                "Configure threshold on otn parameters";
              leaf es-ne {
                type uint32 {
                  range "0..30" {
                    description
                      "ES-NE threshold (seconds)";
                  }
                }
                description
                  "set ES-NE threshold";
              }
              leaf esr-ne {
                type uint32 {
                  range "0..100000" {
                    description
                      "ESR-NE threshold[Ratio parameters range(0-1),eg. 75000 corresponds to 0.75]";
                  }
                }
                description
                  "set ESR-NE threshold";
              }
              leaf ses-ne {
                type uint32 {
                  range "0..30" {
                    description
                      "SES-NE threshold (seconds)";
                  }
                }
                description
                  "set SES-NE threshold";
              }
              leaf sesr-ne {
                type uint32 {
                  range "0..100000" {
                    description
                      "SESR-NE threshold[Ratio parameters range(0-1),eg. 75000 corresponds to 0.75]";
                  }
                }
                description
                  "set SESR-NE threshold";
              }
              leaf uas-ne {
                type uint32 {
                  range "0..30" {
                    description
                      "UAS-NE threshold (seconds)";
                  }
                }
                description
                  "set UAS-NE threshold";
              }
              leaf bbe-ne {
                type uint32 {
                  range "0..8850600" {
                    description
                      "BBE-NE threshold";
                  }
                }
                description
                  "set BBE-NE threshold";
              }
              leaf bber-ne {
                type uint32 {
                  range "0..100000" {
                    description
                      "BBER-NE threshold[Ratio parameters range(0-1),eg. 75000 corresponds to 0.75]";
                  }
                }
                description
                  "set BBER-NE threshold";
              }
              leaf fc-ne {
                type uint32 {
                  range "0..72" {
                    description
                      "FC-NE threshold";
                  }
                }
                description
                  "set FC-NE threshold";
              }
              leaf es-fe {
                type uint32 {
                  range "0..30" {
                    description
                      "ES-FE threshold (seconds)";
                  }
                }
                description
                  "set ES-FE threshold";
              }
              leaf esr-fe {
                type uint32 {
                  range "0..100000" {
                    description
                      "ESR-FE threshold[Ratio parameters range(0-1),eg. 75000 corresponds to 0.75]";
                  }
                }
                description
                  "set ESR-FE threshold";
              }
              leaf ses-fe {
                type uint32 {
                  range "0..30" {
                    description
                      "SES-FE threshold (seconds)";
                  }
                }
                description
                  "set SES-FE threshold";
              }
              leaf sesr-fe {
                type uint32 {
                  range "0..100000" {
                    description
                      "SESR-FE threshold[Ratio parameters range(0-1),eg. 75000 corresponds to 0.75]";
                  }
                }
                description
                  "set SESR-FE threshold";
              }
              leaf uas-fe {
                type uint32 {
                  range "0..30" {
                    description
                      "UAS-FE threshold (seconds)";
                  }
                }
                description
                  "set UAS-FE threshold";
              }
              leaf bbe-fe {
                type uint32 {
                  range "0..8850600" {
                    description
                      "BBE-FE threshold";
                  }
                }
                description
                  "set BBE-FE threshold";
              }
              leaf bber-fe {
                type uint32 {
                  range "0..100000" {
                    description
                      "BBER-FE threshold[Ratio parameters range(0-1),eg. 75000 corresponds to 0.75]";
                  }
                }
                description
                  "set BBER-FE threshold";
              }
              leaf fc-fe {
                type uint32 {
                  range "0..72" {
                    description
                      "FC-FE threshold";
                  }
                }
                description
                  "set FC-FE threshold";
              }
            }
            container report {
              description
                "set otn TCA reporting status";
              container es-ne {
                description
                  "set es-ne TCA reporting status";
                container disable {
                  presence "Indicates a disable node is configured.";
                  description
                    "Disable TCA reporting";
                }
              }
              container ses-ne {
                description
                  "set ses-ne TCA reporting status";
                container disable {
                  presence "Indicates a disable node is configured.";
                  description
                    "Disable TCA reporting";
                }
              }
              container uas-ne {
                description
                  "set uas-ne TCA reporting status";
                container disable {
                  presence "Indicates a disable node is configured.";
                  description
                    "Disable TCA reporting";
                }
              }
              container bbe-ne {
                description
                  "set bbe-ne TCA reporting status";
                container disable {
                  presence "Indicates a disable node is configured.";
                  description
                    "Disable TCA reporting";
                }
              }
              container fc-ne {
                description
                  "set fc-ne TCA reporting status";
                container disable {
                  presence "Indicates a disable node is configured.";
                  description
                    "Disable TCA reporting";
                }
              }
              container esr-ne {
                description
                  "set esr-ne TCA reporting status";
                container disable {
                  presence "Indicates a disable node is configured.";
                  description
                    "Disable TCA reporting";
                }
              }
              container sesr-ne {
                description
                  "set sesr-ne TCA reporting status";
                container disable {
                  presence "Indicates a disable node is configured.";
                  description
                    "Disable TCA reporting";
                }
              }
              container bber-ne {
                description
                  "set bber-ne TCA reporting status";
                container disable {
                  presence "Indicates a disable node is configured.";
                  description
                    "Disable TCA reporting";
                }
              }
              container es-fe {
                description
                  "set es-fe TCA reporting status";
                container disable {
                  presence "Indicates a disable node is configured.";
                  description
                    "Disable TCA reporting";
                }
              }
              container ses-fe {
                description
                  "set ses-fe TCA reporting status";
                container disable {
                  presence "Indicates a disable node is configured.";
                  description
                    "Disable TCA reporting";
                }
              }
              container uas-fe {
                description
                  "set uas-fe TCA reporting status";
                container disable {
                  presence "Indicates a disable node is configured.";
                  description
                    "Disable TCA reporting";
                }
              }
              container bbe-fe {
                description
                  "set bbe-fe TCA reporting status";
                container disable {
                  presence "Indicates a disable node is configured.";
                  description
                    "Disable TCA reporting";
                }
              }
              container fc-fe {
                description
                  "set fc-fe TCA reporting status";
                container disable {
                  presence "Indicates a disable node is configured.";
                  description
                    "Disable TCA reporting";
                }
              }
              container esr-fe {
                description
                  "set esr-fe TCA reporting status";
                container disable {
                  presence "Indicates a disable node is configured.";
                  description
                    "Disable TCA reporting";
                }
              }
              container sesr-fe {
                description
                  "set sesr-fe TCA reporting status";
                container disable {
                  presence "Indicates a disable node is configured.";
                  description
                    "Disable TCA reporting";
                }
              }
              container bber-fe {
                description
                  "set bber-fe TCA reporting status";
                container disable {
                  presence "Indicates a disable node is configured.";
                  description
                    "Disable TCA reporting";
                }
              }
            }
          }
          container tcms {
            description
              "configure tcm performance monitoring";
            list tcm {
              key "channel-number";
              description
                "configure tcm performance monitoring";
              leaf channel-number {
                type uint32 {
                  range "1..6" {
                    description
                      " Channel Number";
                  }
                }
                description
                  "configure tcm performance monitoring";
              }
              container threshold {
                description
                  "Configure threshold on otn parameters";
                leaf es-ne {
                  type uint32 {
                    range "0..30" {
                      description
                        "ES-NE threshold (seconds)";
                    }
                  }
                  description
                    "set ES-NE threshold";
                }
                leaf esr-ne {
                  type uint32 {
                    range "0..100000" {
                      description
                        "ESR-NE threshold[Ratio parameters range(0-1),eg. 75000 corresponds to 0.75]";
                    }
                  }
                  description
                    "set ESR-NE threshold";
                }
                leaf ses-ne {
                  type uint32 {
                    range "0..30" {
                      description
                        "SES-NE threshold (seconds)";
                    }
                  }
                  description
                    "set SES-NE threshold";
                }
                leaf sesr-ne {
                  type uint32 {
                    range "0..100000" {
                      description
                        "SESR-NE threshold[Ratio parameters range(0-1),eg. 75000 corresponds to 0.75]";
                    }
                  }
                  description
                    "set SESR-NE threshold";
                }
                leaf uas-ne {
                  type uint32 {
                    range "0..30" {
                      description
                        "UAS-NE threshold (seconds)";
                    }
                  }
                  description
                    "set UAS-NE threshold";
                }
                leaf bbe-ne {
                  type uint32 {
                    range "0..8850600" {
                      description
                        "BBE-NE threshold";
                    }
                  }
                  description
                    "set BBE-NE threshold";
                }
                leaf bber-ne {
                  type uint32 {
                    range "0..100000" {
                      description
                        "BBER-NE threshold[Ratio parameters range(0-1),eg. 75000 corresponds to 0.75]";
                    }
                  }
                  description
                    "set BBER-NE threshold";
                }
                leaf fc-ne {
                  type uint32 {
                    range "0..72" {
                      description
                        "FC-NE threshold";
                    }
                  }
                  description
                    "set FC-NE threshold";
                }
                leaf es-fe {
                  type uint32 {
                    range "0..30" {
                      description
                        "ES-FE threshold (seconds)";
                    }
                  }
                  description
                    "set ES-FE threshold";
                }
                leaf esr-fe {
                  type uint32 {
                    range "0..100000" {
                      description
                        "ESR-FE threshold[Ratio parameters range(0-1),eg. 75000 corresponds to 0.75]";
                    }
                  }
                  description
                    "set ESR-FE threshold";
                }
                leaf ses-fe {
                  type uint32 {
                    range "0..30" {
                      description
                        "SES-FE threshold (seconds)";
                    }
                  }
                  description
                    "set SES-FE threshold";
                }
                leaf sesr-fe {
                  type uint32 {
                    range "0..100000" {
                      description
                        "SESR-FE threshold[Ratio parameters range(0-1),eg. 75000 corresponds to 0.75]";
                    }
                  }
                  description
                    "set SESR-FE threshold";
                }
                leaf uas-fe {
                  type uint32 {
                    range "0..30" {
                      description
                        "UAS-FE threshold (seconds)";
                    }
                  }
                  description
                    "set UAS-FE threshold";
                }
                leaf bbe-fe {
                  type uint32 {
                    range "0..8850600" {
                      description
                        "BBE-FE threshold";
                    }
                  }
                  description
                    "set BBE-FE threshold";
                }
                leaf bber-fe {
                  type uint32 {
                    range "0..100000" {
                      description
                        "BBER-FE threshold[Ratio parameters range(0-1),eg. 75000 corresponds to 0.75]";
                    }
                  }
                  description
                    "set BBER-FE threshold";
                }
                leaf fc-fe {
                  type uint32 {
                    range "0..72" {
                      description
                        "FC-FE threshold";
                    }
                  }
                  description
                    "set FC-FE threshold";
                }
              }
              container report {
                description
                  "set otn TCA reporting status";
                container es-fe {
                  description
                    "set es-fe TCA reporting status";
                  container disable {
                    presence "Indicates a disable node is configured.";
                    description
                      "Disable TCA reporting";
                  }
                }
                container ses-fe {
                  description
                    "set ses-fe TCA reporting status";
                  container disable {
                    presence "Indicates a disable node is configured.";
                    description
                      "Disable TCA reporting";
                  }
                }
                container uas-fe {
                  description
                    "set uas-fe TCA reporting status";
                  container disable {
                    presence "Indicates a disable node is configured.";
                    description
                      "Disable TCA reporting";
                  }
                }
                container bbe-fe {
                  description
                    "set bbe-fe TCA reporting status";
                  container disable {
                    presence "Indicates a disable node is configured.";
                    description
                      "Disable TCA reporting";
                  }
                }
                container fc-fe {
                  description
                    "set fc-fe TCA reporting status";
                  container disable {
                    presence "Indicates a disable node is configured.";
                    description
                      "Disable TCA reporting";
                  }
                }
                container esr-fe {
                  description
                    "set esr-fe TCA reporting status";
                  container disable {
                    presence "Indicates a disable node is configured.";
                    description
                      "Disable TCA reporting";
                  }
                }
                container sesr-fe {
                  description
                    "set sesr-fe TCA reporting status";
                  container disable {
                    presence "Indicates a disable node is configured.";
                    description
                      "Disable TCA reporting";
                  }
                }
                container bber-fe {
                  description
                    "set bber-fe TCA reporting status";
                  container disable {
                    presence "Indicates a disable node is configured.";
                    description
                      "Disable TCA reporting";
                  }
                }
                container es-ne {
                  description
                    "set es-ne TCA reporting status";
                  container disable {
                    presence "Indicates a disable node is configured.";
                    description
                      "Disable TCA reporting";
                  }
                }
                container ses-ne {
                  description
                    "set ses-ne TCA reporting status";
                  container disable {
                    presence "Indicates a disable node is configured.";
                    description
                      "Disable TCA reporting";
                  }
                }
                container uas-ne {
                  description
                    "set uas-ne TCA reporting status";
                  container disable {
                    presence "Indicates a disable node is configured.";
                    description
                      "Disable TCA reporting";
                  }
                }
                container bbe-ne {
                  description
                    "set bbe-ne TCA reporting status";
                  container disable {
                    presence "Indicates a disable node is configured.";
                    description
                      "Disable TCA reporting";
                  }
                }
                container fc-ne {
                  description
                    "set fc-ne TCA reporting status";
                  container disable {
                    presence "Indicates a disable node is configured.";
                    description
                      "Disable TCA reporting";
                  }
                }
                container esr-ne {
                  description
                    "set esr-ne TCA reporting status";
                  container disable {
                    presence "Indicates a disable node is configured.";
                    description
                      "Disable TCA reporting";
                  }
                }
                container sesr-ne {
                  description
                    "set sesr-ne TCA reporting status";
                  container disable {
                    presence "Indicates a disable node is configured.";
                    description
                      "Disable TCA reporting";
                  }
                }
                container bber-ne {
                  description
                    "set bber-ne TCA reporting status";
                  container disable {
                    presence "Indicates a disable node is configured.";
                    description
                      "Disable TCA reporting";
                  }
                }
              }
            }
          }
          container threshold {
            description
              "Configure threshold on otn parameters";
            leaf es-ne {
              type uint32 {
                range "0..900" {
                  description
                    "es-ne threshold (seconds)";
                }
              }
              description
                "set ES-NE threshold";
            }
            leaf esr-ne {
              type uint32 {
                range "0..100000" {
                  description
                    "esr-ne threshold[Ratio parameters range(0-1),eg. 75000 corresponds to 0.75]";
                }
              }
              description
                "set ESR-NE threshold";
            }
            leaf ses-ne {
              type uint32 {
                range "0..900" {
                  description
                    "ses-ne threshold (seconds)";
                }
              }
              description
                "set SES-NE threshold";
            }
            leaf sesr-ne {
              type uint32 {
                range "0..100000" {
                  description
                    "sesr-ne threshold[Ratio parameters range(0-1),eg. 75000 corresponds to 0.75]";
                }
              }
              description
                "set SESR-NE threshold";
            }
            leaf uas-ne {
              type uint32 {
                range "0..900" {
                  description
                    "uas-ne threshold (seconds)";
                }
              }
              description
                "set UAS-NE threshold";
            }
            leaf bbe-ne {
              type uint32 {
                range "0..8850600" {
                  description
                    "bbe-ne threshold";
                }
              }
              description
                "set BBE-NE threshold";
            }
            leaf bber-ne {
              type uint32 {
                range "1..100000" {
                  description
                    "bber-ne threshold[Ratio parameters range(0-1),eg. 75000 corresponds to 0.75]";
                }
              }
              description
                "set BBER-NE threshold";
            }
            leaf fc-ne {
              type uint32 {
                range "0..72" {
                  description
                    "fc-ne threshold";
                }
              }
              description
                "set FC-NE threshold";
            }
            leaf es-fe {
              type uint32 {
                range "0..900" {
                  description
                    "es-fe threshold (seconds)";
                }
              }
              description
                "set ES-FE threshold";
            }
            leaf esr-fe {
              type uint32 {
                range "0..100000" {
                  description
                    "esr-fe threshold[Ratio parameters range(0-1),eg. 75000 corresponds to 0.75]";
                }
              }
              description
                "set ESR-FE threshold";
            }
            leaf ses-fe {
              type uint32 {
                range "0..900" {
                  description
                    "ses-fe threshold (seconds)";
                }
              }
              description
                "set SES-FE threshold";
            }
            leaf sesr-fe {
              type uint32 {
                range "0..100000" {
                  description
                    "sesr-fe threshold[Ratio parameters range(0-1),eg. 75000 corresponds to 0.75]";
                }
              }
              description
                "set SESR-FE threshold";
            }
            leaf uas-fe {
              type uint32 {
                range "0..900" {
                  description
                    "uas-fe threshold (seconds)";
                }
              }
              description
                "set UAS-FE threshold";
            }
            leaf bbe-fe {
              type uint32 {
                range "0..8850600" {
                  description
                    "bbe-fe threshold";
                }
              }
              description
                "set BBE-FE threshold";
            }
            leaf bber-fe {
              type uint32 {
                range "1..100000" {
                  description
                    "bber-fe threshold[Ratio parameters range(0-1),eg. 75000 corresponds to 0.75]";
                }
              }
              description
                "set BBER-FE threshold";
            }
            leaf fc-fe {
              type uint32 {
                range "0..72" {
                  description
                    "fc-fe threshold";
                }
              }
              description
                "set FC-FE threshold";
            }
          }
          container report {
            description
              "set otn TCA reporting status";
            container es-ne {
              description
                "set es-ne TCA reporting status";
              container disable {
                presence "Indicates a disable node is configured.";
                description
                  "Disable TCA reporting";
              }
            }
            container ses-ne {
              description
                "set ses-ne TCA reporting status";
              container disable {
                presence "Indicates a disable node is configured.";
                description
                  "Disable TCA reporting";
              }
            }
            container uas-ne {
              description
                "set uas-ne TCA reporting status";
              container disable {
                presence "Indicates a disable node is configured.";
                description
                  "Disable TCA reporting";
              }
            }
            container bbe-ne {
              description
                "set bbe-ne TCA reporting status";
              container disable {
                presence "Indicates a disable node is configured.";
                description
                  "Disable TCA reporting";
              }
            }
            container fc-ne {
              description
                "set fc-ne TCA reporting status";
              container disable {
                presence "Indicates a disable node is configured.";
                description
                  "Disable TCA reporting";
              }
            }
            container esr-ne {
              description
                "set esr-ne TCA reporting status";
              container disable {
                presence "Indicates a disable node is configured.";
                description
                  "Disable TCA reporting";
              }
            }
            container sesr-ne {
              description
                "set sesr-ne TCA reporting status";
              container disable {
                presence "Indicates a disable node is configured.";
                description
                  "Disable TCA reporting";
              }
            }
            container bber-ne {
              description
                "set bber-ne TCA reporting status";
              container disable {
                presence "Indicates a disable node is configured.";
                description
                  "Disable TCA reporting";
              }
            }
            container es-pm-ne {
              description
                "set es-pm TCA reporting status";
              container enable {
                presence "Indicates a enable node is configured.";
                description
                  "Enable TCA reporting";
              }
            }
            container ses-pm-ne {
              description
                "set ses-pm TCA reporting status";
              container enable {
                presence "Indicates a enable node is configured.";
                description
                  "Enable TCA reporting";
              }
            }
            container uas-pm-ne {
              description
                "set uas-pm TCA reporting status";
              container enable {
                presence "Indicates a enable node is configured.";
                description
                  "Enable TCA reporting";
              }
            }
            container bbe-pm-ne {
              description
                "set bbe-pm TCA reporting status";
              container enable {
                presence "Indicates a enable node is configured.";
                description
                  "Enable TCA reporting";
              }
            }
            container fc-pm-ne {
              description
                "set fc-pm TCA reporting status";
              container enable {
                presence "Indicates a enable node is configured.";
                description
                  "Enable TCA reporting";
              }
            }
            container esr-pm-ne {
              description
                "set esr-pm TCA reporting status";
              container enable {
                presence "Indicates a enable node is configured.";
                description
                  "Enable TCA reporting";
              }
            }
            container sesr-pm-ne {
              description
                "set sesr-pm TCA reporting status";
              container enable {
                presence "Indicates a enable node is configured.";
                description
                  "Enable TCA reporting";
              }
            }
            container bber-pm-ne {
              description
                "set bber-pm TCA reporting status";
              container enable {
                presence "Indicates a enable node is configured.";
                description
                  "Enable TCA reporting";
              }
            }
            container es-fe {
              description
                "set es-fe TCA reporting status";
              container disable {
                presence "Indicates a disable node is configured.";
                description
                  "Disable TCA reporting";
              }
            }
            container ses-fe {
              description
                "set ses-fe TCA reporting status";
              container disable {
                presence "Indicates a disable node is configured.";
                description
                  "Disable TCA reporting";
              }
            }
            container uas-fe {
              description
                "set uas-fe TCA reporting status";
              container disable {
                presence "Indicates a disable node is configured.";
                description
                  "Disable TCA reporting";
              }
            }
            container bbe-fe {
              description
                "set bbe-fe TCA reporting status";
              container disable {
                presence "Indicates a disable node is configured.";
                description
                  "Disable TCA reporting";
              }
            }
            container fc-fe {
              description
                "set fc-fe TCA reporting status";
              container disable {
                presence "Indicates a disable node is configured.";
                description
                  "Disable TCA reporting";
              }
            }
            container esr-fe {
              description
                "set esr-fe TCA reporting status";
              container disable {
                presence "Indicates a disable node is configured.";
                description
                  "Disable TCA reporting";
              }
            }
            container sesr-fe {
              description
                "set sesr-fe TCA reporting status";
              container disable {
                presence "Indicates a disable node is configured.";
                description
                  "Disable TCA reporting";
              }
            }
            container bber-fe {
              description
                "set bber-fe TCA reporting status";
              container disable {
                presence "Indicates a disable node is configured.";
                description
                  "Disable TCA reporting";
              }
            }
            container es-pm-fe {
              description
                "set es-pm TCA reporting status";
              container enable {
                presence "Indicates a enable node is configured.";
                description
                  "Enable TCA reporting";
              }
            }
            container ses-pm-fe {
              description
                "set ses-pm TCA reporting status";
              container enable {
                presence "Indicates a enable node is configured.";
                description
                  "Enable TCA reporting";
              }
            }
            container uas-pm-fe {
              description
                "set uas-pm TCA reporting status";
              container enable {
                presence "Indicates a enable node is configured.";
                description
                  "Enable TCA reporting";
              }
            }
            container bbe-pm-fe {
              description
                "set bbe-pm TCA reporting status";
              container enable {
                presence "Indicates a enable node is configured.";
                description
                  "Enable TCA reporting";
              }
            }
            container fc-pm-fe {
              description
                "set fc-pm TCA reporting status";
              container enable {
                presence "Indicates a enable node is configured.";
                description
                  "Enable TCA reporting";
              }
            }
            container esr-pm-fe {
              description
                "set esr-pm TCA reporting status";
              container enable {
                presence "Indicates a enable node is configured.";
                description
                  "Enable TCA reporting";
              }
            }
            container sesr-pm-fe {
              description
                "set sesr-pm TCA reporting status";
              container enable {
                presence "Indicates a enable node is configured.";
                description
                  "Enable TCA reporting";
              }
            }
            container bber-pm-fe {
              description
                "set bber-pm TCA reporting status";
              container enable {
                presence "Indicates a enable node is configured.";
                description
                  "Enable TCA reporting";
              }
            }
          }
        }
        container gfp {
          description
            "Configure gfp performance monitoring";
          container threshold {
            description
              "Configure gfp threshold";
            leaf rx-bit-err {
              type uint32 {
                range "1..4294967295" {
                  description
                    "RX-BIT-ERR threshold";
                }
              }
              description
                "set RX-BIT-ERR threshold";
            }
            leaf rx-inv-type {
              type uint32 {
                range "1..4294967295" {
                  description
                    "RX-INV-TYP threshold";
                }
              }
              description
                "set RX-INV-TYP threshold";
            }
            leaf rx-crc-err {
              type uint32 {
                range "1..4294967295" {
                  description
                    "RX-CRC threshold";
                }
              }
              description
                "set RX-CRC threshold";
            }
            leaf rx-lfd-stats {
              type uint32 {
                range "1..4294967295" {
                  description
                    "RX-LFD threshold";
                }
              }
              description
                "set RX-LFD threshold";
            }
            leaf rx-csf-stats {
              type uint32 {
                range "1..4294967295" {
                  description
                    "RX-CSF threshold";
                }
              }
              description
                "set RX-CSF threshold";
            }
          }
          container report {
            description
              "set gfp TCA reporting status";
            container rx-bit-err {
              description
                "set rx-bit-err TCA reporting status";
              container enable {
                presence "Indicates a enable node is configured.";
                description
                  "Enable TCA reporting";
              }
            }
            container rx-inv-type {
              description
                "set rx-inv-type TCA reporting status";
              container enable {
                presence "Indicates a enable node is configured.";
                description
                  "Enable TCA reporting";
              }
            }
            container rx-crc-err {
              description
                "set rx-crc-err TCA reporting status";
              container enable {
                presence "Indicates a enable node is configured.";
                description
                  "Enable TCA reporting";
              }
            }
            container rx-lfd-stats {
              description
                "set rx-lfd-stats TCA reporting status";
              container enable {
                presence "Indicates a enable node is configured.";
                description
                  "Enable TCA reporting";
              }
            }
            container rx-csf-stats {
              description
                "set rx-csf-stats TCA reporting status";
              container enable {
                presence "Indicates a enable node is configured.";
                description
                  "Enable TCA reporting";
              }
            }
          }
        }
        container optics {
          description
            "Configure optics performance monitoring";
          container threshold {
            description
              "Configure threshold on optics parameters";
            container lbc {
              description
                "set lbc threshold";
              leaf min {
                type uint32 {
                  range "1..4294967294" {
                    description
                      "lbc min threshold (mA)";
                  }
                }
                description
                  "set lbc min threshold";
              }
              leaf max {
                type uint32 {
                  range "1..4294967294" {
                    description
                      "lbc max threshold (mA)";
                  }
                }
                description
                  "set lbc max threshold";
              }
            }
            container lbc-pc {
              description
                "set lbc % threshold";
              leaf min {
                type uint32 {
                  range "0..1000" {
                    description
                      "lbc min threshold (in units of 0.1%)";
                  }
                }
                description
                  "set lbc % min threshold";
              }
              leaf max {
                type uint32 {
                  range "0..1000" {
                    description
                      "lbc max threshold (in units of 0.1%)";
                  }
                }
                description
                  "set lbc % max threshold";
              }
            }
            container opt {
              description
                "set opt threshold in uW";
              leaf min {
                type uint32 {
                  range "1..4294967294" {
                    description
                      "opt min threshold (uW)";
                  }
                }
                description
                  "set opt min threshold in uW";
              }
              leaf max {
                type uint32 {
                  range "1..4294967294" {
                    description
                      "opt max threshold (uW)";
                  }
                }
                description
                  "set opt max threshold in uW";
              }
            }
            container opr {
              description
                "set opr threshold in uW ";
              leaf min {
                type uint32 {
                  range "1..4294967294" {
                    description
                      "opr min threshold (uW)";
                  }
                }
                description
                  "set opr min threshold in uW";
              }
              leaf max {
                type uint32 {
                  range "1..4294967294" {
                    description
                      "opr max threshold (uW)";
                  }
                }
                description
                  "set opr max threshold in uW";
              }
            }
            container dgd {
              description
                "set differential group delay threshold";
              leaf min {
                type uint32 {
                  range "1..4294967294" {
                    description
                      "differential group delay min threshold (1/100th of ps)";
                  }
                }
                description
                  "set differential group delay min threshold";
              }
              leaf max {
                type uint32 {
                  range "1..4294967294" {
                    description
                      "differential delay group max threshold (1/100th of ps)";
                  }
                }
                description
                  "set differential group delay max threshold";
              }
            }
            container sopmd {
              description
                "set second order polarization mode dispersion threshold";
              leaf min {
                type uint32 {
                  range "1..4294967294" {
                    description
                      "polarization mode dispersion min threshold (in units of 0.01 ps^2)";
                  }
                }
                description
                  "set polarization mode dispersion min threshold";
              }
              leaf max {
                type uint32 {
                  range "1..4294967294" {
                    description
                      "polarization mode dispersion max threshold ( in units of 0.01  ps^2)";
                  }
                }
                description
                  "set polarization mode dispersion max threshold";
              }
            }
            container osnr {
              description
                "set optical signal to noise ratio threshold";
              leaf min {
                type uint32 {
                  range "1..4294967294" {
                    description
                      "optical signal to noise ratio min threshold (1/100th of dB)";
                  }
                }
                description
                  "set optical signal to noise ratio min threshold";
              }
              leaf max {
                type uint32 {
                  range "1..4294967294" {
                    description
                      "optical signal to noise ratio max threshold (1/100th of dB)";
                  }
                }
                description
                  "set optical siganl to noise max threshold";
              }
            }
            container pdl {
              description
                "set polarization dependent loss threshold";
              leaf min {
                type uint32 {
                  range "1..4294967294" {
                    description
                      "polarization dependent loss min threshold (1/100th of dB)";
                  }
                }
                description
                  "set polarization dependent loss min threshold";
              }
              leaf max {
                type uint32 {
                  range "1..4294967294" {
                    description
                      "polarization dependent loss max threshold (1/100th of dB)";
                  }
                }
                description
                  "set polarization dependent loss max threshold";
              }
            }
            container pcr {
              description
                "set polarization change rate threshold";
              leaf min {
                type uint32 {
                  range "1..4294967294" {
                    description
                      "polarization change rate min threshold (in units of 0.01 rad/s)";
                  }
                }
                description
                  "set polarization change rate min threshold";
              }
              leaf max {
                type uint32 {
                  range "1..4294967294" {
                    description
                      "polarization change rate max threshold (in units of 0.01 rad/s)";
                  }
                }
                description
                  "set polarization change rate max threshold";
              }
            }
            container pn {
              description
                "set phase noise threshold";
              leaf min {
                type uint32 {
                  range "1..4294967294" {
                    description
                      "phase noise min threshold (1/1000 dB)";
                  }
                }
                description
                  "set phase noise min threshold";
              }
              leaf max {
                type uint32 {
                  range "1..4294967290" {
                    description
                      "phase noise max threshold (1/1000 dB)";
                  }
                }
                description
                  "set phase noise max threshold";
              }
            }
            container rx-sig-pow {
              description
                "set rx sig power threshold in uW";
              leaf min {
                type uint32 {
                  range "1..4294967290" {
                    description
                      " rx sig power threshold in uW";
                  }
                }
                description
                  "rx sig power min threshold in uW ";
              }
              leaf max {
                type uint32 {
                  range "1..4294967290" {
                    description
                      "rx sig power max threshold in uW";
                  }
                }
                description
                  "set rx sig power max threshold in uW";
              }
            }
            container snr {
              description
                "set SNR threshold";
              leaf min {
                type uint32 {
                  range "1..2147483646" {
                    description
                      "SNR min threshold";
                  }
                }
                description
                  "set SNR min threshold ";
              }
              leaf max {
                type uint32 {
                  range "1..2147483646" {
                    description
                      "SNR max threshold ";
                  }
                }
                description
                  "set SNR max threshold ";
              }
            }
            container snr-ax {
              description
                "set SNR AX threshold";
              leaf min {
                type uint32 {
                  range "1..2147483646" {
                    description
                      "SNR AX min threshold";
                  }
                }
                description
                  "set SNR AX min threshold ";
              }
              leaf max {
                type uint32 {
                  range "1..2147483646" {
                    description
                      "SNR AX max threshold ";
                  }
                }
                description
                  "set SNR AX max threshold ";
              }
            }
            container snr-bx {
              description
                "set SNR BX threshold";
              leaf min {
                type uint32 {
                  range "1..2147483646" {
                    description
                      "SNR BX min threshold";
                  }
                }
                description
                  "set SNR BX min threshold ";
              }
              leaf max {
                type uint32 {
                  range "1..2147483646" {
                    description
                      "SNR BX max threshold ";
                  }
                }
                description
                  "set SNR BX max threshold ";
              }
            }
            container snr-ay {
              description
                "set SNR AY threshold";
              leaf min {
                type uint32 {
                  range "1..2147483646" {
                    description
                      "SNR AY min threshold";
                  }
                }
                description
                  "set SNR AY min threshold ";
              }
              leaf max {
                type uint32 {
                  range "1..2147483646" {
                    description
                      "SNR AY max threshold ";
                  }
                }
                description
                  "set SNR AY max threshold ";
              }
            }
            container snr-by {
              description
                "set SNR BY threshold";
              leaf min {
                type uint32 {
                  range "1..2147483646" {
                    description
                      "SNR BY min threshold";
                  }
                }
                description
                  "set SNR BY min threshold ";
              }
              leaf max {
                type uint32 {
                  range "1..2147483646" {
                    description
                      "SNR BY max threshold ";
                  }
                }
                description
                  "set SNR BY max threshold ";
              }
            }
            container cd {
              description
                "set chromatic dispersion threshold";
              leaf min {
                type int32 {
                  range "-350000..350000" {
                    description
                      "chromatic dispersion min threshold (ps/nm)";
                  }
                }
                description
                  "set chromatic dispersion min threshold";
              }
              leaf max {
                type int32 {
                  range "-350000..350000" {
                    description
                      "chromatic dispersion max threshold (ps/nm)";
                  }
                }
                description
                  "set chromatic dispersion max threshold";
              }
            }
            container opt-dbm {
              description
                "set opt threshold in dbm";
              leaf min {
                type int32 {
                  range "-3000..6633" {
                    description
                      "Enter 4 digit value ;Input value 3000 for 30.00dbm";
                  }
                }
                description
                  "set opt min threshold in dbm";
              }
              leaf max {
                type int32 {
                  range "-3000..6633" {
                    description
                      "Enter 4 digit value ;Input value 3000 for 30.00dbm";
                  }
                }
                description
                  "set opt max threshold in dbm";
              }
            }
            container opr-dbm {
              description
                "set opr threshold in dbm";
              leaf min {
                type int32 {
                  range "-3000..6633" {
                    description
                      "Enter 4 digit value ;Input value 3000 for 30.00dbm";
                  }
                }
                description
                  "set opr min threshold in dbm";
              }
              leaf max {
                type int32 {
                  range "-3000..6633" {
                    description
                      "Enter 4 digit value ;Input value 3000 for 30.00dbm";
                  }
                }
                description
                  "set opr max threshold in dbm";
              }
            }
            container rx-sig-pow-dbm {
              description
                "set rx-sig-pow threshold in dbm";
              leaf min {
                type int32 {
                  range "-3000..6633" {
                    description
                      "Enter 4 digit value ;Input value 3000 for 30.00dbm";
                  }
                }
                description
                  "set rx-sig-pow min threshold in dbm";
              }
              leaf max {
                type int32 {
                  range "-3000..6633" {
                    description
                      "Enter 4 digit value ;Input value 3000 for 30.00dbm";
                  }
                }
                description
                  "set rx-sig-pow max threshold in dbm";
              }
            }
            container low-freq-off {
              description
                "set low signal freq offset threshold in Mhz";
              leaf min {
                type int32 {
                  range "-1500..1500" {
                    description
                      "low signal freq offset min threshold in Mhz";
                  }
                }
                description
                  "set low signal freq offset min threshold in Mhz";
              }
              leaf max {
                type int32 {
                  range "-1500..1500" {
                    description
                      "low signal freq offset max threshold in Mhz";
                  }
                }
                description
                  "set low signal freq offset max threshold in Mhz";
              }
            }
            container sop-s1 {
              description
                "set SOP S1 threshold ";
              leaf min {
                type int32 {
                  range "-100..100" {
                    description
                      "SOP S1 threshold ";
                  }
                }
                description
                  "set SOP S1 min threshold ";
              }
              leaf max {
                type int32 {
                  range "-100..100" {
                    description
                      "SOP S1 max threshold ";
                  }
                }
                description
                  "set SOP S1 max threshold ";
              }
            }
            container sop-s2 {
              description
                "set SOP S2 threshold ";
              leaf min {
                type int32 {
                  range "-100..100" {
                    description
                      "SOP S2 threshold ";
                  }
                }
                description
                  "set SOP S2 min threshold ";
              }
              leaf max {
                type int32 {
                  range "-100..100" {
                    description
                      "SOP S2 max threshold ";
                  }
                }
                description
                  "set SOP S2 max threshold ";
              }
            }
            container sop-s3 {
              description
                "set SOP S3 threshold ";
              leaf min {
                type int32 {
                  range "-100..100" {
                    description
                      "SOP S3 threshold ";
                  }
                }
                description
                  "set SOP S3 min threshold ";
              }
              leaf max {
                type int32 {
                  range "-100..100" {
                    description
                      "SOP S3 max threshold ";
                  }
                }
                description
                  "set SOP S3 max threshold ";
              }
            }
          }
          container report {
            description
              "set optics TCA reporting status";
            container lbc {
              description
                "set lbc TCA reporting status";
              container min-tca {
                description
                  "set lbc min TCA reporting status";
                container enable {
                  presence "Indicates a enable node is configured.";
                  description
                    "Enable TCA reporting";
                }
              }
              container max-tca {
                description
                  "set lbc max TCA reporting status";
                container enable {
                  presence "Indicates a enable node is configured.";
                  description
                    "Enable TCA reporting";
                }
              }
            }
            container lbc-pc {
              description
                "set lbc % TCA reporting status";
              container min-tca {
                description
                  "set lbc min % TCA reporting status";
                container enable {
                  presence "Indicates a enable node is configured.";
                  description
                    "Enable TCA reporting";
                }
              }
              container max-tca {
                description
                  "set lbc max % TCA reporting status";
                container enable {
                  presence "Indicates a enable node is configured.";
                  description
                    "Enable TCA reporting";
                }
              }
            }
            container opt {
              description
                "set opt/opt-dbm TCA reporting status";
              container min-tca {
                description
                  "set opt/opt-dbm min TCA reporting status";
                container enable {
                  presence "Indicates a enable node is configured.";
                  description
                    "Enable TCA reporting";
                }
              }
              container max-tca {
                description
                  "set opt/opt-dbm max TCA reporting status";
                container enable {
                  presence "Indicates a enable node is configured.";
                  description
                    "Enable TCA reporting";
                }
              }
            }
            container opr {
              description
                "set opr/opr-dbm TCA reporting status";
              container min-tca {
                description
                  "set opr/opr-dbm min TCA reporting status";
                container enable {
                  presence "Indicates a enable node is configured.";
                  description
                    "Enable TCA reporting";
                }
              }
              container max-tca {
                description
                  "set opr/opr-dbm max TCA reporting status";
                container enable {
                  presence "Indicates a enable node is configured.";
                  description
                    "Enable TCA reporting";
                }
              }
            }
            container cd {
              description
                "set chromatic dispersion TCA reporting status";
              container min-tca {
                description
                  "set chromatic dispersion min TCA reporting status";
                container enable {
                  presence "Indicates a enable node is configured.";
                  description
                    "Enable TCA reporting";
                }
              }
              container max-tca {
                description
                  "set chromatic dispersion max TCA reporting status";
                container enable {
                  presence "Indicates a enable node is configured.";
                  description
                    "Enable TCA reporting";
                }
              }
            }
            container dgd {
              description
                "set differential group delay TCA reporting status";
              container min-tca {
                description
                  "set differentail group delay min TCA reporting status";
                container enable {
                  presence "Indicates a enable node is configured.";
                  description
                    "Enable TCA reporting";
                }
              }
              container max-tca {
                description
                  "set differential group delay max TCA reporting status";
                container enable {
                  presence "Indicates a enable node is configured.";
                  description
                    "Enable TCA reporting";
                }
              }
            }
            container sopmd {
              description
                "set second order polarization mode dispersion TCA reporting status";
              container min-tca {
                description
                  "set polarization mode dispersion min TCA reporting status";
                container enable {
                  presence "Indicates a enable node is configured.";
                  description
                    "Enable TCA reporting";
                }
              }
              container max-tca {
                description
                  "set polarization mode dispersion max TCA reporting status";
                container enable {
                  presence "Indicates a enable node is configured.";
                  description
                    "Enable TCA reporting";
                }
              }
            }
            container osnr {
              description
                "set optical signal to noise ratio TCA reporting status";
              container min-tca {
                description
                  "set optical signal to noise ratio min TCA reporting status";
                container enable {
                  presence "Indicates a enable node is configured.";
                  description
                    "Enable TCA reporting";
                }
              }
              container max-tca {
                description
                  "set optical signal to noise ratio max TCA reporting status";
                container enable {
                  presence "Indicates a enable node is configured.";
                  description
                    "Enable TCA reporting";
                }
              }
            }
            container pdl {
              description
                "set polarization dependent loss TCA reporting status";
              container min-tca {
                description
                  "set polarization dependent loss min TCA reporting status";
                container enable {
                  presence "Indicates a enable node is configured.";
                  description
                    "Enable TCA reporting";
                }
              }
              container max-tca {
                description
                  "set polarization dependent loss max TCA reporting status";
                container enable {
                  presence "Indicates a enable node is configured.";
                  description
                    "Enable TCA reporting";
                }
              }
            }
            container pcr {
              description
                "set polarization change rate TCA reporting status";
              container min-tca {
                description
                  "set polarization change rate min TCA reporting status";
                container enable {
                  presence "Indicates a enable node is configured.";
                  description
                    "Enable TCA reporting";
                }
              }
              container max-tca {
                description
                  "set polarization change rate max TCA reporting status";
                container enable {
                  presence "Indicates a enable node is configured.";
                  description
                    "Enable TCA reporting";
                }
              }
            }
            container pn {
              description
                "set phase noise TCA reporting status";
              container min-tca {
                description
                  "set phase noise min TCA reporting status";
                container enable {
                  presence "Indicates a enable node is configured.";
                  description
                    "Enable TCA reporting";
                }
              }
              container max-tca {
                description
                  "set phase noise max TCA reporting status";
                container enable {
                  presence "Indicates a enable node is configured.";
                  description
                    "Enable TCA reporting";
                }
              }
            }
            container rx-sig-pow {
              description
                "set rx sig power TCA reporting status";
              container min-tca {
                description
                  "set rx sig power(uW/dBm) min TCA reporting status";
                container enable {
                  presence "Indicates a enable node is configured.";
                  description
                    "Enable TCA reporting";
                }
              }
              container max-tca {
                description
                  "set rx sig power(uW/dBm) max TCA reporting status";
                container enable {
                  presence "Indicates a enable node is configured.";
                  description
                    "Enable TCA reporting";
                }
              }
            }
            container low-freq-off {
              description
                "set low signal freq offset TCA reporting status";
              container min-tca {
                description
                  "set low signal freq offset min TCA reporting status";
                container enable {
                  presence "Indicates a enable node is configured.";
                  description
                    "Enable TCA reporting";
                }
              }
              container max-tca {
                description
                  "set low signal freq offset max TCA reporting status";
                container enable {
                  presence "Indicates a enable node is configured.";
                  description
                    "Enable TCA reporting";
                }
              }
            }
            container snr {
              description
                "set SNR TCA reporting status";
              container min-tca {
                description
                  "set SNR min TCA reporting status";
                container enable {
                  presence "Indicates a enable node is configured.";
                  description
                    "Enable TCA reporting";
                }
              }
              container max-tca {
                description
                  "set SNR max TCA reporting status";
                container enable {
                  presence "Indicates a enable node is configured.";
                  description
                    "Enable TCA reporting";
                }
              }
            }
            container snr-ax {
              description
                "set SNR-AX TCA reporting status";
              container min-tca {
                description
                  "set SNR-AX min TCA reporting status";
                container enable {
                  presence "Indicates a enable node is configured.";
                  description
                    "Enable TCA reporting";
                }
              }
              container max-tca {
                description
                  "set SNR-AX max TCA reporting status";
                container enable {
                  presence "Indicates a enable node is configured.";
                  description
                    "Enable TCA reporting";
                }
              }
            }
            container snr-bx {
              description
                "set SNR-BX TCA reporting status";
              container min-tca {
                description
                  "set SNR-BX min TCA reporting status";
                container enable {
                  presence "Indicates a enable node is configured.";
                  description
                    "Enable TCA reporting";
                }
              }
              container max-tca {
                description
                  "set SNR-BX max TCA reporting status";
                container enable {
                  presence "Indicates a enable node is configured.";
                  description
                    "Enable TCA reporting";
                }
              }
            }
            container snr-ay {
              description
                "set SNR-AY TCA reporting status";
              container min-tca {
                description
                  "set SNR-AY min TCA reporting status";
                container enable {
                  presence "Indicates a enable node is configured.";
                  description
                    "Enable TCA reporting";
                }
              }
              container max-tca {
                description
                  "set SNR-AY max TCA reporting status";
                container enable {
                  presence "Indicates a enable node is configured.";
                  description
                    "Enable TCA reporting";
                }
              }
            }
            container snr-by {
              description
                "set SNR-BY TCA reporting status";
              container min-tca {
                description
                  "set SNR-BY min TCA reporting status";
                container enable {
                  presence "Indicates a enable node is configured.";
                  description
                    "Enable TCA reporting";
                }
              }
              container max-tca {
                description
                  "set SNR-BY max TCA reporting status";
                container enable {
                  presence "Indicates a enable node is configured.";
                  description
                    "Enable TCA reporting";
                }
              }
            }
            container sop-s1 {
              description
                "set SOP-S1 TCA reporting status";
              container min-tca {
                description
                  "set SOP-S1 min TCA reporting status";
                container enable {
                  presence "Indicates a enable node is configured.";
                  description
                    "Enable TCA reporting";
                }
              }
              container max-tca {
                description
                  "set SOP-S1 max TCA reporting status";
                container enable {
                  presence "Indicates a enable node is configured.";
                  description
                    "Enable TCA reporting";
                }
              }
            }
            container sop-s2 {
              description
                "set SOP-S2 TCA reporting status";
              container min-tca {
                description
                  "set SOP-S2 min TCA reporting status";
                container enable {
                  presence "Indicates a enable node is configured.";
                  description
                    "Enable TCA reporting";
                }
              }
              container max-tca {
                description
                  "set SOP-S2 max TCA reporting status";
                container enable {
                  presence "Indicates a enable node is configured.";
                  description
                    "Enable TCA reporting";
                }
              }
            }
            container sop-s3 {
              description
                "set SOP-S3 TCA reporting status";
              container min-tca {
                description
                  "set SOP-S3 min TCA reporting status";
                container enable {
                  presence "Indicates a enable node is configured.";
                  description
                    "Enable TCA reporting";
                }
              }
              container max-tca {
                description
                  "set SOP-S3 max TCA reporting status";
                container enable {
                  presence "Indicates a enable node is configured.";
                  description
                    "Enable TCA reporting";
                }
              }
            }
          }
        }
        container fec {
          description
            "Configure fec g709 performance monitoring";
          container threshold {
            description
              "Configure fec threshold";
            leaf ec-bits {
              type xr:Cisco-ios-xr-string {
                length "1..20" {
                  description
                    "ec-bits threshold  <range:0-75279974400>";
                }
              }
              description
                "set EC-BITS threshold";
            }
            leaf uc-words {
              type xr:Cisco-ios-xr-string {
                length "1..20" {
                  description
                    "uc-words threshold <range:0-4724697600>";
                }
              }
              description
                "set UC-WORDS threshold";
            }
            container pre-fec-ber {
              description
                "Set PRE-FEC-BER Thresholds";
              leaf min {
                type xr:Cisco-ios-xr-string {
                  length "1..20" {
                    description
                      "pre-fec-ber min threshold range : <1-18446744073709551615>. BER is based on E-15, set value = 150, equivalent BER = 1.5E-13";
                  }
                }
                description
                  "set pre-fec-ber min threshold";
              }
              leaf max {
                type xr:Cisco-ios-xr-string {
                  length "1..20" {
                    description
                      "pre-fec-ber max threshold range : <1-18446744073709551615>. BER is based on E-15, set value = 150, equivalent BER = 1.5E-13";
                  }
                }
                description
                  "set pre-fec-ber max threshold";
              }
            }
            container post-fec-ber {
              description
                "Set POST-FEC-BER Thresholds";
              leaf min {
                type xr:Cisco-ios-xr-string {
                  length "1..20" {
                    description
                      "post-fec-ber min threshold range : <1-18446744073709551615>. BER is based on E-15, set value = 150, equivalent BER = 1.5E-13";
                  }
                }
                description
                  "set post-fec-ber min threshold";
              }
              leaf max {
                type xr:Cisco-ios-xr-string {
                  length "1..20" {
                    description
                      "post-fec-ber max threshold range : <1-18446744073709551615>. BER is based on E-15, set value = 150, equivalent BER = 1.5E-13";
                  }
                }
                description
                  "set post-fec-ber max threshold";
              }
            }
            container q {
              description
                "set Q threshold";
              leaf min {
                type xr:Cisco-ios-xr-string {
                  length "1..20" {
                    description
                      "Q min threshold <1-18446744073709551615>set value = 150, equivalent value = 1.5";
                  }
                }
                description
                  "set Q min threshold";
              }
              leaf max {
                type xr:Cisco-ios-xr-string {
                  length "1..20" {
                    description
                      "Q max threshold <1-18446744073709551615>set value = 150, equivalent value = 1.5";
                  }
                }
                description
                  "set Q max threshold";
              }
            }
            container q-margin {
              description
                "set Q margin threshold";
              leaf min {
                type xr:Cisco-ios-xr-string {
                  length "1..20" {
                    description
                      "Q margin min threshold <1-18446744073709551615>set value = 150, equivalent value = 1.5";
                  }
                }
                description
                  "set Q margin min threshold";
              }
              leaf max {
                type xr:Cisco-ios-xr-string {
                  length "1..20" {
                    description
                      "Q margin max threshold <1-18446744073709551615>set value = 150, equivalent value = 1.5";
                  }
                }
                description
                  "set Q margin max threshold";
              }
            }
            container inst-q-margin {
              description
                "set Instantaneous Q margin threshold";
              leaf min {
                type xr:Cisco-ios-xr-string {
                  length "1..20" {
                    description
                      "Instantaneous Q margin min threshold <1-18446744073709551615>set value = 150, equivalent value = 1.5";
                  }
                }
                description
                  "set Instantaneous Q margin min threshold";
              }
              leaf max {
                type xr:Cisco-ios-xr-string {
                  length "1..20" {
                    description
                      "Q margin max threshold <1-18446744073709551615>set value = 150, equivalent value = 1.5";
                  }
                }
                description
                  "set Instantaneous Q margin max threshold";
              }
            }
          }
          container report {
            description
              "set fec TCA reporting status";
            container ec-bits {
              description
                "set ec-bits TCA reporting status";
              container enable {
                presence "Indicates a enable node is configured.";
                description
                  "Enable TCA reporting";
              }
            }
            container uc-words {
              description
                "set uc-words TCA reporting status";
              container enable {
                presence "Indicates a enable node is configured.";
                description
                  "Enable TCA reporting";
              }
            }
          }
        }
        container prbs {
          description
            "Configure prbs performance monitoring";
          container threshold {
            description
              "Configure prbs threshold";
            leaf ebc {
              type xr:Cisco-ios-xr-string {
                length "1..20" {
                  description
                    "ebc threshold <1-18446744073709551615>";
                }
              }
              description
                "set EBC threshold";
            }
            leaf found-count {
              type xr:Cisco-ios-xr-string {
                length "1..10" {
                  description
                    "found-count threshold <1-4294967295>";
                }
              }
              description
                "set FOUND-COUNT threshold";
            }
            leaf lost-count {
              type xr:Cisco-ios-xr-string {
                length "1..10" {
                  description
                    "lost-count threshold <1-4294967295>";
                }
              }
              description
                "set LOST-COUNT threshold";
            }
          }
          container report {
            description
              "set prbs TCA reporting status";
            container ebc {
              description
                "set ebc TCA reporting status";
              container enable {
                presence "Indicates a enable node is configured.";
                description
                  "Enable TCA reporting";
              }
            }
            container found-count {
              description
                "set found-count TCA reporting status";
              container enable {
                presence "Indicates a enable node is configured.";
                description
                  "Enable TCA reporting";
              }
            }
            container lost-count {
              description
                "set lost-count TCA reporting status";
              container enable {
                presence "Indicates a enable node is configured.";
                description
                  "Enable TCA reporting";
              }
            }
          }
        }
      }
    }
  }

  augment "/a1:controllers/a1:controller" {
    description
      "This augment extends active nodes configuration";
    uses CONT-BODY;
  }

  augment "/a1:controllers/a1:controller-preconfigure" {
    description
      "This augment extends preconfigured nodes
       configuration";
    uses CONT-BODY;
  }
}
