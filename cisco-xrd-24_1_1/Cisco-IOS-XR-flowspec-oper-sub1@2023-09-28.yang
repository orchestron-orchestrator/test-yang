submodule Cisco-IOS-XR-flowspec-oper-sub1 {

  belongs-to Cisco-IOS-XR-flowspec-oper {
    prefix Cisco-IOS-XR-flowspec-oper;
  }

  /*** LINKAGE (IMPORTS / INCLUDES) ***/

  import ietf-inet-types { prefix "inet"; }

  import cisco-semver { prefix "semver"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR flowspec package operational data.

     Copyright (c) 2013-2023 by Cisco Systems, Inc.
     All rights reserved.";

  revision "2023-09-28" {
    description
      "Added support to include transmitted packets
       2023-07-03
         Added support to fetch total-inactive-flows.
       2023-01-19
         Modified bag file to add support for NOT in tcp flag.";
    semver:module-version "1.1.0";
  }

  revision "2019-04-05" {
    description
      "Establish semantic version baseline.";
    semver:module-version "1.0.0";
  }

  revision "2015-11-09" {
    description
      "IOS XR 6.0 revision.";
  }

  typedef Fs-mgr-client-state {
    type enumeration {
      enum dormant {
        description "Dormant";
      }
      enum connected {
        description "Connected";
      }
      enum replay {
        description "Replay";
      }
      enum unconfigured {
        description "Unconfigured";
      }
    }
    description "FlowSpec manager client state";
  }

  grouping FS-MGR-TCP-FLAG {
    description "Flowspec tcp flag information";
    leaf value {
      type uint16;
      description "value";
    }
    leaf match-any {
      type boolean;
      description "match any";
    }
    leaf match-not {
      type boolean;
      description "match not";
    }
  }

  grouping UINT16-RNG-ST {
    description "UINT16 RNG ST";
    leaf min {
      type uint16;
      description "Lower limit of the range";
    }
    leaf max {
      type uint16;
      description "Upper limit of the range";
    }
  }

  grouping UINT16-RNG-ARRAY {
    description "UINT16 RNG ARRAY";

    list uint16_rng_array {
      description "uint16 rng array";
      uses UINT16-RNG-ST;
    }
  }

  grouping UINT8-RNG-ST {
    description "UINT8 RNG ST";
    leaf min {
      type uint8;
      description "Lower limit of the range";
    }
    leaf max {
      type uint8;
      description "Upper limit of the range";
    }
  }

  grouping UINT8-RNG-ARRAY {
    description "UINT8 RNG ARRAY";

    list uint8_rng_array {
      description "uint8 rng array";
      uses UINT8-RNG-ST;
    }
  }

  grouping PROTO-ICMP-ST {
    description "PROTO ICMP ST";
    leaf type {
      type uint8;
      description "Protocol type";
    }
    leaf code {
      type uint8;
      description "Protocol code";
    }
  }

  grouping MATCH-IPV6-ST {
    description "MATCH IPV6 ST";
    leaf prefix {
      type inet:ipv6-address;
      description "IPV6 prefix";
    }
    leaf mask {
      type uint32;
      description "IPV6 mask";
    }
  }

  grouping MATCH-IPV4-ST {
    description "Source Address IPv4";
    leaf prefix {
      type inet:ipv4-address;
      description "prefix";
    }
    leaf mask {
      type inet:ipv4-address;
      description "mask";
    }
  }

  grouping FS-MGR-FLOW-MATCH {
    description "Flowspec client match.";

    container destination-prefix-ipv4 {
      description "IPv4 Destination Prefix";
      uses MATCH-IPV4-ST;
    }

    container destination-prefix-ipv6 {
      description "IPv6 Destination Prefix";
      uses MATCH-IPV6-ST;
    }

    container source-prefix-ipv4 {
      description "IPv4 Source Prefix";
      uses MATCH-IPV4-ST;
    }

    container source-prefix-ipv6 {
      description "IPv6 Source Prefix";
      uses MATCH-IPV6-ST;
    }

    container icmp {
      description "Icmp Type/Code";
      uses PROTO-ICMP-ST;
    }

    container dscp {
      description "Dscp";
      uses UINT8-RNG-ARRAY;
    }

    container packet-length {
      description "Packet Length";
      uses UINT16-RNG-ARRAY;
    }

    container ip-protocol {
      description "IP Protocol";
      uses UINT16-RNG-ARRAY;
    }

    container tcp-flag {
      description "Tcp Flag";
      uses FS-MGR-TCP-FLAG;
    }

    container source-port {
      description "Source Port";
      uses UINT16-RNG-ARRAY;
    }

    container destination-port {
      description "Destination Port";
      uses UINT16-RNG-ARRAY;
    }
    leaf fragment-type {
      type string;
      description "fragment type";
    }
  }

  grouping FS-MGR-FLOW-STATS-CTRS {
    description "Flowspec class stats counters.";
    leaf packets {
      type uint64;
      description "Number of packets";
    }
    leaf bytes {
      type uint64;
      units "byte";
      description "Number of bytes";
    }
  }

  grouping FS-MGR-FLOW-STATS {
    description
      "Flowspec class classified, transmitted and drop
      stats.";

    container classified {
      description "Classified statistics";
      uses FS-MGR-FLOW-STATS-CTRS;
    }

    container transmitted {
      description "Transmitted statistics";
      uses FS-MGR-FLOW-STATS-CTRS;
    }

    container dropped {
      description "Drop statistics";
      uses FS-MGR-FLOW-STATS-CTRS;
    }
  }

  grouping FS-MGR-FLOW-ACTION {
    description "FlowSpec client action.";
    leaf rate {
      type uint64;
      description "rate";
    }
    leaf vrf-name {
      type string;
      description "vrf name";
    }
    leaf dscp {
      type uint8;
      description "dscp";
    }
    leaf ipv4-nh {
      type inet:ipv4-address;
      description "ipv4 nh";
    }
    leaf ipv6-nh {
      type inet:ipv6-address;
      description "ipv6 nh";
    }
    leaf route-target {
      type string;
      description "route target";
    }
  }

  grouping FS-MGR-FLOW-CLIENT {
    description "FlowSpec client flow.";

    list action {
      description "action";
      uses FS-MGR-FLOW-ACTION;
    }
  }

  grouping FS-MGR-NLRI {
    description "FlowSpec manager NLRI information";

    container synced-flow-client {
      description "synced flow client";
      uses FS-MGR-FLOW-CLIENT;
    }

    container active-flow-client {
      description "active flow client";
      uses FS-MGR-FLOW-CLIENT;
    }

    container flow-statistics {
      description
        "Flowspec classification, transmitted and drop
        statistics";
      uses FS-MGR-FLOW-STATS;
    }

    container matches {
      description "Match";
      uses FS-MGR-FLOW-MATCH;
    }

    list inactive-flow-client {
      description "inactive flow client";
      uses FS-MGR-FLOW-CLIENT;
    }
  }

  grouping FS-MGR-TBL-SUMMARY {
    description "FlowSpec manager table summary information";
    leaf total-flows {
      type uint32;
      description "Total number of flows";
    }
    leaf service-policies {
      type uint32;
      description "Total number of attached service policies";
    }
    leaf local-install-enabled {
      type boolean;
      description "Local installation of flowspec rules";
    }
    leaf total-inactive-flows {
      type uint32;
      description "Total number of inactive flows";
    }
  }

  grouping FS-MGR-SUMMARY {
    description "FlowSpec manager summary information";
    leaf vrfafi-tables {
      type uint32;
      description "Total VRF+AFI tables";
    }
    leaf flows {
      type uint32;
      description "Total flows";
    }
  }

  grouping FS-MGR-CLIENT {
    description "FlowSpec manager client information";
    leaf client-state {
      type Fs-mgr-client-state;
      description "State of FS client";
    }
    leaf client-flows {
      type uint32;
      description "Number of client flows";
    }
  }
}
