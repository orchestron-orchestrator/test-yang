module Cisco-IOS-XR-linux-security-factory-reset-act-deviations {

    /* Define the namespace and prefix for the deviation */
    namespace "http://cisco.com/ns/yang/Cisco-IOS-XR-linux-security-factory-reset-act-deviations";

    prefix "factory-reset-act-dev";

    /* import the original module and prefix */
    import Cisco-IOS-XR-linux-security-factory-reset-act { prefix "factory-reset-act"; }

    import cisco-semver { prefix "semver"; }

    organization "Cisco Systems, Inc.";

    contact
    "Cisco Systems, Inc.
     Customer Service

     Postal: 170 West Tasman Drive
     San Jose, CA 95134

     Tel: +1 800 553-NETS

     E-mail: cs-yang@cisco.com";

    description
    "This module contains a set of deviations for unsupported platforms
    for Cisco-IOS-XR-linux-security-factory-reset-act

     Copyright (c) 2022 by Cisco Systems, Inc.
     All rights reserved.";

    revision "2022-04-29" {
        description
            "IOS XR 7.8.1 revision.";
        semver:module-version "1.0.0";
    }


    /*
     * deviation: /original_prefix:original_rpc
     * only 8000 platform supports both RPCs.
     */

    deviation /factory-reset-act:factory-reset-shut {
        deviate not-supported;
    }

    deviation /factory-reset-act:factory-reset-reload {
        deviate not-supported;
    }
}

//total 2 deviations for factory reset act
