submodule Cisco-IOS-XR-snmp-agent-oper-sub4 {

  belongs-to Cisco-IOS-XR-snmp-agent-oper {
    prefix Cisco-IOS-XR-snmp-agent-oper;
  }

  /*** LINKAGE (IMPORTS / INCLUDES) ***/

  import cisco-semver { prefix "semver"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR snmp-agent package operational data.

     Copyright (c) 2013-2020 by Cisco Systems, Inc.
     All rights reserved.";

  revision "2020-09-15" {
    description
      "Updated oper path for show snmp traps details";
    semver:module-version "2.0.0";
  }

  revision "2020-03-31" {
    description
      "Fixing backward compatibility error in module.";
    semver:module-version "1.1.0";
  }

  revision "2019-04-05" {
    description
      "Establish semantic version baseline.";
    semver:module-version "1.0.1";
  }

  revision "2018-07-20" {
    description
      "Fixed English plural name transformation error.";
  }

  revision "2017-09-07" {
    description
      "Fixed type translation error.";
  }

  revision "2017-05-01" {
    description
      "Fixing backward compatibility error in module.";
  }

  revision "2016-06-01" {
    description
      "IOS XR 6.0.1 revision.";
  }

  revision "2015-01-07" {
    description
      "IOS XR 5.3.1 revision.";
  }

  grouping SNMP-USM-USER-ENTRY {
    description "SNMP usmUserTable Information";
    leaf usm-user-storage-type {
      type uint32;
      description "Storage type";
    }
    leaf usm-user-status {
      type uint32;
      description "Status of this user";
    }
  }

  grouping SNMP-VACM-ACCESS-ENTRY {
    description "SNMP vacmAccessTable Information";
    leaf vacm-access-read-view-name {
      type string;
      description "Read view name";
    }
    leaf vacm-access-write-view-name {
      type string;
      description "Write view name";
    }
    leaf vacm-access-notify-view-name {
      type string;
      description "Notify view name";
    }
    leaf vacm-access-status {
      type uint32;
      description "Status of this view configuration";
    }
  }

  grouping SNMP-SNMP-VIEW-XML-ENTRY {
    description "SNMP SNMPViewXmlTable Information";
    leaf snmp-view-family-type {
      type string;
      description "Include or exclude";
    }
    leaf snmp-view-family-storage-type {
      type string;
      description "Storage type";
    }
    leaf snmp-view-family-status {
      type string;
      description "Status of this entry";
    }
  }

  grouping SNMP-SNMP-HOST-XML {
    description "SNMP host xml information";
    leaf snmp-target-address-t-host {
      type string;
      description "Transport type of address";
    }
    leaf snmp-target-address-port {
      type string;
      description "Target UDP port";
    }
    leaf snmp-target-addresstype {
      type string;
      description "Target host type (Inform or Trap)";
    }
    leaf snmp-target-params-security-model {
      type string;
      description "Security model";
    }
    leaf snmp-target-params-security-name {
      type string;
      description "Security name";
    }
    leaf snmp-target-params-security-level {
      type string;
      description "Security level";
    }
  }
}
