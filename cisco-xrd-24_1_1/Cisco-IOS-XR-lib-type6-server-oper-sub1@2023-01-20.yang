submodule Cisco-IOS-XR-lib-type6-server-oper-sub1 {

  belongs-to Cisco-IOS-XR-lib-type6-server-oper {
    prefix Cisco-IOS-XR-lib-type6-server-oper;
  }

  /*** LINKAGE (IMPORTS / INCLUDES) ***/

  import cisco-semver { prefix "semver"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR lib-type6-server package operational data.

     Copyright (c) 2013-2023 by Cisco Systems, Inc.
     All rights reserved.";

  revision "2023-01-20" {
    description
      "Added Timestamp feature";
    semver:module-version "1.2.0";
  }

  revision "2019-09-20" {
    description
      "Added support for new show CLI.";
    semver:module-version "1.1.0";
  }

  revision "2019-04-05" {
    description
      "Establish semantic version baseline.";
    semver:module-version "1.0.0";
  }

  revision "2018-09-28" {
    description
      "Fixed incorrect plural rendering.";
  }

  revision "2015-11-09" {
    description
      "IOS XR 6.0 revision.";
  }

  typedef String-array {
    type string;
    description "String array";
  }

  grouping TYPE6-CLIENT-INFO {
    description "TYPE6 CLIENT INFO";
    leaf client-name {
      type string;
      description "Client Name";
    }
    leaf mk-state {
      type string;
      description "Client masterkey state";
    }
  }

  grouping TYPE6-SERVER-INFO {
    description "TYPE6 SERVER INFO";
    leaf aes-config {
      type boolean;
      description "Aes config state";
    }
    leaf mk-config {
      type boolean;
      description "mk config state";
    }
    leaf type6-feature-state {
      type boolean;
      description "Type6 feature state";
    }
    leaf mk-inprogress-state {
      type boolean;
      description "mk inprogress state";
    }
    leaf mk-timestamp {
      type string;
      description "MK Timestamp";
    }
  }

  grouping TYPE6-CLIENT-STATE-BAG {
    description "TYPE6 CLIENT STATE BAG";
    leaf-list client-name {
      type String-array;
      description "Client Name";
    }
    leaf-list client-mkstate {
      type String-array;
      description "Client         masterkey operation state";
    }
  }

  grouping TYPE6-MK-UPDATE-BAG {
    description "TYPE6 MK UPDATE BAG";

    container client-info {
      description "Status of each client";
      uses TYPE6-CLIENT-STATE-BAG;
    }
    leaf message {
      type string;
      description "Masterkey operation         status";
    }
  }

  grouping TYPE6-MK-OPER-BAG {
    description "TYPE6 MK OPER BAG";

    container update-bag {
      description "Masterkey Update         status";
      uses TYPE6-MK-UPDATE-BAG;
    }
  }
}
