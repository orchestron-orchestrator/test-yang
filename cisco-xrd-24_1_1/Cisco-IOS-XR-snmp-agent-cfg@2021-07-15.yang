module Cisco-IOS-XR-snmp-agent-cfg {

  /*** NAMESPACE / PREFIX DEFINITION ***/

  namespace "http://cisco.com/ns/yang/Cisco-IOS-XR-snmp-agent-cfg";


  prefix "snmp-agent-cfg";

  /*** LINKAGE (IMPORTS / INCLUDES) ***/

  import ietf-inet-types { prefix "inet"; }

  import Cisco-IOS-XR-types { prefix "xr"; }

  import cisco-semver { prefix "semver"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR snmp-agent package configuration.

     This module contains definitions
     for the following management objects:
       snmp: The heirarchy point for all the SNMP configurations
       mib: The heirarchy point for all the MIB configurations

     Copyright (c) 2013-2021 by Cisco Systems, Inc.
     All rights reserved.";

  revision "2021-07-15" {
    description
      "New config for OPS Script OID added
       2021-05-15
         New config snmp tcp added";
    semver:module-version "3.2.0";
  }

  revision "2020-09-15" {
    description
      "New config snmp trap delay timer added";
    semver:module-version "3.1.0";
  }

  revision "2020-03-31" {
    description
      "CSCvs82990 Native yang model support for uncovered snmp-server cmds";
    semver:module-version "3.0.0";
  }

  revision "2019-11-21" {
    description
      "CSCvs07760 Changed host config schema default values in sync with cli
      2019-11-06
         Yang Support for snmp-agent components via bug CSCvk56072
      2019-10-31
         Added mandatory nodes.
      2019-06-13
         Added new option under host config via bug CSCvq13863";
    semver:module-version "2.0.0";
  }

  revision "2019-05-29" {
    description
      "Type6 algorithm support to configure SNMP community, community-map, host, vrf host and user via bug CSCvp30991.";
    semver:module-version "1.0.0";
  }

  revision "2019-04-05" {
    description
      "Establish semantic version baseline.";
  }

  revision "2018-06-27" {
    description
      "Error while configuring snmp-server host via netconf bug CSCvj92659.";
  }

  revision "2018-03-12" {
    description
      "Yang model support to configure snmp-server timeouts threshold 100000";
  }

  revision "2017-12-20" {
    description
      "Removed nonstateful class from correlator config";
  }

  revision "2017-10-15" {
    description
      "Removed presence statement generated from internal CLI data.";
  }

  revision "2017-09-07" {
    description
      "Fixed type translation error.";
  }

  revision "2017-05-01" {
    description
      "Fixing backward compatibility error in module.";
  }

  revision "2015-10-27" {
    description
      "IOS XR 5.3.2 revision.";
  }

  revision "2015-01-07" {
    description
      "IOS XR 5.3.1 revision.";
  }

  typedef Snmp-tos {
    type enumeration {
      enum precedence {
        value 0;
        description "SNMP TOS type Precedence";
      }
      enum dscp {
        value 1;
        description "SNMP TOS type DSCP";
      }
    }
    description "Snmp tos";
  }
  typedef Snmp-hash-algorithm {
    type enumeration {
      enum none {
        value 0;
        description "No authentication required";
      }
      enum md5 {
        value 1;
        description "Standard Message Digest algorithm";
      }
      enum sha {
        value 2;
        description "SHA algorithm";
      }
    }
    description "Snmp hash algorithm";
  }
  typedef Snmp-priv-algorithm {
    type enumeration {
      enum none {
        value 0;
        description "No Privacy";
      }
      enum des {
        value 1;
        description "Des algorithm";
      }
      enum 3des {
        value 2;
        description "3des algorithm";
      }
      enum aes128 {
        value 3;
        description "aes128 algorithm";
      }
      enum aes192 {
        value 4;
        description "aes192 algorithm";
      }
      enum aes256 {
        value 5;
        description "aes256 algorithm";
      }
    }
    description "Snmp priv algorithm";
  }
  typedef Snmp-owner-access {
    type enumeration {
      enum sdr-owner {
        value 0;
        description "Secure Domain Router Owner permissions";
      }
      enum system-owner {
        value 1;
        description "System owner permissions";
      }
    }
    description "Snmp owner access";
  }
  typedef Snmp-bulkstat-schema {
    type enumeration {
      enum exact-interface {
        value 1;
        description "Exact Interface";
      }
      enum exact-oid {
        value 2;
        description "Exact OID";
      }
      enum wild-interface {
        value 3;
        description "Wild Interface";
      }
      enum wild-oid {
        value 4;
        description "Wild OID";
      }
      enum range-oid {
        value 5;
        description "Range of OID";
      }
      enum repeat-oid {
        value 6;
        description "Repeated the instance";
      }
    }
    description "Snmp bulkstat schema";
  }
  typedef Snmpacl {
    type enumeration {
      enum ipv4 {
        value 1;
        description "Ipv4 Access-list";
      }
      enum ipv6 {
        value 2;
        description "Ipv6 Access-list";
      }
    }
    description "Snmpacl";
  }
  typedef Snmp-dscp-value {
    type union {
      type enumeration {
        enum default {
          value 0;
          description "Applicable to DSCP: bits 000000";
        }
        enum af11 {
          value 10;
          description "Applicable to DSCP: bits 001010";
        }
        enum af12 {
          value 12;
          description "Applicable to DSCP: bits 001100";
        }
        enum af13 {
          value 14;
          description "Applicable to DSCP: bits 001110";
        }
        enum af21 {
          value 18;
          description "Applicable to DSCP: bits 010010";
        }
        enum af22 {
          value 20;
          description "Applicable to DSCP: bits 010100";
        }
        enum af23 {
          value 22;
          description "Applicable to DSCP: bits 010110";
        }
        enum af31 {
          value 26;
          description "Applicable to DSCP: bits 011010";
        }
        enum af32 {
          value 28;
          description "Applicable to DSCP: bits 011100";
        }
        enum af33 {
          value 30;
          description "Applicable to DSCP: bits 011110";
        }
        enum af41 {
          value 34;
          description "Applicable to DSCP: bits 100010";
        }
        enum af42 {
          value 36;
          description "Applicable to DSCP: bits 100100";
        }
        enum af43 {
          value 38;
          description "Applicable to DSCP: bits 100110";
        }
        enum ef {
          value 46;
          description "Applicable to DSCP: bits 101110";
        }
        enum cs1 {
          value 8;
          description "Applicable to DSCP: bits 001000";
        }
        enum cs2 {
          value 16;
          description "Applicable to DSCP: bits 010000";
        }
        enum cs3 {
          value 24;
          description "Applicable to DSCP: bits 011000";
        }
        enum cs4 {
          value 32;
          description "Applicable to DSCP: bits 100000";
        }
        enum cs5 {
          value 40;
          description "Applicable to DSCP: bits 101000";
        }
        enum cs6 {
          value 48;
          description "Applicable to DSCP: bits 110000";
        }
        enum cs7 {
          value 56;
          description "Applicable to DSCP: bits 111000";
        }
      }
      type uint32 {
        range "0..63";
      }
    }
    description "Snmp dscp value";
  }
  typedef Snmp-precedence-value1 {
    type union {
      type enumeration {
        enum routine {
          value 0;
          description "Applicable to Precedence: value 0";
        }
        enum priority {
          value 1;
          description "Applicable to Precedence: value 1";
        }
        enum immediate {
          value 2;
          description "Applicable to Precedence: value 2";
        }
        enum flash {
          value 3;
          description "Applicable to Precedence: value 3";
        }
        enum flash-override {
          value 4;
          description "Applicable to Precedence: value 4";
        }
        enum critical {
          value 5;
          description "Applicable to Precedence: value 5";
        }
        enum internet {
          value 6;
          description "Applicable to Precedence: value 6";
        }
        enum network {
          value 7;
          description "Applicable to Precedence: value 7";
        }
      }
      type uint32 {
        range "0..7";
      }
    }
    description "Snmp precedence value1";
  }
  typedef Snmp-security-model {
    type enumeration {
      enum no-authentication {
        value 0;
        description "No Authentication required";
      }
      enum authentication {
        value 1;
        description
          "Authentication password alone required for
          access";
      }
      enum privacy {
        value 2;
        description
          "Authentication and privacy password required
          for access";
      }
    }
    description "Snmp security model";
  }
  typedef Snmp-mib-view-inclusion {
    type enumeration {
      enum included {
        value 1;
        description "MIB View to be included";
      }
      enum excluded {
        value 2;
        description "MIB View to be excluded";
      }
    }
    description "Snmp mib view inclusion";
  }
  typedef Snmp-bulkstat-file-format {
    type enumeration {
      enum schema-ascii {
        value 1;
        description "Tranfer file in schema Ascii format";
      }
      enum bulk-ascii {
        value 2;
        description "Tranfer file in Bulk Ascii format";
      }
      enum bulk-binary {
        value 3;
        description "Tranfer file in Bulk binary format";
      }
    }
    description "Snmp bulkstat file format";
  }
  typedef Snmp-access-level {
    type enumeration {
      enum read-only {
        value 0;
        description "Read Only Access for a community string";
      }
      enum read-write {
        value 1;
        description "Read Write Access for a community string";
      }
    }
    description "Snmp access level";
  }
  typedef Snmp-context {
    type enumeration {
      enum vrf {
        value 1;
        description "VRF feature";
      }
      enum bridge {
        value 4;
        description "BRIDGE feature";
      }
      enum ospf {
        value 5;
        description "OSPF feature";
      }
      enum ospfv3 {
        value 6;
        description "OSPFv3 feature";
      }
    }
    description "Snmp context";
  }
  typedef Group-snmp-version {
    type enumeration {
      enum v1 {
        value 0;
        description "SNMP version 1";
      }
      enum v2c {
        value 1;
        description "SNMP version 2";
      }
      enum v3 {
        value 2;
        description "SNMP version 3";
      }
    }
    description "Group snmp version";
  }
  typedef User-snmp-version {
    type enumeration {
      enum v1 {
        value 1;
        description "SNMP version 1";
      }
      enum v2c {
        value 2;
        description "SNMP version 2";
      }
      enum v3 {
        value 3;
        description "SNMP version 3";
      }
    }
    description "User snmp version";
  }

  grouping APPLIED-TO {
    description "Common node of rule, rule-set";

    container applied-to {
      description "Applied to the Rule or Ruleset";

      container hosts {
        description "Table of configured hosts to apply rules to";

        list host {
          key "ip-address port";
          description "A destination host";
          leaf ip-address {
            type inet:ip-address-no-zone;
            description "IP address";
          }
          leaf port {
            type xr:Cisco-ios-xr-port-number;
            description "Port (specify 162 for default)";
          }
        }
      }
      leaf all {
        type empty;
        description "Apply to all of the device";
      }
    }
  }

  grouping CONTEXT-TABLE {
    description "Common node of snmp, vrf";

    container contexts {
      description "List of Context Names";

      list context {
        key "context-name";
        description "Context Name";
        leaf context-name {
          type xr:Cisco-ios-xr-string;
          description "Context Name";
        }
      }
    }
  }

  grouping VAR-BIND-TABLE {
    description "Common node of root-cause, non-root-cause";

    container var-binds {
      description "Varbinds to match";

      list var-bind {
        key "oid";
        description "Varbind match conditions";

        container match {
          description "VarBind match conditions";
          leaf value {
            type string;
            description "Regular Expression to match value";
          }
          leaf index {
            type string;
            description "Regular Expression to match index";
          }
        }
        leaf oid {
          type string;
          description "OID of varbind (dotted decimal)";
        }
      }
    }
  }

  grouping TRAP-HOST-TABLE {
    description "Common node of snmp, vrf";

    container trap-hosts {
      description "Specify hosts to receive SNMP notifications";

      list trap-host {
        key "ip-address";
        description "Specify hosts to receive SNMP notifications";

        container encrypted-user-communities {
          description
            "Container class for defining default
            Clear/encrypt communities for a trap host";

          list encrypted-user-community {
            key "community-name";
            description
              "Default Clear/Encrypt Community name
              associated with a trap host";
            leaf community-name {
              type xr:Cisco-ios-xr-string;
              description
                "SNMPv1/v2c community string or SNMPv3 user";
            }
            leaf port {
              type xr:Cisco-ios-xr-port-number;
              description "UDP port number";
            }
            leaf version {
              type string;
              mandatory true;
              description "SNMP Version to be used 1/2c/3";
            }
            leaf security-level {
              type Snmp-security-model;
              description
                "Security level to be used noauth/auth/priv";
            }
            leaf basic-trap-types {
              type uint32;
              mandatory true;
              description
                "Number to signify the feature traps that
                needs to be setBasicTrapTypes is used for
                all traps except copy-completeSet this value
                to an integer corresponding to the trapBGP
                8192, CONFIG 4096,SYSLOG 131072,SNMP_TRAP
                1COPY_COMPLETE_TRAP 64To provide a
                combination of trap Add the respective
                numbersValue must be set to 0 for all traps";
            }
            leaf advanced-trap-types1 {
              type uint32;
              mandatory true;
              description
                "Number to signify the feature traps that
                needs to be setUse this for providing
                copy-complete trapValue must be set to 0 if
                not used";
            }
            leaf advanced-trap-types2 {
              type uint32;
              mandatory true;
              description
                "Number to signify the feature traps that
                needs to be setvalue should always to set as
                0";
            }
            leaf dying-gasp {
              type boolean;
              description "Enable dying gasp trap for this host";
            }
          }
        }

        container type6-encrypted-user-communities {
          description
            "Container class for defining type6
            Clear/encrypt communities for a trap host";

          list type6-encrypted-user-community {
            key "community-name";
            description
              "Type6 Clear/Encrypt Community name associated
              with a trap host";
            leaf community-name {
              type xr:Cisco-ios-xr-string;
              description
                "SNMPv1/v2c community string or SNMPv3 user";
            }
            leaf port {
              type xr:Cisco-ios-xr-port-number;
              description "UDP port number";
            }
            leaf version {
              type string;
              mandatory true;
              description "SNMP Version to be used 1/2c/3";
            }
            leaf security-level {
              type Snmp-security-model;
              description
                "Security level to be used noauth/auth/priv";
            }
            leaf basic-trap-types {
              type uint32;
              mandatory true;
              description
                "Number to signify the feature traps that
                needs to be setBasicTrapTypes is used for
                all traps except copy-completeSet this value
                to an integer corresponding to the trapBGP
                8192, CONFIG 4096,SYSLOG 131072,SNMP_TRAP
                1COPY_COMPLETE_TRAP 64To provide a
                combination of trap Add the respective
                numbersValue must be set to 0 for all traps";
            }
            leaf advanced-trap-types1 {
              type uint32;
              mandatory true;
              description
                "Number to signify the feature traps that
                needs to be setUse this for providing
                copy-complete trapValue must be set to 0 if
                not used";
            }
            leaf advanced-trap-types2 {
              type uint32;
              mandatory true;
              description
                "Number to signify the feature traps that
                needs to be setvalue should always to set as
                0";
            }
            leaf dying-gasp {
              type boolean;
              description "Enable dying gasp trap for this host";
            }
          }
        }

        container inform-host {
          description
            "Container class for defining notification type
            for a Inform host";

          container inform-user-communities {
            description
              "Container class for defining communities for
              a inform host";

            list inform-user-community {
              key "community-name";
              description
                "Unencrpted Community name associated with a
                inform host";
              leaf community-name {
                type xr:Cisco-ios-xr-string {
                  length "1..128";
                }
                description
                  "SNMPv2c community string or SNMPv3 user";
              }
              leaf port {
                type xr:Cisco-ios-xr-port-number;
                description "UDP port number";
              }
              leaf version {
                type string;
                mandatory true;
                description "SNMP Version to be used 2c/3";
              }
              leaf security-level {
                type Snmp-security-model;
                description
                  "Security level to be used noauth/auth/priv";
              }
              leaf basic-trap-types {
                type uint32;
                mandatory true;
                description
                  "Number to signify the feature traps that
                  needs to be setBasicTrapTypes is used for
                  all traps except copy-completeSet this
                  value to an integer corresponding to the
                  trapBGP 8192, CONFIG 4096,SYSLOG 131072
                  ,SNMP_TRAP 1COPY_COMPLETE_TRAP 64To provide
                  a combination of trap Add the respective
                  numbersValue must be set to 0 for all traps";
              }
              leaf advanced-trap-types1 {
                type uint32;
                mandatory true;
                description
                  "Number to signify the feature traps that
                  needs to be setUse this for providing
                  copy-complete trapValue must be set to 0 if
                  not used";
              }
              leaf advanced-trap-types2 {
                type uint32;
                mandatory true;
                description
                  "Number to signify the feature traps that
                  needs to be setvalue should always to set
                  as 0";
              }
              leaf dying-gasp {
                type boolean;
                description "Enable dying gasp trap for this host";
              }
            }
          }

          container inform-type6-encrypted-user-communities {
            description
              "Container class for defining type6
              Clear/encrypt communities for a inform host";

            list inform-type6-encrypted-user-community {
              key "community-name";
              description
                "Type6 Clear/Encrypt Community name
                associated with a inform host";
              leaf community-name {
                type xr:Cisco-ios-xr-string;
                description
                  "SNMPv2c community string or SNMPv3 user";
              }
              leaf port {
                type xr:Cisco-ios-xr-port-number;
                description "UDP port number";
              }
              leaf version {
                type string;
                mandatory true;
                description "SNMP Version to be used 2c/3";
              }
              leaf security-level {
                type Snmp-security-model;
                description
                  "Security level to be used noauth/auth/priv";
              }
              leaf basic-trap-types {
                type uint32;
                mandatory true;
                description
                  "Number to signify the feature traps that
                  needs to be setBasicTrapTypes is used for
                  all traps except copy-completeSet this
                  value to an integer corresponding to the
                  trapBGP 8192, CONFIG 4096,SYSLOG 131072
                  ,SNMP_TRAP 1COPY_COMPLETE_TRAP 64To provide
                  a combination of trap Add the respective
                  numbersValue must be set to 0 for all traps";
              }
              leaf advanced-trap-types1 {
                type uint32;
                mandatory true;
                description
                  "Number to signify the feature traps that
                  needs to be setUse this for providing
                  copy-complete trapValue must be set to 0 if
                  not used";
              }
              leaf advanced-trap-types2 {
                type uint32;
                mandatory true;
                description
                  "Number to signify the feature traps that
                  needs to be setvalue should always to set
                  as 0";
              }
              leaf dying-gasp {
                type boolean;
                description "Enable dying gasp trap for this host";
              }
            }
          }

          container inform-encrypted-user-communities {
            description
              "Container class for defining default
              Clear/encrypt communities for a inform host";

            list inform-encrypted-user-community {
              key "community-name";
              description
                "Clear/Encrypt Community name associated with
                a inform host";
              leaf community-name {
                type xr:Cisco-ios-xr-string;
                description
                  "SNMPv2c community string or SNMPv3 user";
              }
              leaf port {
                type xr:Cisco-ios-xr-port-number;
                description "UDP port number";
              }
              leaf version {
                type string;
                mandatory true;
                description "SNMP Version to be used 2c/3";
              }
              leaf security-level {
                type Snmp-security-model;
                description
                  "Security level to be used noauth/auth/priv";
              }
              leaf basic-trap-types {
                type uint32;
                mandatory true;
                description
                  "Number to signify the feature traps that
                  needs to be setBasicTrapTypes is used for
                  all traps except copy-completeSet this
                  value to an integer corresponding to the
                  trapBGP 8192, CONFIG 4096,SYSLOG 131072
                  ,SNMP_TRAP 1COPY_COMPLETE_TRAP 64To provide
                  a combination of trap Add the respective
                  numbersValue must be set to 0 for all traps";
              }
              leaf advanced-trap-types1 {
                type uint32;
                mandatory true;
                description
                  "Number to signify the feature traps that
                  needs to be setUse this for providing
                  copy-complete trapValue must be set to 0 if
                  not used";
              }
              leaf advanced-trap-types2 {
                type uint32;
                mandatory true;
                description
                  "Number to signify the feature traps that
                  needs to be setvalue should always to set
                  as 0";
              }
              leaf dying-gasp {
                type boolean;
                description "Enable dying gasp trap for this host";
              }
            }
          }
        }

        container default-user-communities {
          description
            "Container class for defining communities for a
            trap host";

          list default-user-community {
            key "community-name";
            description
              "Unencrpted Community name associated with a
              trap host";
            leaf community-name {
              type xr:Cisco-ios-xr-string {
                length "1..128";
              }
              description
                "SNMPv1/v2c community string or SNMPv3 user";
            }
            leaf port {
              type xr:Cisco-ios-xr-port-number;
              description "UDP port number";
            }
            leaf version {
              type string;
              mandatory true;
              description "SNMP Version to be used 1/2c/3";
            }
            leaf security-level {
              type Snmp-security-model;
              description
                "Security level to be used noauth/auth/priv";
            }
            leaf basic-trap-types {
              type uint32;
              mandatory true;
              description
                "Number to signify the feature traps that
                needs to be setBasicTrapTypes is used for
                all traps except copy-completeSet this value
                to an integer corresponding to the trapBGP
                8192, CONFIG 4096,SYSLOG 131072,SNMP_TRAP
                1COPY_COMPLETE_TRAP 64To provide a
                combination of trap Add the respective
                numbersValue must be set to 0 for all traps";
            }
            leaf advanced-trap-types1 {
              type uint32;
              mandatory true;
              description
                "Number to signify the feature traps that
                needs to be setUse this for providing
                copy-complete trapValue must be set to 0 if
                not used";
            }
            leaf advanced-trap-types2 {
              type uint32;
              mandatory true;
              description
                "Number to signify the feature traps that
                needs to be setvalue should always to set as
                0";
            }
            leaf dying-gasp {
              type boolean;
              description "Enable dying gasp trap for this host";
            }
          }
        }
        leaf ip-address {
          type inet:ip-address-no-zone;
          description "IP address of SNMP notification host";
        }
      }
    }
  }

  grouping CONTEXT-MAPPING-TABLE {
    description "Common node of snmp, vrf";

    container context-mappings {
      description "List of context names";

      list context-mapping {
        key "context-mapping-name";
        description "Context mapping name";
        leaf context-mapping-name {
          type xr:Cisco-ios-xr-string;
          description "Context mapping name";
        }
        leaf context {
          type Snmp-context;
          description "SNMP context feature type";
        }
        leaf instance-name {
          type string;
          description "OSPF protocol instance";
        }
        leaf vrf-name {
          type string;
          description "VRF name associated with the context";
        }
        leaf topology-name {
          type string;
          description "Topology name associated with the context";
        }
      }
    }
  }

  container snmp {
    description
      "The heirarchy point for all the SNMP
      configurations";

    container encrypted-community-maps {
      description
        "Container class to hold clear/encrypted
        communitie maps";

      list encrypted-community-map {
        key "community-name";
        description "Clear/encrypted SNMP community map";
        leaf community-name {
          type xr:Cisco-ios-xr-string;
          description "SNMP community map";
        }
        leaf context {
          type string;
          description "SNMP Context Name ";
        }
        leaf security {
          type string;
          description "SNMP Security Name ";
        }
        leaf target-list {
          type string;
          description "target list name ";
        }
      }
    }

    container views {
      description "Class to configure a SNMPv2 MIB view";

      list view {
        key "view-name family";
        description "Name of the view";
        leaf view-name {
          type xr:Cisco-ios-xr-string;
          description "Name of the view";
        }
        leaf family {
          type string;
          description "MIB view family name";
        }
        leaf view-inclusion {
          type Snmp-mib-view-inclusion;
          mandatory true;
          description "MIB view to be included or excluded";
        }
      }
    }

    container logging {
      description "SNMP logging";

      container threshold {
        description "SNMP logging threshold";
        leaf oid-processing {
          type uint32 {
            range "0..20000";
          }
          default "500";
          description "SNMP logging threshold for OID processing";
        }
        leaf pdu-processing {
          type uint32 {
            range "0..20000";
          }
          default "20000";
          description "SNMP logging threshold for PDU processing";
        }
      }
    }

    container script-inputs {
      description "SNMP script OID config";

      list script-input {
        key "script-oid";
        description "Input to Script";
        leaf script-oid {
          type xr:Cisco-ios-xr-string;
          description "Input OID to Script";
        }
        leaf script-file-name {
          type string;
          mandatory true;
          description "Script File Path";
        }
      }
    }

    container administration {
      description "Container class for SNMP administration";

      container default-communities {
        description
          "Container class to hold unencrpted communities";

        list default-community {
          key "community-name";
          description
            "Unencrpted SNMP community string and access
            priviledges";
          leaf community-name {
            type string {
              length "1..128";
            }
            description "SNMP community string";
          }
          leaf priviledge {
            type Snmp-access-level;
            description "Read/Write Access";
          }
          leaf view-name {
            type string;
            description
              "MIB view to which the community has access";
          }
          leaf v4acl-type {
            type Snmpacl;
            description "Access-list type";
          }
          leaf v4-access-list {
            type string;
            description "Ipv4 Access-list name";
          }
          leaf v6acl-type {
            type Snmpacl;
            description "Access-list type";
          }
          leaf v6-access-list {
            type string;
            description "Ipv6 Access-list name";
          }
          leaf owner {
            type Snmp-owner-access;
            description "Logical Router or System owner access";
          }
        }
      }

      container type6-encrypted-communities {
        description
          "Container class to hold type6 clear/encrypted
          communities";

        list type6-encrypted-community {
          key "community-name";
          description
            "Type6 Clear/encrypted SNMP community string
            and access priviledges";
          leaf community-name {
            type xr:Cisco-ios-xr-string;
            description "SNMP community string";
          }
          leaf priviledge {
            type Snmp-access-level;
            description "Read/Write Access";
          }
          leaf view-name {
            type string;
            description
              "MIB view to which the community has access";
          }
          leaf v4acl-type {
            type Snmpacl;
            description "Access-list type";
          }
          leaf v4-access-list {
            type string;
            description "Ipv4 Access-list name";
          }
          leaf v6acl-type {
            type Snmpacl;
            description "Access-list type";
          }
          leaf v6-access-list {
            type string;
            description "Ipv6 Access-list name";
          }
          leaf owner {
            type Snmp-owner-access;
            description "Logical Router or System owner access";
          }
        }
      }

      container encrypted-communities {
        description
          "Container class to hold clear/encrypted
          communities";

        list encrypted-community {
          key "community-name";
          description
            "Clear/encrypted SNMP community string and
            access priviledges";
          leaf community-name {
            type xr:Cisco-ios-xr-string;
            description "SNMP community string";
          }
          leaf priviledge {
            type Snmp-access-level;
            description "Read/Write Access";
          }
          leaf view-name {
            type string;
            description
              "MIB view to which the community has access";
          }
          leaf v4acl-type {
            type Snmpacl;
            description "Access-list type";
          }
          leaf v4-access-list {
            type string;
            description "Ipv4 Access-list name";
          }
          leaf v6acl-type {
            type Snmpacl;
            description "Access-list type";
          }
          leaf v6-access-list {
            type string;
            description "Ipv6 Access-list name";
          }
          leaf owner {
            type Snmp-owner-access;
            description "Logical Router or System owner access";
          }
        }
      }
    }

    container agent {
      description
        "The heirarchy point for SNMP Agent
        configurations";

      container engine-id {
        description "SNMPv3 engineID";

        container remotes {
          description "SNMPv3 remote SNMP Entity";

          list remote {
            key "remote-address";
            description "engineID of the remote agent";
            leaf remote-address {
              type inet:ip-address-no-zone;
              description "IP address of remote SNMP entity";
            }
            leaf remote-engine-id {
              type string;
              description "engine ID octet string";
            }
            leaf port {
              type xr:Cisco-ios-xr-port-number;
              description "UDP port number";
            }
          }
        }
        leaf local {
          type string;
          description "engineID of the local agent";
        }
      }
    }

    container trap {
      description "Class to hold trap configurations";
      leaf timeout {
        type uint32 {
          range "1..1000";
        }
        description "Timeout for TRAP message retransmissions";
      }
      leaf throttle-time {
        type uint32 {
          range "10..500";
        }
        units "millisecond";
        description "Set throttle time for handling traps";
      }
      leaf queue-length {
        type uint32 {
          range "1..5000";
        }
        description "Message queue length for each TRAP host";
      }
      leaf trap-delay-time {
        type uint32 {
          range "30..240";
        }
        units "minute";
        description "Set time to delay sending traps on init";
      }
    }

    container type6-encrypted-community-maps {
      description
        "Container class to hold type6 clear/encrypted
        communitie maps";

      list type6-encrypted-community-map {
        key "community-name";
        description "Type6 Clear/encrypted SNMP community map";
        leaf community-name {
          type xr:Cisco-ios-xr-string;
          description "SNMP community map";
        }
        leaf context {
          type string;
          description "SNMP Context Name ";
        }
        leaf security {
          type string;
          description "SNMP Security Name ";
        }
        leaf target-list {
          type string;
          description "target list name ";
        }
      }
    }

    container drop-packet {
      description "SNMP packet drop config";

      container report {
        description "SNMP drop report";

        container acl {
          description "SNMP drop report for ACL";
          leaf v4acl-type {
            type Snmpacl;
            description "Access-list type";
          }
          leaf v4-access-list {
            type string;
            description "Ipv4 Access-list name";
          }
          leaf v6acl-type {
            type Snmpacl;
            description "Access-list type";
          }
          leaf v6-access-list {
            type string;
            description "Ipv6 Access-list name";
          }
        }
      }
      leaf unknown-user {
        type empty;
        description "Enable drop unknown user name";
      }
    }

    container ipv6 {
      description "SNMP TOS bit for outgoing packets";

      container tos {
        description "Type of TOS";
        leaf type {
          type Snmp-tos;
          description "SNMP TOS type DSCP or Precedence";
        }
        leaf precedence {
          when "../type = 'precedence'" {
            description "../Type = Precedence";
          }
          type Snmp-precedence-value1;
          description "SNMP Precedence value";
        }
        leaf dscp {
          when "../type = 'dscp'" {
            description "../Type = DSCP";
          }
          type Snmp-dscp-value;
          description "SNMP DSCP value";
        }
      }
    }

    container ipv4 {
      description "SNMP TOS bit for outgoing packets";

      container tos {
        description "Type of TOS";
        leaf type {
          type Snmp-tos;
          description "SNMP TOS type DSCP or Precedence";
        }
        leaf precedence {
          when "../type = 'precedence'" {
            description "../Type = Precedence";
          }
          type Snmp-precedence-value1;
          description "SNMP Precedence value";
        }
        leaf dscp {
          when "../type = 'dscp'" {
            description "../Type = DSCP";
          }
          type Snmp-dscp-value;
          description "SNMP DSCP value";
        }
      }
    }

    container system {
      description "container to hold system information";
      leaf chassis-id {
        type string {
          length "1..255";
        }
        description "String to uniquely identify this chassis";
      }
      leaf location {
        type string {
          length "1..255";
        }
        description "The physical location of this node";
      }
      leaf contact {
        type string {
          length "1..255";
        }
        description
          "identification of the contact person for this
          managed node";
      }
    }

    container target {
      description "SNMP target configurations";

      container targets {
        description "List of targets";

        list target {
          key "target-list-name";
          description "Name of the target list";

          container vrf-names {
            description "List of VRF Name for a target list";

            list vrf-name {
              key "name";
              description "VRF name of the target";
              leaf name {
                type xr:Cisco-ios-xr-string;
                description "VRF Name";
              }
            }
          }

          container target-addresses {
            description "SNMP Target address configurations";

            list target-address {
              key "ip-address";
              description
                "IP Address to be configured for the Target";
              leaf ip-address {
                type inet:ip-address-no-zone;
                description "IPv4/Ipv6 address";
              }
            }
          }
          leaf target-list-name {
            type xr:Cisco-ios-xr-string;
            description "Name of the target list";
          }
        }
      }
    }

    container notification {
      description "Enable SNMP notifications";

      container snmp {
        description "SNMP notification configuration";
        leaf authentication {
          type empty;
          description "Enable authentication notification";
        }
        leaf cold-start {
          type empty;
          description "Enable cold start notification";
        }
        leaf warm-start {
          type empty;
          description "Enable warm start notification";
        }
        leaf enable {
          type empty;
          description "Enable SNMP notifications";
        }
      }
    }

    container correlator {
      description "Configure properties of the trap correlator";

      container rules {
        description "Table of configured rules";

        list rule {
          key "name";
          description "Rule name";

          container non-stateful {
            description "The Non-Stateful Rule Type";

            container root-causes {
              description
                "Table of configured rootcause (only one
                entry allowed)";

              list root-cause {
                key "oid";
                description
                  "The rootcause - maximum of one can be
                  configured per rule";
                leaf created {
                  type empty;
                  description "Create rootcause";
                }
                leaf oid {
                  type string;
                  description
                    "OID of rootcause trap (dotted decimal)";
                }
                uses VAR-BIND-TABLE;
              }
            }

            container non-root-causes {
              description "Table of configured non-rootcause";

              list non-root-cause {
                key "oid";
                description "A non-rootcause";
                leaf created {
                  type empty;
                  description "Create nonrootcause";
                }
                leaf oid {
                  type string;
                  description
                    "OID of nonrootcause trap (dotted decimal)";
                }
                uses VAR-BIND-TABLE;
              }
            }
            leaf timeout {
              type uint32 {
                range "1..600000";
              }
              units "millisecond";
              description
                "Timeout (time to wait for active
                correlation) in milliseconds";
            }
          }
          leaf created {
            type empty;
            description "Create rule";
          }
          leaf name {
            type string {
              length "1..32";
            }
            description "Rule name";
          }
          uses APPLIED-TO;
        }
      }

      container rule-sets {
        description "Table of configured rulesets";

        list rule-set {
          key "name";
          description "Ruleset name";

          container rulenames {
            description "Table of configured rulenames";

            list rulename {
              key "rulename";
              description "A rulename";
              leaf rulename {
                type string {
                  length "1..32";
                }
                description "Rule name";
              }
            }
          }
          leaf name {
            type string {
              length "1..32";
            }
            description "Ruleset name";
          }
          uses APPLIED-TO;
        }
      }
      leaf buffer-size {
        type uint32 {
          range "1024..52428800";
        }
        description "Configure size of the correlator buffer";
      }
    }

    container bulk-stats {
      description "SNMP bulk stats configuration commands";

      container schemas {
        description "Configure schema definition";

        list schema {
          key "schema-name";
          description "The name of the Schema";

          container instance {
            presence "Indicates a instance node is configured.";
            description "Object instance information";
            leaf type {
              type Snmp-bulkstat-schema;
              mandatory true;
              description "Type of the instance";
            }
            leaf instance {
              type xr:Interface-name;
              description "Instance of the schema";
            }
            leaf start {
              type string;
              mandatory true;
              description "Start Instance OID for repetition";
            }
            leaf end {
              type string;
              mandatory true;
              description "End Instance OID for repetition";
            }
            leaf max {
              type uint32;
              mandatory true;
              description "Max value of Instance repetition";
            }
            leaf sub-interface {
              type boolean;
              mandatory true;
              description "Include all the subinterface";
            }
          }
          leaf type {
            type empty;
            description "Configure schema name";
          }
          leaf schema-object-list {
            type xr:Cisco-ios-xr-string {
              length "1..32";
            }
            description "Name of an object List";
          }
          leaf poll-interval {
            type uint32 {
              range "1..20000";
            }
            units "minute";
            description
              "Periodicity for polling of objects in this
              schema in minutes";
          }
          leaf schema-name {
            type xr:Cisco-ios-xr-string {
              length "1..32";
            }
            description "The name of the schema";
          }
        }
      }

      container objects {
        description "Configure an Object List ";

        list object {
          key "object-list-name";
          description "Name of the object List";

          container objects {
            description "Configure an object List";

            list object {
              key "oid";
              description "Object name or OID";
              leaf oid {
                type string;
                description "Object name or OID ";
              }
            }
          }
          leaf type {
            type empty;
            description "Configure object list name";
          }
          leaf object-list-name {
            type xr:Cisco-ios-xr-string {
              length "1..32";
            }
            description "Name of the object List";
          }
        }
      }

      container transfers {
        description
          "Periodicity for the transfer of bulk data in
          minutes";

        list transfer {
          key "transfer-name";
          description "Name of bulk transfer";

          container transfer-schemas {
            description
              "Schema that contains objects to be collected";

            list transfer-schema {
              key "schema-name";
              description
                "Schema that contains objects to be collected";
              leaf schema-name {
                type xr:Cisco-ios-xr-string {
                  length "1..32";
                }
                description
                  "Schema that contains objects to be
                  collected";
              }
            }
          }
          leaf secondary {
            type string;
            description
              "FTP or rcp or TFTP can be used for file
              transfer";
          }
          leaf type {
            type empty;
            description "Configure transfer list name";
          }
          leaf buffer-size {
            type uint32 {
              range "1024..2147483647";
            }
            units "byte";
            description "Bulkstat data file maximum size in bytes";
          }
          leaf retain {
            type uint32 {
              range "0..20000";
            }
            units "minute";
            description "Retention period in minutes";
          }
          leaf format {
            type Snmp-bulkstat-file-format;
            description "Format of the bulk data file";
          }
          leaf retry {
            type uint32 {
              range "0..100";
            }
            description "Number of transmission retries";
          }
          leaf enable {
            type empty;
            description
              "Start Data Collection for this Configuration";
          }
          leaf primary {
            type string;
            description
              "FTP or rcp or TFTP can be used for file
              transfer";
          }
          leaf interval {
            type uint32;
            units "minute";
            description
              "Periodicity for the transfer of bulk data in
              minutes";
          }
          leaf transfer-name {
            type xr:Cisco-ios-xr-string {
              length "1..32";
            }
            description "Name of bulk transfer";
          }
        }
      }
      leaf memory {
        type uint32 {
          range "100..200000";
        }
        units "kilobyte";
        description "per process memory limit in kilo bytes";
      }
    }

    container default-community-maps {
      description
        "Container class to hold unencrpted community map";

      list default-community-map {
        key "community-name";
        description "Unencrpted SNMP community map name ";
        leaf community-name {
          type xr:Cisco-ios-xr-string {
            length "1..128";
          }
          description "SNMP community map";
        }
        leaf context {
          type string;
          description "SNMP Context Name ";
        }
        leaf security {
          type string;
          description "SNMP Security Name ";
        }
        leaf target-list {
          type string;
          description "target list name ";
        }
      }
    }

    container overload-control {
      presence "Indicates a overload-control node is configured.";
      description
        "Set overload control params for handling
        incoming messages";
      leaf drop-time {
        type uint32 {
          range "0..300";
        }
        units "second";
        mandatory true;
        description
          "Drop time in seconds for incoming queue
          (default 1 sec)";
      }
      leaf throttle-rate {
        type uint32 {
          range "0..1000";
        }
        units "millisecond";
        mandatory true;
        description
          "Throttle time in milliseconds for incoming
          queue (default 500 msec)";
      }
    }

    container timeouts {
      description "SNMP timeouts";
      leaf duplicates {
        type uint32 {
          range "0..20";
        }
        units "second";
        default "1";
        description "Duplicate request feature timeout";
      }
      leaf in-qdrop {
        type uint32 {
          range "0..20";
        }
        units "second";
        default "10";
        description "incoming queue drop feature timeout";
      }
      leaf threshold {
        type uint32 {
          range "0..100000";
        }
        units "second";
        default "50000";
        description "Threshold request feature timeout";
      }
      leaf subagent {
        type uint32 {
          range "1..20";
        }
        units "second";
        default "10";
        description "Sub-Agent Request timeout";
      }
      leaf pdu-stats {
        type uint32 {
          range "1..10";
        }
        units "second";
        default "2";
        description "SNMP pdu statistics timeout";
      }
    }

    container users {
      description "Define a user who can access the SNMP engine";

      list user {
        key "user-name";
        description "Name of the user";
        leaf user-name {
          type string;
          description "Name of the user";
        }
        leaf group-name {
          type string;
          mandatory true;
          description "Group to which the user belongs";
        }
        leaf version {
          type User-snmp-version;
          mandatory true;
          description "SNMP version to be used. v1,v2c or v3";
        }
        leaf authentication-password-configured {
          type empty;
          description
            "Flag to indicate that authentication password
            is configred for version 3";
        }
        leaf algorithm {
          type Snmp-hash-algorithm;
          description "The algorithm used md5 or sha";
        }
        leaf authentication-password {
          type xr:Proprietary-password;
          description "The authentication password";
        }
        leaf privacy-password-configured {
          type empty;
          description
            "Flag to indicate that the privacy password is
            configured for version 3";
        }
        leaf priv-algorithm {
          type Snmp-priv-algorithm;
          description
            "The algorithm used des56 or aes128 or aes192or
            aes256 or 3des";
        }
        leaf privacy-password {
          type xr:Proprietary-password;
          description "The privacy password";
        }
        leaf v4acl-type {
          type Snmpacl;
          description "Access-list type";
        }
        leaf v4-access-list {
          type string;
          description "Ipv4 Access-list name";
        }
        leaf v6acl-type {
          type Snmpacl;
          description "Access-list type";
        }
        leaf v6-access-list {
          type string;
          description "Ipv6 Access-list name";
        }
        leaf owner {
          type Snmp-owner-access;
          description
            "The system access either SDROwner or
            SystemOwner";
        }
        leaf remote-address {
          type inet:ip-address-no-zone;
          description "IP address of remote SNMP entity";
        }
        leaf port {
          type xr:Cisco-ios-xr-port-number;
          description "UDP port number";
        }
        leaf user-auth-type {
          type uint32;
          description "User Authentication Type";
        }
        leaf user-priv-auth-type {
          type uint32;
          description "User Priv Authentication Type";
        }
      }
    }

    container vrfs {
      description "SNMP VRF configuration commands";

      list vrf {
        key "name";
        description "VRF name";
        leaf name {
          type xr:Cisco-ios-xr-string;
          description "VRF name";
        }
        uses TRAP-HOST-TABLE;
        uses CONTEXT-TABLE;
        uses CONTEXT-MAPPING-TABLE;
      }
    }

    container snmp-tcp-vrfs {
      description "Enable TCP transport for SNMP";

      list snmp-tcp-vrf {
        key "vrf-name";
        description "Enable TCP transport for SNMP on vrf";
        leaf vrf-name {
          type xr:Cisco-ios-xr-string {
            length "1..32";
          }
          description "vrf name";
        }
      }
    }

    container groups {
      description "Define a User Security Model group";

      list group {
        key "name";
        description "Name of the group";
        leaf name {
          type xr:Cisco-ios-xr-string {
            length "1..128";
          }
          description "Name of the group";
        }
        leaf snmp-version {
          type Group-snmp-version;
          mandatory true;
          description "snmp version";
        }
        leaf security-model {
          type Snmp-security-model;
          description
            "security model like auth/noAuth/Priv
            applicable for v3";
        }
        leaf notify-view {
          type string;
          description "notify view name";
        }
        leaf read-view {
          type string;
          description "read view name";
        }
        leaf write-view {
          type string;
          description "write view name";
        }
        leaf v4acl-type {
          type Snmpacl;
          description "Access-list type";
        }
        leaf v4-access-list {
          type string;
          description "Ipv4 Access-list name";
        }
        leaf v6acl-type {
          type Snmpacl;
          description "Access-list type";
        }
        leaf v6-access-list {
          type string;
          description "Ipv6 Access-list name";
        }
        leaf context-name {
          type string;
          description "Context name";
        }
      }
    }
    leaf inform-retries {
      type uint32 {
        range "0..100";
      }
      description
        "Number of times to retry an Inform request
        (default 3)";
    }
    leaf trap-port {
      type uint32 {
        range "1024..65535";
      }
      description "Change the source port of all traps";
    }
    leaf oid-poll-stats {
      type empty;
      description "Enable Poll OID statistics";
    }
    leaf trap-source {
      type xr:Interface-name;
      description
        "Assign an interface for the source address of
        all traps";
    }
    leaf vrf-authentication-trap-disable {
      type empty;
      description
        "Disable authentication traps for packets on a
        vrf";
    }
    leaf inform-timeout {
      type uint32 {
        range "1..42949671";
      }
      units "second";
      description
        "Timeout value in seconds for Inform request
        (default 15 sec)";
    }
    leaf trap-source-ipv6 {
      type xr:Interface-name;
      description
        "Assign an interface for the source IPV6 address
        of all traps";
    }
    leaf packet-size {
      type uint32 {
        range "484..65500";
      }
      description "Largest SNMP packet size";
    }
    leaf throttle-time {
      type uint32 {
        range "50..1000";
      }
      description
        "Throttle time for incoming queue (default 0
        msec)";
    }
    leaf trap-source-ipv4 {
      type xr:Interface-name;
      description
        "Assign an interface for the source address of
        all traps";
    }
    leaf inform-pending {
      type uint32 {
        range "0..4294967295";
      }
      description
        "Max nmber of informs to hold in queue, (default
        25)";
    }
    uses TRAP-HOST-TABLE;
    uses CONTEXT-TABLE;
    uses CONTEXT-MAPPING-TABLE;
  }

  container mib {
    description
      "The heirarchy point for all the MIB
      configurations";
  }
}
