module Cisco-IOS-XR-infra-infra-cfg {

  /*** NAMESPACE / PREFIX DEFINITION ***/

  namespace "http://cisco.com/ns/yang/Cisco-IOS-XR-infra-infra-cfg";


  prefix "infra-infra-cfg";

  /*** LINKAGE (IMPORTS / INCLUDES) ***/

  import cisco-semver { prefix "semver"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR infra-infra package configuration.

     This module contains definitions
     for the following management objects:
       banners: Schema for Banner configuration commands

     Copyright (c) 2013-2019 by Cisco Systems, Inc.
     All rights reserved.";

  revision "2019-04-05" {
    description
      "Establish semantic version baseline.";
    semver:module-version "1.0.0";
  }

  revision "2016-06-16" {
    description
      "Initial Rev 1";
  }

  revision "2015-01-07" {
    description
      "IOS XR 5.3.1 revision.";
  }

  typedef Banner {
    type enumeration {
      enum exec {
        value 0;
        description "Set EXEC process creation banner";
      }
      enum incoming {
        value 1;
        description "Set incoming terminal line banner";
      }
      enum motd {
        value 2;
        description "Set Message of the Day banner";
      }
      enum login {
        value 3;
        description "Set login banner";
      }
      enum slip-ppp {
        value 4;
        description "Set Message for SLIP/PPP";
      }
      enum prompt-timeout {
        value 5;
        description "Set Message for login authentication timeout";
      }
    }
    description "Banner";
  }

  container banners {
    description "Schema for Banner configuration commands";

    list banner {
      key "banner-name";
      description "Select a Banner Type";
      leaf banner-name {
        type Banner;
        description "Banner Type";
      }
      leaf banner-text {
        type string;
        mandatory true;
        description "Banner text message";
      }
    }
  }
}
