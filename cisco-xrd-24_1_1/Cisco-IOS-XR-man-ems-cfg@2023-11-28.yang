module Cisco-IOS-XR-man-ems-cfg {

  /*** NAMESPACE / PREFIX DEFINITION ***/

  namespace "http://cisco.com/ns/yang/Cisco-IOS-XR-man-ems-cfg";


  prefix "man-ems-cfg";

  /*** LINKAGE (IMPORTS / INCLUDES) ***/

  import ietf-inet-types { prefix "inet"; }

  import Cisco-IOS-XR-types { prefix "xr"; }

  import cisco-semver { prefix "semver"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR man-ems package configuration.

     This model is deprecated and is replaced by
     Cisco-IOS-XR-um-grpc-cfg.yang which will provide the
     compatible functionalities.

     This module contains definitions
     for the following management objects:
       grpc: GRPC configruation

     Copyright (c) 2013-2023 by Cisco Systems, Inc.
     All rights reserved.";

  revision "2023-11-28" {
    description
      "Added support for max-concurrent-streams that corresponds to gRPC server option MaxConcurrentStreams.
       2023-09-01
         Added support to configure SSL profile ID for GNSI certz implementation.
       2023-06-15
         Added support for IANA defined gRPC ports.
       2023-06-01
         Added support for certificate common name.
       2023-04-12
         Added support for EMSd-Go soft memory limit.
       2023-03-22
         Added support for Keepalive.
       2023-01-23
         Added support for virtual IP as gRPC tunnel source address and domain name as gRPC tunnel destination.
       2022-12-14
         Added support for gRPC listen addresses
       2022-12-07
         Added support for SRTE services
       2022-09-26
         Added support for TTL flag
       2022-07-20
         Added support for gRPC TLS version 1.0 flag
       2022-06-21
         Added support for gRPC server name
       2022-06-16
         Removed the enable leafs for P4 Runtime.
       2022-06-07
         Added support for P4 Runtime.";
    semver:module-version "3.0.0";
  }

  revision "2021-09-21" {
    description
      "Changed gRPC port range to avoid conflicts with non-Linux applications.
      2021-06-18
          Added support for local connection leaf.
      2021-05-14
          Added gRPC tunnel.";
    semver:module-version "2.0.0";
  }

  revision "2019-06-02" {
    description
      "Added support for AAA method lists.";
    semver:module-version "1.2.0";
  }

  revision "2019-05-12" {
    description
      "Deprecated the native model, replaced by UM model.";
    semver:module-version "1.1.0";
  }

  revision "2019-04-05" {
    description
      "Establish semantic version baseline.";
  }

  revision "2019-02-22" {
    description
      "Fixed yang evaluator warnings.";
  }

  revision "2015-11-09" {
    description
      "IOS XR 6.0 revision.";
  }

  typedef Dscp {
    type union {
      type enumeration {
        enum default {
          value 0;
          description "Default (DSCP 000000)";
        }
        enum af11 {
          value 10;
          description "AF11 (DSCP 001010)";
        }
        enum af12 {
          value 12;
          description "AF12 (DSCP 001100)";
        }
        enum af13 {
          value 14;
          description "AF13 (DSCP 001110)";
        }
        enum af21 {
          value 18;
          description "AF21 (DSCP 010010)";
        }
        enum af22 {
          value 20;
          description "AF22 (DSCP 010100)";
        }
        enum af23 {
          value 22;
          description "AF23 (DSCP 010110)";
        }
        enum af31 {
          value 26;
          description "AF31 (DSCP 011010)";
        }
        enum af32 {
          value 28;
          description "AF32 (DSCP 011100)";
        }
        enum af33 {
          value 30;
          description "AF33 (DSCP 011110)";
        }
        enum af41 {
          value 34;
          description "AF41 (DSCP 100010)";
        }
        enum af42 {
          value 36;
          description "AF42 (DSCP 100100)";
        }
        enum af43 {
          value 38;
          description "AF43 (DSCP 100110)";
        }
        enum cs1 {
          value 8;
          description "CS1 (Precedence 1) (DSCP 001000)";
        }
        enum cs2 {
          value 16;
          description "CS2 (Precedence 2) (DSCP 010000)";
        }
        enum cs3 {
          value 24;
          description "CS3 (Precedence 3) (DSCP 011000)";
        }
        enum cs4 {
          value 32;
          description "CS4 (Precedence 4) (DSCP 100000)";
        }
        enum cs5 {
          value 40;
          description "CS5 (Precedence 5) (DSCP 101000)";
        }
        enum cs6 {
          value 48;
          description "CS6 (Precedence 6) (DSCP 110000)";
        }
        enum cs7 {
          value 56;
          description "CS7 (Precedence 7) (DSCP 111000)";
        }
        enum ef {
          value 46;
          description "EF (DSCP 101110)";
        }
      }
      type uint32 {
        range "0..63";
      }
    }
    description "Dscp";
  }
  typedef Grp-c-tls-cipher-default {
    type enumeration {
      enum disable {
        value 1;
        description "Default disable all ciphers";
      }
      enum enable {
        value 2;
        description "Default enable all ciphers";
      }
    }
    description "Grp c tls cipher default";
  }
  typedef Grp-c-address-family {
    type enumeration {
      enum ipv4 {
        value 1;
        description "IPv4 address family";
      }
      enum ipv6 {
        value 2;
        description "IPv6 address family";
      }
    }
    description "Grp c address family";
  }

  container grpc {
    status "deprecated";
    description
      "This model is deprecated and is replaced by
      Cisco-IOS-XR-um-grpc-cfg.yang which will provide
      the compatible functionalities.  GRPC
      configruation";

    container memory {
      description "EMSd-Go soft memory limit";
      leaf limit {
        type uint32 {
          range "600..1400";
        }
        default "1024";
        description "Soft memory limit in MB";
      }
    }

    container aaa {
      description "AAA authentication and authorization for gRPC";

      container authentication {
        description "AAA authentication for gRPC";
        leaf login {
          type string;
          description
            "AAA authentication login method list for gRPC";
        }
      }

      container authorization {
        description "AAA authorization for gRPC";
        leaf exec {
          type string;
          description "AAA authorization exec method list for gRPC";
        }
      }
    }

    container service-layer {
      description "Grpc Service Layer";
      leaf enable {
        type empty;
        description "Enable ServiceLayer";
      }
    }

    container tls-cipher {
      description "TLS ciphers";
      leaf default {
        type Grp-c-tls-cipher-default;
        description "Default of all ciphers.";
      }
      leaf enable {
        type string;
        description "Enable ciphers if default is disabled.";
      }
      leaf disable {
        type string;
        description "Disable ciphers if default is enabled.";
      }
    }

    container gnmi {
      presence "Indicates a gnmi node is configured.";
      description "gNMI service";
      leaf port {
        type uint32 {
          range "9339..57999";
        }
        default "9339";
        description "gNMI gRPC service listening port";
      }
      leaf enable {
        type empty;
        mandatory true;
        description "enable gNMI service";
      }
    }

    container listen-addresses {
      description "Listen address and up to 32 addresses";
      leaf-list listen-address {
        type inet:ip-address-no-zone;
        max-elements "32";
        description "Listen addresses";
      }
    }

    container segment-routing {
      description "gRPC segment-routing";

      container traffic-eng {
        description "gRPC segment-routing traffic-eng";

        container policy-service {
          description "SRTE policy service";
          leaf enable {
            type empty;
            description "Enable SRTE policy service";
          }
        }
        leaf enable {
          type empty;
          description "Enable gRPC segment-routing traffic-eng";
        }
      }
      leaf enable {
        type empty;
        description "Enable gRPC segment-routing";
      }
    }

    container p4rt {
      description "P4 Runtime";

      container locations {
        description "Location attributes";

        list location {
          key "node-id";
          description "NPU Location";

          container npus {
            description "P4 Runtime NPU attributes";

            list npu {
              key "npuid";
              description "NPU ID in the node";

              container device {
                description "P4 Runtime Device Class";
                leaf device-id {
                  type uint64;
                  description "P4 Runtime Device Identifier";
                }
              }
              leaf npuid {
                type uint32 {
                  range "0..65535";
                }
                description "NPU ID";
              }
            }
          }
          leaf node-id {
            type xr:Node-id;
            description
              "NodeID of the location where NPU is present";
          }
        }
      }

      container interfaces {
        description "Configure P4 Runtime Interface attributes";

        list interface {
          key "interface-name";
          description "Interface to configure";
          leaf port {
            type uint32 {
              range "0..4294967295";
            }
            description "P4 Runtime Interface Port Identifier";
          }
          leaf interface-name {
            type xr:Interface-name;
            description "Interface name";
          }
        }
      }
      leaf port {
        type uint32 {
          range "9559..57999";
        }
        default "9559";
        description "P4RT service listening port";
      }
    }

    container gnsi {
      description "gRPC gNSI";

      container service {
        description "Service level";

        container certz {
          description "Certificate management";
          leaf ssl-profile-id {
            type string;
            description "SSL profile to be used by gRPC server";
          }
        }
      }
    }

    container certificate {
      description "gRPC certificate";
      leaf common-name {
        type xr:Cisco-ios-xr-string {
          length "1..64";
        }
        default "ems.cisco.com";
        description
          "Common name when generate certificates, default
          : ems.cisco.com";
      }
    }

    container tunnel {
      description "gRPC tunnels";

      container destinations {
        description "gRPC tunnel destinations";

        list destination {
          key "address port";
          description "gRPC tunnel destination";

          container source {
            description "Virtual IP as tunnel source";
            leaf ipv6 {
              type empty;
              description "Set virtual IP address family as IPv6";
            }
            leaf ipv4 {
              type empty;
              description "Set virtual IP address family as IPv4";
            }
          }
          leaf target {
            type xr:Cisco-ios-xr-string {
              length "1..256";
            }
            description "Target name to register tunnel service";
          }
          leaf source-interface {
            type xr:Interface-name;
            description "Source interface for dialout";
          }
          leaf vrf {
            type xr:Cisco-ios-xr-string {
              length "1..32";
            }
            description "VRF for dialout";
          }
          leaf address-family {
            type Grp-c-address-family;
            description
              "Specify the desired address family for the
              returned address(es) from DNS. This is
              applicable only if domain name is specified
              as destination address.";
          }
          leaf address {
            type xr:Cisco-ios-xr-string {
              length "1..128";
            }
            description
              "IPv4 address in dotted-quad notation, IPv6
              address in full, mixed, shortened, and
              shortened-mixed notation, or domain name.";
          }
          leaf port {
            type xr:Cisco-ios-xr-port-number;
            description "Destination port";
          }
        }
      }
    }

    container tls {
      description "Transport Layer Security (TLS)";
      leaf enable {
        type empty;
        status deprecated;
        description "Enable TLS";
      }
    }

    container keepalive {
      description "Server keepalive";
      leaf time {
        type uint32 {
          range "1..1000";
        }
        units "second";
        default "30";
        description "Server keepalive time in seconds";
      }
      leaf timeout {
        type uint32 {
          range "1..1000";
        }
        units "second";
        default "20";
        description "Server keepalive timeout in seconds";
      }
    }

    container gribi {
      presence "Indicates a gribi node is configured.";
      description "gRIBI service";
      leaf port {
        type uint32 {
          range "9340..57999";
        }
        default "9340";
        description "gRIBI gRPC service listening port";
      }
      leaf enable {
        type empty;
        mandatory true;
        description "enable gRIBI service";
      }
    }
    leaf max-concurrent-streams {
      type uint32 {
        range "1..128";
      }
      default "32";
      description
        "gRPC server maximum concurrent streams per
        connection";
    }
    leaf port {
      type uint32 {
        range "57344..57999";
      }
      description "Server listening port";
    }
    leaf vrf {
      type string;
      description "Server vrf name";
    }
    leaf max-streams {
      type uint32 {
        range "1..128";
      }
      default "32";
      description "Maximum number of streaming gRPCs";
    }
    leaf enable {
      type empty;
      description "Enable GRPC";
    }
    leaf ttl {
      type uint32 {
        range "0..255";
      }
      description "TTL settings for outgoing gRPC packets";
    }
    leaf cert-auth {
      type empty;
      description "Certificate Authentication";
    }
    leaf max-streams-per-user {
      type uint32 {
        range "1..128";
      }
      default "32";
      description "Maximum number of streaming gRPCs per user";
    }
    leaf certificate-id {
      type string;
      description "Active Certificate ID";
    }
    leaf max-request-per-user {
      type uint32 {
        range "1..32";
      }
      description "Maximum concurrent requests per user";
    }
    leaf name {
      type xr:Cisco-ios-xr-string {
        length "1..64";
      }
      description "gRPC server name";
    }
    leaf no-tls {
      type empty;
      description "No TLS";
    }
    leaf tls-trustpoint {
      type string;
      description "Trustpoint Name";
    }
    leaf tlsv1 {
      type empty;
      description "TLS version 1.0 support";
    }
    leaf dscp {
      type Dscp;
      description "QoS marking DSCP to be set on transmitted gRPC";
    }
    leaf address-family {
      type string;
      description "Address family identifier type";
    }
    leaf tls-mutual {
      type empty;
      description "TLS mutual authentication";
    }
    leaf local-connection {
      type empty;
      description "Enable gRPC server over Unix socket";
    }
    leaf max-request-total {
      type uint32 {
        range "1..256";
      }
      description "Maximum concurrent requests in total";
    }
  }
}
