module Cisco-IOS-XR-um-segment-routing-cfg {

  /*** NAMESPACE / PREFIX DEFINITION ***/

  namespace "http://cisco.com/ns/yang/Cisco-IOS-XR-um-segment-routing-cfg";
  prefix um-segment-routing-cfg;

  /*** LINKAGE (IMPORTS / INCLUDES) ***/

  import Cisco-IOS-XR-types {
    prefix xr;
  }
  import ietf-inet-types {
    prefix inet;
  }

  import cisco-semver { prefix "semver"; }

  /*** META INFORMATION ***/

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR segment-routing package configuration.

     This YANG module augments the
     modules with configuration data.

     Copyright (c) 2021-2022 by Cisco Systems, Inc.
     All rights reserved.";

  revision 2022-05-31 {
    description
      "Model Deprecated";
    semver:module-version "1.1.0";
  }

  revision "2021-05-10" {
    description
      "Initial release";
    semver:module-version "1.0.0";
  }

  container segment-routing {
    presence "Indicates a segment-routing node is configured.";
    status deprecated;
    description
      "Segment Routing";
    container mapping-server {
      description
        "Segment Routing Mapping Server (SRMS)";
      container prefix-sid-map {
        description
          "Prefix SID Map";
        container address-families {
          description
            "Address Family";
          list address-family {
            key "af-name";
            description
              "Address Family";
            leaf af-name {
              type enumeration {
                enum ipv4 {
                  value 1;
                  description
                    "IP version 4";
                }
                enum ipv6 {
                  value 2;
                  description
                    "IP version 6";
                }
              }
              description
                "Address Family";
            }
            list prefix-address {
              key "address length";
              description
                "SID index range";
              leaf address {
                type inet:ip-address-no-zone;
                description
                  "IP address with prefix";
              }
              leaf length {
                type union {
                  type uint32 {
                    range "0..32";
                  }
                  type uint32 {
                    range "0..128";
                  }
                }
                description
                  "Prefix length";
              }
              leaf sid-index {
                type uint32 {
                  range "0..1048575";
                }
                mandatory true;
                description
                  "Start of SID index range";
              }
              leaf range {
                type uint32 {
                  range "0..65535" {
                    description
                      "Number of allocated SIDs";
                  }
                }
                description
                  "Number of allocated SIDs";
              }
              container attached {
                presence "Indicates a attached node is configured.";
                description
                  "Attached entry advertised via the A-flag";
              }
            }
          }
        }
      }
    }
    container global-block {
      presence "Indicates a global-block node is configured.";
      description
        "Prefix-SID Global label Block (SRGB)";
      leaf lower-bound {
        type uint32 {
          range "16000..1048575" {
            description
              "The lower bound of SRGB";
          }
        }
        mandatory true;
        description
          "Prefix-SID Global label Block (SRGB)";
      }
      leaf upper-bound {
        type uint32 {
          range "16000..1048575" {
            description
              "The upper bound of SRGB";
          }
        }
        mandatory true;
        description
          "The upper bound of SRGB";
      }
    }
    container local-block {
      presence "Indicates a local-block node is configured.";
      description
        "Local Block (SRLB) of labels";
      leaf lower-bound {
        type uint32 {
          range "15000..1048575" {
            description
              "The lower bound of SRLB";
          }
        }
        mandatory true;
        description
          "Local Block (SRLB) of labels";
      }
      leaf upper-bound {
        type uint32 {
          range "15000..1048575" {
            description
              "The upper bound of SRLB (block size may not exceed 262143)";
          }
        }
        mandatory true;
        description
          "The upper bound of SRLB (block size may not exceed 262143)";
      }
    }
    container adjacency-sid {
      description
        "Segment Routing (MPLS) Adjacency SID";
      container interfaces {
        description
          "Interface Instance";
        list interface {
          must 'address-families/address-family';
          key "interface-name";
          description
            "Interface Instance";
          leaf interface-name {
            type xr:Interface-name;
            description
              "Interface Instance";
          }
          container address-families {
            description
              "Address Family";
            list address-family {
              must 'unicast/l2-adjacency-sid-next-hop/next-hop';
              key "af-name";
              description
                "Address Family";
              leaf af-name {
                type enumeration {
                  enum ipv4 {
                    value 1;
                    description
                      "IP version 4";
                  }
                  enum ipv6 {
                    value 2;
                    description
                      "IP version 6 link-local address";
                  }
                }
                description
                  "Address Family";
              }
              container unicast {
                description
                  "Unicast Address Family";
                container l2-adjacency-sid-next-hop {
                  description
                    "L2 Adjacency SID";
                  list next-hop {
                    must '(absolute or index) and not(absolute and index)';
                    key "address";
                    description
                      "Neighbor Address";
                    leaf address {
                      type inet:ip-address-no-zone;
                      description
                        "IP address";
                    }
                    leaf absolute {
                      type uint32 {
                        range "15000..1048575";
                      }
                      description
                        "L2 Adjacency SID value";
                    }
                    leaf index {
                      type uint32 {
                        range "0..1048575";
                      }
                      description
                        "L2 Adjacency SID value";
                    }
                  }
                }
              }
            }
          }
        }
      }
    }
  }
}
