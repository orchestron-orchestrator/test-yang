module Cisco-IOS-XR-fpmgr-oper {

  /*** NAMESPACE / PREFIX DEFINITION ***/

  namespace "http://cisco.com/ns/yang/Cisco-IOS-XR-fpmgr-oper";


  prefix "fpmgr-oper";

  /*** LINKAGE (IMPORTS / INCLUDES) ***/

  import Cisco-IOS-XR-types { prefix "xr"; }

  import cisco-semver { prefix "semver"; }

  include Cisco-IOS-XR-fpmgr-oper-sub1 {
    revision-date 2019-04-05;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR fpmgr package operational data.

     This module contains definitions
     for the following management objects:
       fault-profile: Show fault profile

     Copyright (c) 2013-2019 by Cisco Systems, Inc.
     All rights reserved.";

  revision "2019-04-05" {
    description
      "Establish semantic version baseline.";
    semver:module-version "1.0.0";
  }

  revision "2015-11-09" {
    description
      "IOS XR 6.0 revision.";
  }

  container fault-profile {
    config false;
    description "Show fault profile";

    container brief {
      description "Display brief fault profile info";
      uses FP-SHOW-FP-BRIEF;
    }

    container internals {
      description "Table of Internal";

      list internal {
        key "profile-name";
        description "Display fault profile details";
        leaf profile-name {
          type xr:Cisco-ios-xr-string;
          description "Fault profile name";
        }
        uses FP-SHOW-FP-INTERNAL-DATA;
      }
    }

    container location-lc-names {
      description "Get rack numbers";

      list location-lc-name {
        key "location-rack-name";
        description "Get line card names";

        container location-lc-name-str {
          description "Get line card names";
          uses FP-SHOW-FP-LOCATION-NAME-LIST;
        }
        leaf location-rack-name {
          type xr:Cisco-ios-xr-string;
          description "Rack number";
        }
      }
    }

    container statistics {
      description "Table of Statistics";

      list statistic {
        key "profile-name";
        description "Display fault profile statistics";
        leaf profile-name {
          type xr:Cisco-ios-xr-string;
          description "Fault profile name";
        }
        uses FP-SHOW-FP-STATISTIC-DATA;
      }
    }

    container detail {
      description "Display detailed fault profile info";
      uses FP-SHOW-FP-DETAIL;
    }

    container fault-id-fault-types {
      description "Get subsystem ids";

      list fault-id-fault-type {
        key "fault-id-subsystem-name";
        description "Get fault types";
        leaf fault-id-subsystem-name {
          type xr:Cisco-ios-xr-string;
          description "Subsystem name";
        }

        list fault-id-fault-tag {
          key "fault-id-fault-type-name";
          description "Get fault tags";

          container fault-id-fault-tag-names {
            description "Get fault tags";
            uses FP-SHOW-FP-FAULT-TAG-LIST;
          }
          leaf fault-id-fault-type-name {
            type xr:Cisco-ios-xr-string;
            description "Fault type name";
          }
        }
      }
    }

    container default-profile-fault-types {
      description "Get default subsystem profiles";

      list default-profile-fault-type {
        key "fault-id-subsystem-name";
        description "Get fault types";
        leaf fault-id-subsystem-name {
          type xr:Cisco-ios-xr-string;
          description "Subsystem name";
        }

        list default-profile-fault-tag {
          key "fault-id-fault-type-name";
          description "Get fault tags";

          container default-profile-fault-value-names {
            description "Get fault tags";
            uses FP-SHOW-DEFAULT-PROFILE-LIST;
          }
          leaf fault-id-fault-type-name {
            type xr:Cisco-ios-xr-string;
            description "Fault type name";
          }
        }
      }
    }
  }
}
