module Cisco-IOS-XR-lpts-pa-oper {

  /*** NAMESPACE / PREFIX DEFINITION ***/

  namespace "http://cisco.com/ns/yang/Cisco-IOS-XR-lpts-pa-oper";


  prefix "lpts-pa-oper";

  /*** LINKAGE (IMPORTS / INCLUDES) ***/

  import Cisco-IOS-XR-types { prefix "xr"; }

  import cisco-semver { prefix "semver"; }

  include Cisco-IOS-XR-lpts-pa-oper-sub1 {
    revision-date 2021-11-24;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR lpts-pa package operational data.

     This module contains definitions
     for the following management objects:
       lpts-pa: lpts pre-ifib data

     Copyright (c) 2013-2021 by Cisco Systems, Inc.
     All rights reserved.";

  revision "2021-11-24" {
    description
      "added new members in binding oper data as location name, vrf name, client id name, etc";
    semver:module-version "1.1.0";
  }

  revision "2020-06-24" {
    description
      "added task-name to LptsPA class.";
    semver:module-version "1.0.1";
  }

  revision "2019-04-05" {
    description
      "Establish semantic version baseline.";
    semver:module-version "1.0.1";
  }

  revision "2015-11-09" {
    description
      "IOS XR 6.0 revision.";
  }

  container lpts-pa {
    config false;
    description "lpts pre-ifib data";

    container entry-xr {
      description "lpts pa bindings";

      list entry {
        key "entry";
        description "Data for single PA Binding";
        leaf entry {
          type xr:Cisco-ios-xr-string;
          description "Single Binding entry";
        }
        uses BINDING-ENTRY;
      }
    }

    container entries {
      description "lpts pa clients";

      list entry {
        key "entry";
        description "Data for single PA Client";
        leaf entry {
          type xr:Cisco-ios-xr-string;
          description "Single Client entry";
        }
        uses CLIENT-ENTRY;
      }
    }
  }
}
