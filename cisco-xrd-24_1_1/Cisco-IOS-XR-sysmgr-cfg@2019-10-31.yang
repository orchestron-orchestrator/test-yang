module Cisco-IOS-XR-sysmgr-cfg {

  /*** NAMESPACE / PREFIX DEFINITION ***/

  namespace "http://cisco.com/ns/yang/Cisco-IOS-XR-sysmgr-cfg";


  prefix "sysmgr-cfg";

  /*** LINKAGE (IMPORTS / INCLUDES) ***/

  import Cisco-IOS-XR-types { prefix "xr"; }

  import cisco-semver { prefix "semver"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR sysmgr package configuration.

     This module contains definitions
     for the following management objects:
       process-mandatory: Process mandatory configuration
       process-single-crash: Reboot condition for single mandatory
         process that crashes

     Copyright (c) 2013-2019 by Cisco Systems, Inc.
     All rights reserved.";

  revision "2019-10-31" {
    description
      "Added mandatory nodes.";
    semver:module-version "2.0.0";
  }

  revision "2019-04-05" {
    description
      "Establish semantic version baseline.";
    semver:module-version "1.0.0";
  }

  revision "2015-11-09" {
    description
      "IOS XR 6.0 revision.";
  }

  grouping PROCESS-TABLE {
    description "Common node of all, node";

    container processes {
      description "Table of processes";

      list process {
        key "process-name";
        description "Name of the executable process";
        leaf process-name {
          type xr:Cisco-ios-xr-string;
          description "Process name";
        }
      }
    }
  }

  container process-mandatory {
    description "Process mandatory configuration";

    container nodes {
      description "Table of mandatory nodes";

      list node {
        key "node-name";
        description "Mandatory node";
        leaf node-name {
          type xr:Node-id;
          description "Node name";
        }
        uses PROCESS-TABLE;
      }
    }

    container all {
      description "Mandatory for all nodes";
      uses PROCESS-TABLE;
    }
  }

  container process-single-crash {
    presence "Indicates a process-single-crash node is configured.";
    description
      "Reboot condition for single mandatory process
      that crashes";
    leaf crashes {
      type uint32 {
        range "1..500";
      }
      mandatory true;
      description
        "Number of crashes for a process to trigger
        reboot";
    }
    leaf minimum-up-time {
      type uint32 {
        range "0..4294967295";
      }
      units "second";
      mandatory true;
      description
        "Minimum process up time (in seconds) to reset
        crash count";
    }
  }
}
