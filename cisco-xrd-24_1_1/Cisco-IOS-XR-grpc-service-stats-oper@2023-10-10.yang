module Cisco-IOS-XR-grpc-service-stats-oper {

  /*** NAMESPACE / PREFIX DEFINITION ***/

  namespace "http://cisco.com/ns/yang"+
    "/Cisco-IOS-XR-grpc-service-stats-oper";


  prefix "grpc-service-stats-oper";

  /*** LINKAGE (IMPORTS / INCLUDES) ***/

  import Cisco-IOS-XR-types { prefix "xr"; }

  import cisco-semver { prefix "semver"; }

  include Cisco-IOS-XR-grpc-service-stats-oper-sub1 {
    revision-date 2023-10-10;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR grpc-service-stats package operational data.

     This module contains definitions
     for the following management objects:
       service-stats: Stats for services like gRPC/gNMI/gRIBI

     Copyright (c) 2013-2023 by Cisco Systems, Inc.
     All rights reserved.";

  revision "2023-10-10" {
    description
      "Added support for leaf set-union-replace-paths";
    semver:module-version "1.0.0";
  }

  revision "2022-11-04" {
    description
      "Added support for SRTE gRPC stats";
  }

  revision "2022-09-26" {
    description
      "Added new service stats oper model";
  }

  revision "2019-04-05" {
    description
      "Establish semantic version baseline.";
  }

  revision "2015-11-09" {
    description
      "IOS XR 6.0 revision.";
  }

  container service-stats {
    config false;
    description "Stats for services like gRPC/gNMI/gRIBI";

    container services {
      description "Services list";

      list service {
        key "service-name";
        description "Service name";

        container rpcs {
          description "RPC list";

          list rpc {
            key "rpc-name";
            description "RPC name";
            leaf rpc-name {
              type xr:Cisco-ios-xr-string;
              description "RPC name";
            }
            uses STATISTICS;
          }
        }
        leaf service-name {
          type xr:Cisco-ios-xr-string;
          description "Service name";
        }
      }
    }
  }
}
