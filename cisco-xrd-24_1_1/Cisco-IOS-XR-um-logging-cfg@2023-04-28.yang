module Cisco-IOS-XR-um-logging-cfg {

  /*** NAMESPACE / PREFIX DEFINITION ***/

  namespace "http://cisco.com/ns/yang/Cisco-IOS-XR-um-logging-cfg";
  prefix um-logging-cfg;

  /*** LINKAGE (IMPORTS / INCLUDES) ***/

  import Cisco-IOS-XR-types {
    prefix xr;
  }
  import ietf-inet-types {
    prefix inet;
  }

  import cisco-semver { prefix "semver"; }

  /*** META INFORMATION ***/

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR logging package configuration.

     This YANG module augments the
     modules with configuration data.

     Copyright (c) 2021-2023 by Cisco Systems, Inc.
     All rights reserved.";

  revision "2023-04-28" {
    description
      "Buffered Logging Entries Count Changes
       2023-03-08
         Removed non-standard logging facility enum members
       2023-01-27
         Added facility and source address for per remotehost entry
       2022-07-22
         Added fetch-timestamp
       2022-07-11
         Added missing description statement to nodes
       2022-02-28
         Added leaf yang";
    semver:module-version "3.0.0";
  }

  revision "2021-10-29" {
    description
      "Added the container monitor-discriminator
      2021-10-18
          Changed sch-type for the node ipv6-address under container host-ipv6-addresses";
    semver:module-version "2.0.0";
  }

  revision "2021-03-08" {
    description
      "Initial release";
    semver:module-version "1.0.0";
  }

  container logging {
    description
      "Modify message logging facilities";
    leaf console {
      type enumeration {
        enum emergencies {
          value 0;
          description
            "System is unusable                (severity=0)";
        }
        enum alerts {
          value 1;
          description
            "Immediate action needed           (severity=1)";
        }
        enum critical {
          value 2;
          description
            "Critical conditions               (severity=2)";
        }
        enum errors {
          value 3;
          description
            "Error conditions                  (severity=3)";
        }
        enum warning {
          value 4;
          description
            "Warning conditions                (severity=4)";
        }
        enum notifications {
          value 5;
          description
            "Normal but significant conditions (severity=5)";
        }
        enum informational {
          value 6;
          description
            "Informational messages            (severity=6)";
        }
        enum debugging {
          value 7;
          description
            "Debugging messages                (severity=7)";
        }
        enum disable {
          value 15;
          description
            "Disable logging                               ";
        }
      }
      description
        "Set console logging";
    }
    leaf trap {
      type enumeration {
        enum emergencies {
          value 0;
          description
            "System is unusable                (severity=0)";
        }
        enum alerts {
          value 1;
          description
            "Immediate action needed           (severity=1)";
        }
        enum critical {
          value 2;
          description
            "Critical conditions               (severity=2)";
        }
        enum errors {
          value 3;
          description
            "Error conditions                  (severity=3)";
        }
        enum warning {
          value 4;
          description
            "Warning conditions                (severity=4)";
        }
        enum notifications {
          value 5;
          description
            "Normal but significant conditions (severity=5)";
        }
        enum informational {
          value 6;
          description
            "Informational messages            (severity=6)";
        }
        enum debugging {
          value 7;
          description
            "Debugging messages                (severity=7)";
        }
        enum disable {
          value 15;
          description
            "Disable logging                               ";
        }
      }
      description
        "Set trap logging";
    }
    leaf monitor {
      type enumeration {
        enum emergencies {
          value 0;
          description
            "System is unusable                (severity=0)";
        }
        enum alerts {
          value 1;
          description
            "Immediate action needed           (severity=1)";
        }
        enum critical {
          value 2;
          description
            "Critical conditions               (severity=2)";
        }
        enum errors {
          value 3;
          description
            "Error conditions                  (severity=3)";
        }
        enum warning {
          value 4;
          description
            "Warning conditions                (severity=4)";
        }
        enum notifications {
          value 5;
          description
            "Normal but significant conditions (severity=5)";
        }
        enum informational {
          value 6;
          description
            "Informational messages            (severity=6)";
        }
        enum debugging {
          value 7;
          description
            "Debugging messages                (severity=7)";
        }
        enum disable {
          value 15;
          description
            "Disable logging                               ";
        }
      }
      description
        "Set monitor logging";
    }
    container console-logging {
      description
        "Set console logging parameters";
      container console-log-facility {
        description
          "Modify message logging facilities";
        leaf console-facility-level {
          type enumeration {
            enum all {
              value 192;
              description
                "All Supported Facility";
            }
          }
          description
            "Console message logging facilities";
        }
      }
    }
    container monitor-discriminator {
      description
        "Set monitor logging discriminator";
      leaf match1 {
        type xr:Cisco-ios-xr-string {
          length "1..32" {
            description
              "match discriminator 1";
          }
        }
        description
          "Set match discriminator 1";
      }
      leaf match2 {
        type xr:Cisco-ios-xr-string {
          length "1..32" {
            description
              "match discriminator 2";
          }
        }
        description
          "Set match discriminator 2";
      }
      leaf match3 {
        type xr:Cisco-ios-xr-string {
          length "1..32" {
            description
              "match discriminator 3";
          }
        }
        description
          "Set match discriminator 3";
      }
      leaf nomatch1 {
        type xr:Cisco-ios-xr-string {
          length "1..32" {
            description
              "no-match discriminator 1";
          }
        }
        description
          "Set no-match discriminator 1";
      }
      leaf nomatch2 {
        type xr:Cisco-ios-xr-string {
          length "1..32" {
            description
              "no-match discriminator 2";
          }
        }
        description
          "Set no-match discriminator 2";
      }
      leaf nomatch3 {
        type xr:Cisco-ios-xr-string {
          length "1..32" {
            description
              "no-match discriminator 3";
          }
        }
        description
          "Set no-match discriminator 3";
      }
    }
    container archive {
      description
        "logging to a persistent device(disk/harddisk)";
      container device {
        description
          "Configure the archive device";
        container disk0 {
          must 'not(../disk1 or ../harddisk)';
          presence "Indicates a disk0 node is configured.";
          description
            "Use disk0 as the archive device";
        }
        container disk1 {
          must 'not(../disk0 or ../harddisk)';
          presence "Indicates a disk1 node is configured.";
          description
            "Use disk1 as the archive device";
        }
        container harddisk {
          must 'not(../disk0 or ../disk1)';
          presence "Indicates a harddisk node is configured.";
          description
            "Use harddisk as the archive device";
        }
      }
      container frequency {
        description
          "The collection interval for logs";
        container daily {
          must 'not(../weekly)';
          presence "Indicates a daily node is configured.";
          description
            "Collect log in files on a daily basis";
        }
        container weekly {
          must 'not(../daily)';
          presence "Indicates a weekly node is configured.";
          description
            "Collect log in files on a weekly basis";
        }
      }
      leaf file-size {
        type uint32 {
          range "1..2047" {
            description
              "Size in MB";
          }
        }
        description
          "The maximum file size for a single log file.";
      }
      leaf archive-size {
        type uint32 {
          range "1..2047" {
            description
              "Size in MB";
          }
        }
        description
          "The total size of the archive";
      }
      leaf archive-length {
        type uint32 {
          range "1..256" {
            description
              "Number of weeks";
          }
        }
        description
          "The maximum no of weeks of log to maintain";
      }
      leaf severity {
        type enumeration {
          enum emergencies {
            value 0;
            description
              "System is unusable                (severity=0)";
          }
          enum alerts {
            value 1;
            description
              "Immediate action needed           (severity=1)";
          }
          enum critical {
            value 2;
            description
              "Critical conditions               (severity=2)";
          }
          enum errors {
            value 3;
            description
              "Error conditions                  (severity=3)";
          }
          enum warnings {
            value 4;
            description
              "Warning conditions                (severity=4)";
          }
          enum notifications {
            value 5;
            description
              "Normal but significant conditions (severity=5)";
          }
          enum informational {
            value 6;
            description
              "Informational messages            (severity=6)";
          }
          enum debugging {
            value 7;
            description
              "Debugging messages                (severity=7)";
          }
        }
        description
          "The minimum severity of log messages to archive";
      }
      leaf threshold {
        type uint32 {
          range "1..99" {
            description
              "Threshold percent";
          }
        }
        description
          "The size threshold at which a syslog is generated";
      }
    }
    container ipv4 {
      description
        "Mark the dscp/precedence bit for ipv4 packets";
      leaf dscp {
        type union {
          type uint32 {
            range "0..63" {
              description
                "Differentiated services codepoint value";
            }
          }
          type enumeration {
            enum default {
              value 0;
              description
                "Match packets with default dscp (000000)";
            }
            enum cs1 {
              value 8;
              description
                "Match packets with CS1(precedence 1) dscp (001000)";
            }
            enum af11 {
              value 10;
              description
                "Match packets with AF11 dscp (001010)";
            }
            enum af12 {
              value 12;
              description
                "Match packets with AF12 dscp (001100)";
            }
            enum af13 {
              value 14;
              description
                "Match packets with AF13 dscp (001110)";
            }
            enum cs2 {
              value 16;
              description
                "Match packets with CS2(precedence 2) dscp (010000)";
            }
            enum af21 {
              value 18;
              description
                "Match packets with AF21 dscp (010010)";
            }
            enum af22 {
              value 20;
              description
                "Match packets with AF22 dscp (010100)";
            }
            enum af23 {
              value 22;
              description
                "Match packets with AF23 dscp (010110)";
            }
            enum cs3 {
              value 24;
              description
                "Match packets with CS3(precedence 3) dscp (011000)";
            }
            enum af31 {
              value 26;
              description
                "Match packets with AF31 dscp (011010)";
            }
            enum af32 {
              value 28;
              description
                "Match packets with AF32 dscp (011100)";
            }
            enum af33 {
              value 30;
              description
                "Match packets with AF33 dscp (011110)";
            }
            enum cs4 {
              value 32;
              description
                "Match packets with CS4(precedence 4) dscp (100000)";
            }
            enum af41 {
              value 34;
              description
                "Match packets with AF41 dscp (100010)";
            }
            enum af42 {
              value 36;
              description
                "Match packets with AF42 dscp (100100)";
            }
            enum af43 {
              value 38;
              description
                "Match packets with AF43 dscp (100110)";
            }
            enum cs5 {
              value 40;
              description
                "Match packets with CS5(precedence 5) dscp (101000)";
            }
            enum ef {
              value 46;
              description
                "Match packets with EF dscp (101110)";
            }
            enum cs6 {
              value 48;
              description
                "Match packets with CS6(precedence 6) dscp (110000)";
            }
            enum cs7 {
              value 56;
              description
                "Match packets with CS7(precedence 7) dscp (111000)";
            }
          }
        }
        must 'not(../precedence)';
        description
          "Set IP DSCP (DiffServ CodePoint)";
      }
      leaf precedence {
        type union {
          type uint32 {
            range "0..7" {
              description
                "Precedence value";
            }
          }
          type enumeration {
            enum routine {
              value 0;
              description
                "Match packets with routine precedence (0)";
            }
            enum priority {
              value 1;
              description
                "Match packets with priority precedence (1)";
            }
            enum immediate {
              value 2;
              description
                "Match packets with immediate precedence (2)";
            }
            enum flash {
              value 3;
              description
                "Match packets with flash precedence (3)";
            }
            enum flash-override {
              value 4;
              description
                "Match packets with flash override precedence (4)";
            }
            enum critical {
              value 5;
              description
                "Match packets with critical precedence (5)";
            }
            enum internet {
              value 6;
              description
                "Match packets with internetwork control precedence (6)";
            }
            enum network {
              value 7;
              description
                "Match packets with network control precedence (7)";
            }
          }
        }
        must 'not(../dscp)';
        description
          "Set precedence";
      }
    }
    container ipv6 {
      description
        "Mark the dscp/precedence bit for ipv6 packets";
      leaf dscp {
        type union {
          type uint32 {
            range "0..63" {
              description
                "Differentiated services codepoint value";
            }
          }
          type enumeration {
            enum default {
              value 0;
              description
                "Match packets with default dscp (000000)";
            }
            enum cs1 {
              value 8;
              description
                "Match packets with CS1(precedence 1) dscp (001000)";
            }
            enum af11 {
              value 10;
              description
                "Match packets with AF11 dscp (001010)";
            }
            enum af12 {
              value 12;
              description
                "Match packets with AF12 dscp (001100)";
            }
            enum af13 {
              value 14;
              description
                "Match packets with AF13 dscp (001110)";
            }
            enum cs2 {
              value 16;
              description
                "Match packets with CS2(precedence 2) dscp (010000)";
            }
            enum af21 {
              value 18;
              description
                "Match packets with AF21 dscp (010010)";
            }
            enum af22 {
              value 20;
              description
                "Match packets with AF22 dscp (010100)";
            }
            enum af23 {
              value 22;
              description
                "Match packets with AF23 dscp (010110)";
            }
            enum cs3 {
              value 24;
              description
                "Match packets with CS3(precedence 3) dscp (011000)";
            }
            enum af31 {
              value 26;
              description
                "Match packets with AF31 dscp (011010)";
            }
            enum af32 {
              value 28;
              description
                "Match packets with AF32 dscp (011100)";
            }
            enum af33 {
              value 30;
              description
                "Match packets with AF33 dscp (011110)";
            }
            enum cs4 {
              value 32;
              description
                "Match packets with CS4(precedence 4) dscp (100000)";
            }
            enum af41 {
              value 34;
              description
                "Match packets with AF41 dscp (100010)";
            }
            enum af42 {
              value 36;
              description
                "Match packets with AF42 dscp (100100)";
            }
            enum af43 {
              value 38;
              description
                "Match packets with AF43 dscp (100110)";
            }
            enum cs5 {
              value 40;
              description
                "Match packets with CS5(precedence 5) dscp (101000)";
            }
            enum ef {
              value 46;
              description
                "Match packets with EF dscp (101110)";
            }
            enum cs6 {
              value 48;
              description
                "Match packets with CS6(precedence 6) dscp (110000)";
            }
            enum cs7 {
              value 56;
              description
                "Match packets with CS7(precedence 7) dscp (111000)";
            }
          }
        }
        must 'not(../precedence)';
        description
          "Set IP DSCP (DiffServ CodePoint)";
      }
      leaf precedence {
        type union {
          type uint32 {
            range "0..7" {
              description
                "Precedence value";
            }
          }
          type enumeration {
            enum routine {
              value 0;
              description
                "Match packets with routine precedence (0)";
            }
            enum priority {
              value 1;
              description
                "Match packets with priority precedence (1)";
            }
            enum immediate {
              value 2;
              description
                "Match packets with immediate precedence (2)";
            }
            enum flash {
              value 3;
              description
                "Match packets with flash precedence (3)";
            }
            enum flash-override {
              value 4;
              description
                "Match packets with flash override precedence (4)";
            }
            enum critical {
              value 5;
              description
                "Match packets with critical precedence (5)";
            }
            enum internet {
              value 6;
              description
                "Match packets with internetwork control precedence (6)";
            }
            enum network {
              value 7;
              description
                "Match packets with network control precedence (7)";
            }
          }
        }
        must 'not(../dscp)';
        description
          "Set precedence";
      }
    }
    container facility {
      description
        "Modify message logging facilities";
      leaf level {
        type enumeration {
          enum kern {
            value 0;
            description
              "Kernel";
          }
          enum user {
            value 8;
            description
              "User process";
          }
          enum mail {
            value 16;
            description
              "Mail system";
          }
          enum daemon {
            value 24;
            description
              "System daemons";
          }
          enum auth {
            value 32;
            description
              "Authorization system";
          }
          enum syslog {
            value 40;
            description
              "Syslog itself";
          }
          enum authpriv {
            value 80;
            description
              "Privileged authorization messages";
          }
          enum ntp {
            value 96;
            description
              "NTP subsystem";
          }
          enum audit {
            value 104;
            description
              "log audit";
          }
          enum console {
            value 112;
            description
              "log alert messages";
          }
          enum local0 {
            value 128;
            description
              "Local use";
          }
          enum local1 {
            value 136;
            description
              "Local use";
          }
          enum local2 {
            value 144;
            description
              "Local use";
          }
          enum local3 {
            value 152;
            description
              "Local use";
          }
          enum local4 {
            value 160;
            description
              "Local use";
          }
          enum local5 {
            value 168;
            description
              "Local use";
          }
          enum local6 {
            value 176;
            description
              "Local use";
          }
          enum local7 {
            value 184;
            description
              "Local use";
          }
          enum all {
            value 192;
            description
              "All supported facilities";
          }
        }
        description
          "configure this node";
      }
    }
    container buffered {
      description
        "Set buffered logging parameters";
      container buffered-entries {
        description
          "Syslog in buffer";
        leaf count {
          type uint32 {
            range "2545..151699" {
              description
                "Number of syslog entries in buffer";
            }
          }
          description
            "Number of syslog entries in buffer";
        }
      }
      leaf logging-buffer-size {
        type uint32 {
          range "307200..125000000" {
            description
              "Logging buffer size";
          }
        }
        description
          "Logging buffer size";
      }
      leaf level {
        type enumeration {
          enum emergencies {
            value 0;
            description
              "System is unusable";
          }
          enum alerts {
            value 1;
            description
              "Immediate action needed";
          }
          enum critical {
            value 2;
            description
              "Critical conditions";
          }
          enum errors {
            value 3;
            description
              "Error conditions";
          }
          enum warnings {
            value 4;
            description
              "Warning conditions";
          }
          enum notifications {
            value 5;
            description
              "Normal but significant conditions";
          }
          enum informational {
            value 6;
            description
              "Informational messages";
          }
          enum debugging {
            value 7;
            description
              "Debugging messages";
          }
        }
        description
          "configure this node";
      }
      container discriminator {
        description
          "Set logging buffer discriminator";
        leaf match1 {
          type xr:Cisco-ios-xr-string {
            length "1..32" {
              description
                "match discriminator 1";
            }
          }
          description
            "Set match discriminator 1";
        }
        leaf match2 {
          type xr:Cisco-ios-xr-string {
            length "1..32" {
              description
                "match discriminator 2";
            }
          }
          description
            "Set match discriminator 2";
        }
        leaf match3 {
          type xr:Cisco-ios-xr-string {
            length "1..32" {
              description
                "match discriminator 3";
            }
          }
          description
            "Set match discriminator 3";
        }
        leaf nomatch1 {
          type xr:Cisco-ios-xr-string {
            length "1..32" {
              description
                "no-match discriminator 1";
            }
          }
          description
            "Set no-match discriminator 1";
        }
        leaf nomatch2 {
          type xr:Cisco-ios-xr-string {
            length "1..32" {
              description
                "no-match discriminator 2";
            }
          }
          description
            "Set no-match discriminator 2";
        }
        leaf nomatch3 {
          type xr:Cisco-ios-xr-string {
            length "1..32" {
              description
                "no-match discriminator 3";
            }
          }
          description
            "Set no-match discriminator 3";
        }
      }
    }
    container container {
      description "Enable to include containers application logs";

      container all {
        presence "Indicates a all node is configured.";
        description "Enables log collection from all containers";
      }
      container fetch-timestamp {
        presence "Indicates a fetch-timestamp node is configured.";
        description "Fetch logs with container timestamp for all containers";
      }
    }
    container files {
      description
        "Set file logging";
      list file {
        key "file-name";
        description
          "Set file logging";
        leaf file-name {
          type xr:Cisco-ios-xr-string {
            length "1..256" {
              description
                "File name";
            }
          }
          description
            "Set file logging";
        }
        leaf path {
          type string {
            length "1..256" {
              description
                "File path (e.g. /disk0: )";
            }
          }
          mandatory true;
          description
            "Set file path ";
        }
        leaf maxfilesize {
          type uint32 {
            range "1..2097152" {
              description
                "Max file size (in KB)";
            }
          }
          mandatory true;
          description
            "Set max file size";
        }
        leaf severity {
          type enumeration {
            enum emergencies {
              value 0;
              description
                "System is unusable                (severity=0)";
            }
            enum alerts {
              value 1;
              description
                "Immediate action needed           (severity=1)";
            }
            enum critical {
              value 2;
              description
                "Critical conditions               (severity=2)";
            }
            enum error {
              value 3;
              description
                "Error conditions                  (severity=3)";
            }
            enum warning {
              value 4;
              description
                "Warning conditions                (severity=4)";
            }
            enum notifications {
              value 5;
              description
                "Normal but significant conditions (severity=5)";
            }
            enum info {
              value 6;
              description
                "Informational messages            (severity=6)";
            }
            enum debugging {
              value 7;
              description
                "Debugging messages                (severity=7)";
            }
          }
          mandatory true;
          description
            "Set severity level";
        }
        container local-accounting {
          presence "Indicates a local-accounting node is configured.";
          description
            "Store only the command accounting logs";
          container send-to-remote {
            description
              "Send the command accounting logs to syslog server";
            container facility {
              description
                "Modify message logging facilities";
              leaf level {
                type enumeration {
                  enum kern {
                    value 0;
                    description
                      "Kernel";
                  }
                  enum user {
                    value 8;
                    description
                      "User process";
                  }
                  enum mail {
                    value 16;
                    description
                      "Mail system";
                  }
                  enum daemon {
                    value 24;
                    description
                      "System daemons";
                  }
                  enum auth {
                    value 32;
                    description
                      "Authorization system";
                  }
                  enum syslog {
                    value 40;
                    description
                      "Syslog itself";
                  }
                  enum lpr {
                    value 48;
                    description
                      " Line printer system";
                  }
                  enum news {
                    value 56;
                    description
                      "USENET news";
                  }
                  enum uucp {
                    value 64;
                    description
                      "Unix-to-Unix copy system";
                  }
                  enum cron {
                    value 72;
                    description
                      "Cron/at facility";
                  }
                  enum local0 {
                    value 128;
                    description
                      "Local use";
                  }
                  enum local1 {
                    value 136;
                    description
                      "Local use";
                  }
                  enum local2 {
                    value 144;
                    description
                      "Local use";
                  }
                  enum local3 {
                    value 152;
                    description
                      "Local use";
                  }
                  enum local4 {
                    value 160;
                    description
                      "Local use";
                  }
                  enum local5 {
                    value 168;
                    description
                      "Local use";
                  }
                  enum local6 {
                    value 176;
                    description
                      "Local use";
                  }
                  enum local7 {
                    value 184;
                    description
                      "Local use";
                  }
                  enum sys9 {
                    value 192;
                    description
                      "System use";
                  }
                  enum sys10 {
                    value 200;
                    description
                      "System use";
                  }
                  enum sys11 {
                    value 208;
                    description
                      "System use";
                  }
                  enum sys12 {
                    value 216;
                    description
                      "System use";
                  }
                  enum sys13 {
                    value 224;
                    description
                      "System use";
                  }
                  enum sys14 {
                    value 232;
                    description
                      "System use";
                  }
                }
                description
                  "configure this node";
              }
            }
          }
        }
        container discriminator {
          description
            "Set file logging discriminator";
          leaf match1 {
            type xr:Cisco-ios-xr-string {
              length "1..32" {
                description
                  "match discriminator 1";
              }
            }
            description
              "Set match discriminator 1";
          }
          leaf match2 {
            type xr:Cisco-ios-xr-string {
              length "1..32" {
                description
                  "match discriminator 2";
              }
            }
            description
              "Set match discriminator 2";
          }
          leaf match3 {
            type xr:Cisco-ios-xr-string {
              length "1..32" {
                description
                  "match discriminator 3";
              }
            }
            description
              "Set match discriminator 3";
          }
          leaf nomatch1 {
            type xr:Cisco-ios-xr-string {
              length "1..32" {
                description
                  "no-match discriminator 1";
              }
            }
            description
              "Set no-match discriminator 1";
          }
          leaf nomatch2 {
            type xr:Cisco-ios-xr-string {
              length "1..32" {
                description
                  "no-match discriminator 2";
              }
            }
            description
              "Set no-match discriminator 2";
          }
          leaf nomatch3 {
            type xr:Cisco-ios-xr-string {
              length "1..32" {
                description
                  "no-match discriminator 3";
              }
            }
            description
              "Set no-match discriminator 3";
          }
        }
      }
    }
    leaf history {
      type enumeration {
        enum emergencies {
          value 0;
          description
            "System is unusable";
        }
        enum alerts {
          value 1;
          description
            "Immediate action needed";
        }
        enum critical {
          value 2;
          description
            "Critical conditions";
        }
        enum errors {
          value 3;
          description
            "Error conditions";
        }
        enum warnings {
          value 4;
          description
            "Warning conditions";
        }
        enum notifications {
          value 5;
          description
            "Normal but significant conditions";
        }
        enum informational {
          value 6;
          description
            "Informational messages";
        }
        enum debugging {
          value 7;
          description
            "Debugging messages";
        }
        enum disable {
          value 15;
          description
            "Disable logging";
        }
      }
      description
        "Set history logging";
    }
    leaf history-size {
      type uint32 {
        range "1..500" {
          description
            "Logging history size";
        }
      }
      description
        "Logging history size";
    }
    container tls-servers {
      description
        "Secure server over tls";
      list tls-server {
        key "tls-server-name";
        description
          "Secure server over tls";
        leaf tls-server-name {
          type string {
            length "1..800" {
              description
                "Name for the tls peer configuration";
            }
          }
          description
            "Secure server over tls";
        }
        leaf vrf {
          type xr:Cisco-ios-xr-string {
            length "1..32" {
              description
                "VPN Routing/Forwarding instance name";
            }
          }
          description
            "Set VRF option";
        }
        container address {
          description
            "Specify a TLS server address";
          leaf ipv4 {
            type inet:ipv4-address-no-zone;
            description
              "IPv4 Address";
          }
          leaf ipv6 {
            type inet:ipv6-address-no-zone;
            description
              "IPv6 Address";
          }
        }
        leaf tls-hostname {
          type xr:Cisco-ios-xr-string {
            length "1..800" {
              description
                "Name of the logging host";
            }
          }
          description
            "Hostname or FQDN of Secure Log server";
        }
        leaf trustpoint {
          type xr:Cisco-ios-xr-string {
            length "1..32" {
              description
                "Name of the trustpoint configured";
            }
          }
          description
            "Trustpoint";
        }
        leaf severity {
          type enumeration {
            enum emergencies {
              value 0;
              description
                "System is unusable                (severity=0)";
            }
            enum alerts {
              value 1;
              description
                "Immediate action needed           (severity=1)";
            }
            enum critical {
              value 2;
              description
                "Critical conditions               (severity=2)";
            }
            enum errors {
              value 3;
              description
                "Error conditions                  (severity=3)";
            }
            enum warnings {
              value 4;
              description
                "Warning conditions                (severity=4)";
            }
            enum notifications {
              value 5;
              description
                "Normal but significant conditions (severity=5)";
            }
            enum informational {
              value 6;
              description
                "Informational messages            (severity=6)";
            }
            enum debugging {
              value 7;
              description
                "Debugging messages                (severity=7)";
            }
          }
          description
            "severity of remote host";
        }
      }
    }
    container vrfs {
      description
        "Set VRF option";
      list vrf {
        key "vrf-name";
        description
          "Set VRF option";
        leaf vrf-name {
          type union {
            type string {
              pattern 'default' {
                description
                  "Default VRF name";
              }
            }
            type xr:Cisco-ios-xr-string {
              length "1..32" {
                description
                  "VPN Routing/Forwarding instance name";
              }
            }
          }
          description
            "Set VRF option";
        }
        container host-names {
          description
            "Name of the logging host";
          list host-name {
            key "name";
            description
              "Name of the logging host";
            leaf name {
              type xr:Cisco-ios-xr-string {
                length "1..1024" {
                  description
                    "Name of the logging host";
                }
                pattern '[a-zA-Z0-9._-]+';
              }
              description
                "Name of the logging host";
            }
            leaf severity {
              type enumeration {
                enum emergencies {
                  value 0;
                  description
                    "System is unusable                (severity=0)";
                }
                enum alerts {
                  value 1;
                  description
                    "Immediate action needed           (severity=1)";
                }
                enum critical {
                  value 2;
                  description
                    "Critical conditions               (severity=2)";
                }
                enum error {
                  value 3;
                  description
                    "Error conditions                  (severity=3)";
                }
                enum warning {
                  value 4;
                  description
                    "Warning conditions                (severity=4)";
                }
                enum notifications {
                  value 5;
                  description
                    "Normal but significant conditions (severity=5)";
                }
                enum info {
                  value 6;
                  description
                    "Informational messages            (severity=6)";
                }
                enum debugging {
                  value 7;
                  description
                    "Debugging messages                (severity=7)";
                }
              }
              description
                "Set severity of  messages for particular remote host/vrf";
            }
            leaf port {
              type uint32 {
                range "0..65535" {
                  description
                    "Port number";
                }
              }
              description
                "Set UDP port for this remote host/vrf";
            }
            leaf operator {
              type enumeration {
                enum equals-or-higher {
                  value 0;
                  description
                    "Log messages equal to or higher than severity";
                }
                enum equals {
                  value 1;
                  description
                    "Log messages equal to severity";
                }
                enum not-equals {
                  value 2;
                  description
                    "Log messages not equal to severity";
                }
              }
              description
                "Set severity operator of  messages for particular remote host/vrf";
            }
            leaf facility {
              type enumeration {
                enum kern {
                  value 0;
                  description
                    "Kernel";
                }
                enum user {
                  value 8;
                  description
                    "User process";
                }
                enum mail {
                  value 16;
                  description
                    "Mail system";
                }
                enum daemon {
                  value 24;
                  description
                    "System daemons";
                }
                enum auth {
                  value 32;
                  description
                    "Authorization system";
                }
                enum syslog {
                  value 40;
                  description
                    "Syslog itself";
                }
                enum authpriv {
                  value 80;
                  description
                    "Privileged authorization messages";
                }
                enum ntp {
                  value 96;
                  description
                    "NTP subsystem";
                }
                enum audit {
                  value 104;
                  description
                    "log audit";
                }
                enum console {
                  value 112;
                  description
                    "log alert messages";
                }
                enum local0 {
                  value 128;
                  description
                    "Local use";
                }
                enum local1 {
                  value 136;
                  description
                    "Local use";
                }
                enum local2 {
                  value 144;
                  description
                    "Local use";
                }
                enum local3 {
                  value 152;
                  description
                    "Local use";
                }
                enum local4 {
                  value 160;
                  description
                    "Local use";
                }
                enum local5 {
                  value 168;
                  description
                    "Local use";
                }
                enum local6 {
                  value 176;
                  description
                    "Local use";
                }
                enum local7 {
                  value 184;
                  description
                    "Local use";
                }
                enum all {
                  value 192;
                  description
                    "All supported facilities";
                }
              }
              description
                "Modify message logging facilities";
            }
            leaf hostname-source-address {
              type inet:ip-address-no-zone;
              description
                "hostname source address";
            }
          }
        }
        container host-ipv4-addresses {
          description
            "IPV4 address of the logging host";
          list host-ipv4-address {
            key "ipv4-address";
            description
              "IPV4 address of the logging host";
            leaf ipv4-address {
              type inet:ipv4-address-no-zone;
              description
                "IPV4 address of the logging host";
            }
            leaf severity {
              type enumeration {
                enum emergencies {
                  value 0;
                  description
                    "System is unusable                (severity=0)";
                }
                enum alerts {
                  value 1;
                  description
                    "Immediate action needed           (severity=1)";
                }
                enum critical {
                  value 2;
                  description
                    "Critical conditions               (severity=2)";
                }
                enum error {
                  value 3;
                  description
                    "Error conditions                  (severity=3)";
                }
                enum warning {
                  value 4;
                  description
                    "Warning conditions                (severity=4)";
                }
                enum notifications {
                  value 5;
                  description
                    "Normal but significant conditions (severity=5)";
                }
                enum info {
                  value 6;
                  description
                    "Informational messages            (severity=6)";
                }
                enum debugging {
                  value 7;
                  description
                    "Debugging messages                (severity=7)";
                }
              }
              description
                "Set severity of  messages for particular remote host/vrf";
            }
            leaf port {
              type uint32 {
                range "0..65535" {
                  description
                    "Port number";
                }
              }
              description
                "Set UDP port for this remote host/vrf";
            }
            leaf operator {
              type enumeration {
                enum equals-or-higher {
                  value 0;
                  description
                    "Log messages equal to or higher than severity";
                }
                enum equals {
                  value 1;
                  description
                    "Log messages equal to severity";
                }
                enum not-equals {
                  value 2;
                  description
                    "Log messages not equal to severity";
                }
              }
              description
                "Set severity operator of  messages for particular remote host/vrf";
            }
            leaf facility {
              type enumeration {
                enum kern {
                  value 0;
                  description
                    "Kernel";
                }
                enum user {
                  value 8;
                  description
                    "User process";
                }
                enum mail {
                  value 16;
                  description
                    "Mail system";
                }
                enum daemon {
                  value 24;
                  description
                    "System daemons";
                }
                enum auth {
                  value 32;
                  description
                    "Authorization system";
                }
                enum syslog {
                  value 40;
                  description
                    "Syslog itself";
                }
                enum authpriv {
                  value 80;
                  description
                    "Privileged authorization messages";
                }
                enum ntp {
                  value 96;
                  description
                    "NTP subsystem";
                }
                enum audit {
                  value 104;
                  description
                    "log audit";
                }
                enum console {
                  value 112;
                  description
                    "log alert messages";
                }
                enum local0 {
                  value 128;
                  description
                    "Local use";
                }
                enum local1 {
                  value 136;
                  description
                    "Local use";
                }
                enum local2 {
                  value 144;
                  description
                    "Local use";
                }
                enum local3 {
                  value 152;
                  description
                    "Local use";
                }
                enum local4 {
                  value 160;
                  description
                    "Local use";
                }
                enum local5 {
                  value 168;
                  description
                    "Local use";
                }
                enum local6 {
                  value 176;
                  description
                    "Local use";
                }
                enum local7 {
                  value 184;
                  description
                    "Local use";
                }
                enum all {
                  value 192;
                  description
                    "All supported facilities";
                }
              }
              description
                "Modify message logging facilities";
            }
            leaf ipv4-source-address {
              type inet:ipv4-address-no-zone;
              description
                "IPV4 source address of the logging host";
            }
          }
        }
        container host-ipv6-addresses {
          description
            "IPV6 address of the logging host";
          list host-ipv6-address {
            key "ipv6-address";
            description
              "IPV6 address of the logging host";
            leaf ipv6-address {
              type inet:ipv6-address-no-zone;
              description
                "IPV6 address of the logging host";
            }
            leaf severity {
              type enumeration {
                enum emergencies {
                  value 0;
                  description
                    "System is unusable                (severity=0)";
                }
                enum alerts {
                  value 1;
                  description
                    "Immediate action needed           (severity=1)";
                }
                enum critical {
                  value 2;
                  description
                    "Critical conditions               (severity=2)";
                }
                enum error {
                  value 3;
                  description
                    "Error conditions                  (severity=3)";
                }
                enum warning {
                  value 4;
                  description
                    "Warning conditions                (severity=4)";
                }
                enum notifications {
                  value 5;
                  description
                    "Normal but significant conditions (severity=5)";
                }
                enum info {
                  value 6;
                  description
                    "Informational messages            (severity=6)";
                }
                enum debugging {
                  value 7;
                  description
                    "Debugging messages                (severity=7)";
                }
              }
              description
                "Set severity of  messages for particular remote host/vrf";
            }
            leaf port {
              type uint32 {
                range "0..65535" {
                  description
                    "Port number";
                }
              }
              description
                "Set UDP port for this remote host/vrf";
            }
            leaf operator {
              type enumeration {
                enum equals-or-higher {
                  value 0;
                  description
                    "Log messages equal to or higher than severity";
                }
                enum equals {
                  value 1;
                  description
                    "Log messages equal to severity";
                }
                enum not-equals {
                  value 2;
                  description
                    "Log messages not equal to severity";
                }
              }
              description
                "Set severity operator of  messages for particular remote host/vrf";
            }
            leaf facility {
              type enumeration {
                enum kern {
                  value 0;
                  description
                    "Kernel";
                }
                enum user {
                  value 8;
                  description
                    "User process";
                }
                enum mail {
                  value 16;
                  description
                    "Mail system";
                }
                enum daemon {
                  value 24;
                  description
                    "System daemons";
                }
                enum auth {
                  value 32;
                  description
                    "Authorization system";
                }
                enum syslog {
                  value 40;
                  description
                    "Syslog itself";
                }
                enum authpriv {
                  value 80;
                  description
                    "Privileged authorization messages";
                }
                enum ntp {
                  value 96;
                  description
                    "NTP subsystem";
                }
                enum audit {
                  value 104;
                  description
                    "log audit";
                }
                enum console {
                  value 112;
                  description
                    "log alert messages";
                }
                enum local0 {
                  value 128;
                  description
                    "Local use";
                }
                enum local1 {
                  value 136;
                  description
                    "Local use";
                }
                enum local2 {
                  value 144;
                  description
                    "Local use";
                }
                enum local3 {
                  value 152;
                  description
                    "Local use";
                }
                enum local4 {
                  value 160;
                  description
                    "Local use";
                }
                enum local5 {
                  value 168;
                  description
                    "Local use";
                }
                enum local6 {
                  value 176;
                  description
                    "Local use";
                }
                enum local7 {
                  value 184;
                  description
                    "Local use";
                }
                enum all {
                  value 192;
                  description
                    "All supported facilities";
                }
              }
              description
                "Modify message logging facilities";
            }
            leaf ipv6-source-address {
              type inet:ipv6-address-no-zone;
              description
                "IPV6 source address of the logging host";
            }
          }
        }
      }
    }
    leaf hostnameprefix {
      type xr:Cisco-ios-xr-string {
        length "1..800" {
          description
            "hostname prefix string";
        }
      }
      description
        "Hostname prefix to add on msgs to servers";
    }
    leaf localfilesize {
      type uint32 {
        range "0..4294967295" {
          description
            "Size of the local log file";
        }
      }
      description
        "Set size of the local log file";
    }
    container source-interfaces {
      description
        "Specify interface for source address in logging transactions";
      list source-interface {
        key "source-interface-name";
        description
          "Specify interface for source address in logging transactions";
        leaf source-interface-name {
          type xr:Interface-name;
          description
            "Specify interface for source address in logging transactions";
        }
        container vrfs {
          description
            "Set VRF option";
          list vrf {
            key "vrf-name";
            description
              "Set VRF option";
            leaf vrf-name {
              type union {
                type string {
                  pattern 'default' {
                    description
                      "Default vrf name";
                  }
                }
                type xr:Cisco-ios-xr-string {
                  length "1..1024" {
                    description
                      "specify the vrf name";
                  }
                }
              }
              description
                "Set VRF option";
            }
          }
        }
      }
    }
    container suppress {
      description
        "Suppress logging behaviour";
      container duplicates {
        presence "Indicates a duplicates node is configured.";
        description
          "Suppress consecutive duplicate messages";
      }
    }
    container format {
      description
        "Specify syslog message format send to the server";
      container rfc5424 {
        must 'not(../bsd)';
        presence "Indicates a rfc5424 node is configured.";
        description
          "Enable to send the syslog message rfc5424 format ";
      }
      container bsd {
        must 'not(../rfc5424)';
        presence "Indicates a bsd node is configured.";
        description
          "Enable to send the syslog message as BSD format ";
      }
    }
    leaf yang {
      type enumeration {
        enum emergencies {
          value 0;
          description
            "System is unusable";
        }
        enum alerts {
          value 1;
          description
            "Immediate action needed";
        }
        enum critical {
          value 2;
          description
            "Critical conditions";
        }
        enum errors {
          value 3;
          description
            "Error conditions";
        }
        enum warnings {
          value 4;
          description
            "Warning conditions";
        }
        enum notifications {
          value 5;
          description
            "Normal but significant conditions";
        }
        enum informational {
          value 6;
          description
            "Informational messages";
        }
        enum debugging {
          value 7;
          description
            "Debugging messages";
        }
      }
      description
        "Set yang logging parameters";
    }
  }
}
