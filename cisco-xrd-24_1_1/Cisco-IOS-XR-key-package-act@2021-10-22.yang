module Cisco-IOS-XR-key-package-act {
  namespace "http://cisco.com/ns/yang/Cisco-IOS-XR-key-package-act";
  prefix sb-kpkg;

  import Cisco-IOS-XR-types {
    prefix csc;
  }

  organization
    "Cisco Systems, Inc.";
  contact
    "Cisco Systems, Inc.
     Customer Service
     Postal: 170 West Tasman Drive
     San Jose, CA 95134
     Tel: +1 800 553-NETS
     E-mail: cs-yang@cisco.com";
  description
    "This module defines procedure to apply key package. 

     Copyright (c) 2017 IETF Trust and the persons identified
     as authors of the code. All rights reserved.

     Redistribution and use in source and binary forms, with
     or without modification, is permitted pursuant to, and
     subject to the license terms contained in, the Simplified
     BSD License set forth in Section 4.c of the IETF Trust''s
     Legal Provisions Relating to IETF Documents
     (http://trustee.ietf.org/license-info).

     This version of this YANG module is part of RFC VVVV; see
     the RFC itself for full legal notices.";

  revision "2021-10-22" {
    description
      "NSO build related fixes";
  }


  revision "2021-09-08" {
    description
      "Initial revision.";
  }


  typedef kpkg_type {
      type enumeration {
          enum customer {
              value 1;
              description
              "Key Package is signed by Customer Key";
          }
      }
      description
      "Signer of the key package";
  }

  rpc kpkg-apply {
    description
      "Applies a Key Package to the system.
       Returns whether operation is succeeded or failed.
       When in error condition, error code will be populated.";
    input {
      leaf keypackage-type {
        type kpkg_type;
        mandatory true;
        description
          " Type of key package. In revision 1, only customer key packages
            are supported";
      }
      leaf keypackage-file {
        type string;
        mandatory true;
        description
          "Key package file path on local filesystem";
      }
    }

    csc:xr-task "system";
  }
}
