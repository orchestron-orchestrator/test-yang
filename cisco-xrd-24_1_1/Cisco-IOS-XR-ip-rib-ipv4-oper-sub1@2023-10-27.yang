submodule Cisco-IOS-XR-ip-rib-ipv4-oper-sub1 {

  belongs-to Cisco-IOS-XR-ip-rib-ipv4-oper {
    prefix Cisco-IOS-XR-ip-rib-ipv4-oper;
  }

  /*** LINKAGE (IMPORTS / INCLUDES) ***/

  import ietf-inet-types { prefix "inet"; }

  import ietf-yang-types { prefix "yang"; }

  import Cisco-IOS-XR-types { prefix "xr"; }

  import cisco-semver { prefix "semver"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ip-rib-ipv4 package operational data.

     Copyright (c) 2013-2023 by Cisco Systems, Inc.
     All rights reserved.";

  revision "2023-10-27" {
    description
      "Minor protocol and infosource field renaming for consistency
       2023-10-06
         Add IID Context for NextHop Groups
       2023-09-20
         Consolidate RIB schemas to use unioned IPv4/IPv6 address in routes and paths
       2023-08-31
         Update RIB-EDM-PATH-IP-TUNNEL-INFO
       2023-02-16
         Update RIB NHID info
       2022-12-13
         Modify RIB opaque redist history
       2022-12-02
         Modify RIB redist history
       2022-11-23
         Modify RIB stats
       2022-11-03
         Update IID Context for Segment List Identifier
       2022-09-13
         Add IID Context for Segment List Identifier
       2022-08-29
         Segment List Identifier added to a routes path
       2022-08-18
         Updated IID entry infromation to display IID as an IPv6 prefix
       2022-07-04
         Add IID Context for L2VPN IP Tunnels. Add Remote Tunnel Endpoint ID: RTEP ID, to resolve via tunnel.
       2022-05-11
         has-aft added to route
       2022-04-26
         Clear AFT stats added
       2022-02-18
         Add client id, proto id, flags, backup number and distance to opaque bag Added table-id for opaque redistribution history
       2022-01-11
         Add IID Context for AFT NextHop Groups
       2021-12-16
         Updated aft route and path attributes with vrf names
       2021-12-16
         Added VNI to ip tunnel info path attribute
       2021-12-14
         Updated aft route and path attributes
       2021-11-26
         Add IID Local to known Protocol Types
       2021-11-17
         Add AFT id path and route attributes
       2021-10-29
         Added Opaque redistribution history
       2021-09-24
         New path vpn attribute for ip tunnels";
    semver:module-version "5.0.0";
  }

  revision "2021-07-20" {
    description
      "Flexible Algorithm attribute added to IP Route
      2021-06-24
          L2 Path attribute extended with support for Split Horizong Group and BridgeID
      2021-03-25
          Add FIB redistribution flag to route bag";
    semver:module-version "4.1.0";
  }

  revision "2020-12-11" {
    description
      "Add forwarding sidlist
      2020-10-16
           Route model now includes optional SRv6 SID Format field for SRv6 Local SID routes
      2020-09-30
           Nexthop notification model now includes client specific registration flags";
    semver:module-version "4.0.0";
  }

  revision "2020-05-29" {
    description
      "Updated the max number of elements for opaque stats to 16 Extended rib edm path to include IID info and SID Format type
      2020-04-02
         Increased path_num size in redist hist route bag to 16 bits";
    semver:module-version "3.0.0";
  }

  revision "2019-11-05" {
    description
      "Extended Nexthop and NexhopPrefix paths to include all by NH flags
      2019-10-22
         Extended rib_edm_client_stats_summary to include client stats on bcdl ugs Extended rib_edm_local_label to support AIB prefer Extended rib_edm_path to include recursion length field Extended rib_edm_path to include metric field Extended iidmgr_summary to include oor summary info Extended rib_edm_route to include l3 route type field";
    semver:module-version "2.0.0";
  }

  revision "2019-06-28" {
    description
      "Fixed NexthopPrefix path";
    semver:module-version "1.0.0";
  }

  revision "2019-06-08" {
    description
      "Added RPF list and NHIDs";
  }

  revision "2019-05-30" {
    description
      "Fixed adverts and backup paths";
  }

  revision "2019-05-17" {
    description
      "Added Nexthops Summary, Nexthop Route, Longer Routes, Redist Clients and Client Stasts";
  }

  revision "2019-04-25" {
    description
      "Updated yang schema to extend Native Yang model for the data exposed via CLI";
  }

  revision "2019-04-05" {
    description
      "Establish semantic version baseline.";
  }

  revision "2019-02-21" {
    description
      "Yang evaluator: updates to schema descriptions and ranges";
  }

  revision "2019-01-11" {
    description
      "Route lookup key is limited to Prefix and Prefix Length";
  }

  revision "2018-11-20" {
    description
      "Add keys for route lookup via restconf.";
  }

  revision "2018-11-06" {
    description
      "Support Algorithm Label List per route";
  }

  revision "2015-11-09" {
    description
      "IOS XR 6.0 revision.";
  }

  typedef Rib-opaque {
    type enumeration {
      enum opaque-attribute {
        value 0;
        description "opaque attribute";
      }
      enum opaque-ipfrr {
        value 1;
        description "opaque ipfrr";
      }
      enum opaque-ip-nh {
        value 2;
        description "opaque ip nh";
      }
      enum opaque-tunnel-nh {
        value 3;
        description "opaque tunnel nh";
      }
      enum opaque-tunnel-safi {
        value 4;
        description "opaque tunnel safi";
      }
      enum opaque-virtual-ll-address {
        value 5;
        description "opaque virtual ll address";
      }
      enum opaque-lisp {
        value 6;
        description "opaque lisp";
      }
      enum opaque-tep-vxlan {
        value 7;
        description "opaque tep vxlan";
      }
      enum opaque-tep-bgp {
        value 8;
        description "opaque tep bgp";
      }
      enum opaque-cofo-s-label {
        value 9;
        description "opaque cofo s label";
      }
      enum opaque-cofo-nnh-if {
        value 10;
        description "opaque cofo nnh if";
      }
      enum opaque-cofo-mcast {
        value 11;
        description "opaque cofo mcast";
      }
      enum opaque-label-range {
        value 12;
        description "opaque label range";
      }
      enum opaque-tep {
        value 13;
        description "opaque tep";
      }
      enum opaque-ipv4-adj {
        value 14;
        description "opaque ipv4 adj";
      }
      enum opaque-ipv6-adj {
        value 15;
        description "opaque ipv6 adj";
      }
      enum opaque-sfi {
        value 16;
        description "opaque sfi";
      }
      enum opaque-ltep {
        value 17;
        description "opaque ltep";
      }
      enum opaque-aft-nh {
        value 18;
        description "opaque aft nh";
      }
      enum opaque-rtep {
        value 19;
        description "opaque rtep";
      }
      enum opaque-encap-id {
        value 20;
        description "opaque encap id";
      }
      enum opaque-policy {
        value 21;
        description "opaque policy";
      }
      enum opaque-max {
        value 22;
        description "opaque max";
      }
    }
    description "Rib opaque";
  }
  typedef Rib-edm-sl-id {
    type enumeration {
      enum invalid {
        description "Invalid Segment List";
      }
      enum srv6 {
        description "SRv6 Segment List";
      }
      enum mpls {
        description "MPLS Segment List";
      }
    }
    description "Rib edm sl id";
  }
  typedef Rib-via-aft-id {
    type enumeration {
      enum none {
        description "Via None";
      }
      enum via-nh-aft-id {
        description "Via Next-hop AFT ID";
      }
      enum via-nh-group-aft-id {
        description "Via Next-hop Group AFT ID";
      }
    }
    description "Rib via aft id";
  }
  typedef Mgmt-srv6-headend {
    type enumeration {
      enum unknown {
        description "Unknown";
      }
      enum transit {
        description "T (Pure transit)";
      }
      enum h-insert {
        description "H.Insert";
      }
      enum h-insert-red {
        description "H.Insert.Red";
      }
      enum h-encaps {
        description "H.Encaps";
      }
      enum h-encaps-red {
        description "H.Encaps.Red";
      }
      enum h-encaps-l2 {
        description "H.Encaps.L2";
      }
      enum h-encaps-l2-red {
        description "H.Encaps.L2.Red";
      }
    }
    description "SRv6 Headend Behavior Type";
  }
  typedef Rib-edm-nnh {
    type enumeration {
      enum unknown {
        description "Unknown - Invalid";
      }
      enum ipv4-address {
        description "IPv4 Address";
      }
      enum if-index {
        description "Interface Index";
      }
    }
    description "Rib edm nnh";
  }
  typedef Rib-edm-safi-id {
    type enumeration {
      enum none {
        value 0;
        description "No sub-address family";
      }
      enum unicast {
        value 1;
        description "Unicast SAFI";
      }
      enum multicast {
        value 2;
        description "Multicast SAFI";
      }
    }
    description "Rib edm safi id";
  }
  typedef Mgmt-srv6-sid-fmt {
    type enumeration {
      enum none {
        value 0;
        description "No format";
      }
      enum base {
        value 1;
        description "Base Format";
      }
      enum f3216 {
        value 2;
        description "Micro-segment F3216 Format";
      }
    }
    description "SRv6 SID Format Type";
  }
  typedef Mgmt-srv6-endpoint {
    type enumeration {
      enum unknown {
        value 0;
        description "Unknown Endpoint type";
      }
      enum end {
        value 1;
        description "End (no PSP/USP)";
      }
      enum end-with-psp {
        value 2;
        description "End with PSP";
      }
      enum end-with-usp {
        value 3;
        description "End with USP";
      }
      enum end-with-psp-usp {
        value 4;
        description "End with PSP/USP";
      }
      enum end-x {
        value 5;
        description "End.X (no PSP/USP)";
      }
      enum end-x-with-psp {
        value 6;
        description "End.X with PSP";
      }
      enum end-x-with-usp {
        value 7;
        description "End.X with USP";
      }
      enum end-x-with-psp-usp {
        value 8;
        description "End.X with PSP/USP";
      }
      enum end-tbl {
        value 9;
        description "End.T (no PSP/USP)";
      }
      enum end-tbl-with-psp {
        value 10;
        description "End.T with PSP";
      }
      enum end-tbl-with-usp {
        value 11;
        description "End.T with USP";
      }
      enum end-tbl-with-psp-usp {
        value 12;
        description "End.T with PSP/USP";
      }
      enum end-b6-insert {
        value 13;
        description "End.B6.Insert";
      }
      enum end-b6-encaps {
        value 14;
        description "End.B6.Encaps";
      }
      enum end-bm {
        value 15;
        description "End.BM";
      }
      enum end-dx6 {
        value 16;
        description "End.DX6";
      }
      enum end-dx4 {
        value 17;
        description "End.DX4";
      }
      enum end-dt6 {
        value 18;
        description "End.DT6";
      }
      enum end-dt4 {
        value 19;
        description "End.DT4";
      }
      enum end-dt46 {
        value 20;
        description "End.DT46";
      }
      enum end-dx2 {
        value 21;
        description "End.DX2";
      }
      enum end-dx2v {
        value 22;
        description "End.DX2V";
      }
      enum end-dt2u {
        value 23;
        description "End.DT2U";
      }
      enum end-dt2m {
        value 24;
        description "End.DT2M";
      }
      enum end-s {
        value 25;
        description "End.S";
      }
      enum end-b6-insert-red {
        value 26;
        description "End.B6.Insert.Reduced";
      }
      enum end-b6-encaps-red {
        value 27;
        description "End.B6.Encaps.Reduced";
      }
      enum end-with-usd {
        value 28;
        description "End with USD";
      }
      enum end-with-psp-usd {
        value 29;
        description "End with PSP/USD";
      }
      enum end-with-usp-usd {
        value 30;
        description "End with USP/USD";
      }
      enum end-with-psp-usp-usd {
        value 31;
        description "End with PSP/USP/USD";
      }
      enum end-x-with-usd {
        value 32;
        description "End.X with USD";
      }
      enum end-x-with-psp-usd {
        value 33;
        description "End.X with PSP/USD";
      }
      enum end-x-with-usp-usd {
        value 34;
        description "End.X with USP/USD";
      }
      enum end-x-with-psp-usp-usd {
        value 35;
        description "End.X with PSP/USP/USD";
      }
      enum end-tbl-with-usd {
        value 36;
        description "End.T with USD";
      }
      enum end-tbl-with-psp-usd {
        value 37;
        description "End.T with PSP/USD";
      }
      enum end-tbl-with-usp-usd {
        value 38;
        description "End.T with USP/USD";
      }
      enum end-tbl-with-psp-usp-usd {
        value 39;
        description "End.T with PSP/USP/USD";
      }
      enum end-op {
        value 40;
        description "End.OP";
      }
      enum end-otp {
        value 41;
        description "End.OTP";
      }
      enum un-shift-only {
        value 42;
        description "uN Shift-only";
      }
      enum un {
        value 43;
        description "uN";
      }
      enum un-psp {
        value 44;
        description "uN with PSP";
      }
      enum un-usp {
        value 45;
        description "uN with USP";
      }
      enum un-psp-usp {
        value 46;
        description "uN with PSP-USP";
      }
      enum un-usd {
        value 47;
        description "uN with USD";
      }
      enum un-psp-usd {
        value 48;
        description "uN with PSP-USD";
      }
      enum un-usp-usd {
        value 49;
        description "uN with USP-USD";
      }
      enum un-psp-usp-usd {
        value 50;
        description "uN with PSP_USP-USD";
      }
      enum ua-shift-only {
        value 51;
        description "uA Shift-only";
      }
      enum ua {
        value 52;
        description "uA";
      }
      enum ua-psp {
        value 53;
        description "uA with PSP";
      }
      enum ua-usp {
        value 54;
        description "uA with USP";
      }
      enum ua-psp-usp {
        value 55;
        description "uA with PSP-USP";
      }
      enum ua-usd {
        value 56;
        description "uA with USD";
      }
      enum ua-psp-usd {
        value 57;
        description "uA with PSP-USD";
      }
      enum ua-usp-usd {
        value 58;
        description "uA with USP-USD";
      }
      enum ua-psp-usp-usd {
        value 59;
        description "uA with PSP_USP-USD";
      }
      enum udx6 {
        value 60;
        description "uDX6";
      }
      enum udx4 {
        value 61;
        description "uDX4";
      }
      enum udt6 {
        value 62;
        description "uDT6";
      }
      enum udt4 {
        value 63;
        description "uDT4";
      }
      enum udt46 {
        value 64;
        description "uDT46";
      }
      enum udx2 {
        value 65;
        description "uDX2";
      }
      enum udx2v {
        value 66;
        description "uDX2V";
      }
      enum udt2u {
        value 67;
        description "uDT2U";
      }
      enum udt2m {
        value 68;
        description "uDT2M";
      }
      enum ub6-insert {
        value 69;
        description "uB6 Insert";
      }
      enum ub6-encaps {
        value 70;
        description "uB6 Encaps";
      }
      enum ub6-insert-red {
        value 71;
        description "uB6 Insert.Red";
      }
      enum ub6-encaps-red {
        value 72;
        description "uB6 Encaps.Red";
      }
      enum ubm {
        value 73;
        description "uBM";
      }
      enum ub6-psp-usd-insert-red {
        value 79;
        description "uB6 with PSP-USD Insert.Red";
      }
      enum ub6-psp-usd-encaps-red {
        value 80;
        description "uB6 with PSP-USD Encaps.Red";
      }
      enum utef {
        value 81;
        description "PT uTEF";
      }
    }
    description "SRv6 Endpoint Behavior Type";
  }
  typedef Rib-in6-addr {
    type inet:ipv6-address;
    description "Rib in6 addr";
  }
  typedef Rib-in4-addr {
    type inet:ipv4-address;
    description "Rib in4 addr";
  }
  typedef Rib-edm-afi-id {
    type enumeration {
      enum none {
        value 0;
        description "No address family";
      }
      enum ipv4 {
        value 1;
        description "IPv4 AFI";
      }
      enum ipv6 {
        value 2;
        description "IPv6 AFI";
      }
    }
    description "Rib edm afi id";
  }

  grouping IPV4-RIB-EDM-CLIENT-REDIST-TABLE {
    description
      "Information on a client's redistribution of a
      table";
    leaf full-table {
      type boolean;
      description "Full table redistrbution or not?";
    }
    leaf insync {
      type uint32;
      description "Is this is sync or not?";
    }
    leaf afi {
      type Rib-edm-afi-id;
      description "Address Family";
    }
    leaf safi {
      type Rib-edm-safi-id;
      description "sub Address Family";
    }
    leaf vrf-name {
      type string;
      description "VRF Name of the table";
    }
    leaf updatemode {
      type uint32;
      description "Update type in route registration";
    }
  }

  grouping IPV4-RIB-EDM-CLIENT-REDIST-PROTO {
    description "Information on a client's  redist of a proto";
    leaf insync {
      type boolean;
      description "Is this in sync or not?";
    }
    leaf protocol-names {
      type string;
      description "Name of proto it is redistributing";
    }
    leaf proto-instance {
      type string;
      description "Instance of redistributed proto";
    }
    leaf updatemode {
      type uint32;
      description "Type of route information getting redistributed";
    }
  }

  grouping IPV4-RIB-EDM-CLIENT-HISTORY-ROUTE {
    description "Route information for history purposes";

    list ipv4-rib-edm-client-history-route {
      description "Next route";

      container prefix {
        description "Route prefix";
        uses RIB-EDM-IP-PFX;
      }

      container advertisement {
        description "list of advertising protos";
        uses IPV4-RIB-EDM-ADVERT;
      }
      leaf priority {
        type uint8;
        description "Priority of update";
      }
      leaf flags {
        type uint32;
        description "Route flags";
      }
      leaf source {
        type uint32;
        description "source";
      }
      leaf table-id {
        type uint32;
        description "table identifier";
      }
      leaf distance {
        type uint32;
        description "Administrative distance";
      }
      leaf metric {
        type uint32;
        description "Route metric";
      }
      leaf local-label {
        type uint32;
        description "Route local label";
      }
      leaf path-num {
        type uint16;
        description "Number of paths";
      }
      leaf nnh-num {
        type uint16;
        description "Number of NNHs";
      }
      leaf route-age {
        type uint32;
        units "second";
        description "Age of event (seconds)";
      }
      leaf route-modify-time {
        type uint64;
        units "nanosecond";
        description "Time of event (nanoseconds)";
      }
      leaf private-flags {
        type uint16;
        description "Route head private flags";
      }
      leaf number-of-srv6-sids {
        type uint16;
        description "Number of SRv6 Segment Identifiers";
      }
      leaf converge {
        type uint8;
        description "Redist table converged";
      }
      leaf code {
        type int8;
        description "Protocol code";
      }
      leaf outsync {
        type uint32;
        description "Last packed outsync prio";
      }
      leaf transaction-id {
        type uint64;
        description "Transaction ID packed";
      }
    }
  }

  grouping IPV4-RIB-EDM-CLIENT-REDIST {
    description "General info. on a client's redistribution";

    container routes {
      description "Link to history routes";
      uses IPV4-RIB-EDM-CLIENT-HISTORY-ROUTE;
    }
    leaf num-tables-outsync {
      type uint32;
      description "Num tables to get updates from";
    }
    leaf num-history-routes {
      type uint32;
      description "Number of history routes";
    }
  }

  grouping IPV4-RIB-EDM-CLIENT {
    description "Rib client information";
    leaf pname {
      type string;
      description "Client's name";
    }
    leaf nodename {
      type string;
      description "Node client process is running on";
    }
    leaf pid {
      type uint32;
      description "Client's process ID";
    }
    leaf redist {
      type boolean;
      description "Is client registered for redist";
    }
    leaf proto {
      type boolean;
      description "Is client registered as a protocol";
    }
    leaf client-id {
      type uint32;
      description "Client's RIB ID number";
    }
    leaf redist-opaques {
      type boolean;
      description "Is client registered for redist of opaques";
    }
  }

  grouping IPV4-RIB-EDM-STATS-REDIST-NH {
    description "Nexthop redistribution statistics";
    leaf table-id-xr {
      type uint32;
      description "table id xr";
    }
    leaf vrf-name {
      type string;
      description "vrf name";
    }
    leaf total-redist {
      type uint32;
      description "total redist";
    }
    leaf total-converge {
      type uint32;
      description "total converge";
    }
    leaf total-suppress {
      type uint32;
      description "total suppress";
    }
    leaf last-redist {
      type uint64;
      description "last redist";
    }
    leaf total-converge-sent {
      type uint32;
      description "total converge sent";
    }
    leaf last-converge {
      type uint64;
      description "last converge";
    }
    leaf last-converge-sent {
      type uint64;
      description "last converge sent";
    }
  }

  grouping IPV4-RIB-EDM-CLIENT-HISTORY-OPAQUE {
    description "Opaque information for history purposes";

    list ipv4-rib-edm-client-history-opaque {
      description "Next opaque";
      leaf type {
        type Rib-opaque;
        description "Opaque Type";
      }
      leaf decoded-key {
        type string;
        description "Decoded opaque key string";
      }
      leaf is-deleted {
        type boolean;
        description "Opaque is deleted";
      }
      leaf opaque-modify-time {
        type string;
        description "Timestamp of event";
      }
      leaf table-id {
        type uint32;
        description "table identifier";
      }
      leaf data-size {
        type uint32;
        description "Size of opaque data";
      }
    }
  }

  grouping IPV4-RIB-EDM-CLIENT-REDIST-OPAQUE {
    description "Client redistribution information for opaques";

    container opaques {
      description "Link to history opaques";
      uses IPV4-RIB-EDM-CLIENT-HISTORY-OPAQUE;
    }
    leaf num-history-opaques {
      type uint32;
      description "Number of history opaques";
    }
  }

  grouping IPV4-RIB-EDM-CLIENT-PROTO-INFO {
    description "Information on client protocols";
    leaf num-protos-outsync {
      type uint32;
      description "Count of out-of-sync protocols";
    }
    leaf update-time {
      type uint32;
      units "second";
      description "Time of last update in seconds";
    }
  }

  grouping IPV4-RIB-EDM-CLIENT-PROTO-TABLE-INFO {
    description "Information on table-specific client protocols";
    leaf num-protos-outsync {
      type uint32;
      description "Count of out-of-sync protocols";
    }
    leaf update-time {
      type uint64;
      units "nanosecond";
      description "Time of last update (nanoseconds)";
    }
    leaf afi {
      type Rib-edm-afi-id;
      description "Address Family";
    }
    leaf safi {
      type Rib-edm-safi-id;
      description "sub Address Family";
    }
    leaf vrf-name {
      type string;
      description "VRF Name of the table";
    }
  }

  grouping IPV4-RIB-EDM-CLIENT-PROTO {
    description "Information on a client proto";
    leaf protocol-names {
      type string;
      description "Name of proto";
    }
    leaf proto-instance {
      type string;
      description "Instance of proto";
    }
    leaf distance {
      type uint32;
      description "Route distane for the protocol";
    }
    leaf maxmetric {
      type uint32;
      description "Route metric for the protocol";
    }
    leaf purgetime {
      type uint32;
      description "Route purgetime";
    }
    leaf update-complete {
      type boolean;
      description "Has the client finished updating";
    }
  }

  grouping RIB-EDM-STATS-OPAQUE {
    description "Opaqaue statistics";
    leaf total-registration {
      type uint32;
      description "total registration";
    }
    leaf total-add {
      type uint32;
      description "total add";
    }
    leaf success {
      type uint32;
      description "success";
    }
    leaf last-result {
      type boolean;
      description "last result";
    }
    leaf last-registration {
      type uint64;
      description "last registration";
    }
  }

  grouping IPV4-RIB-EDM-STATS-NEXTHOP {
    description "Nexthop notification statistics";
    leaf table-id-xr {
      type uint32;
      description "table id xr";
    }
    leaf vrf-name {
      type string;
      description "vrf name";
    }
    leaf total-next-hop-reg {
      type uint32;
      description "total next hop reg";
    }
    leaf total-next-hop-unreg {
      type uint32;
      description "total next hop unreg";
    }
    leaf total-sync-reg {
      type uint32;
      description "total sync reg";
    }
    leaf last-registration {
      type uint64;
      description "last registration";
    }
  }

  grouping RIB-EDM-STATS-PURGE {
    description "Purge statistics";
    leaf total-purges {
      type uint32;
      description "total purges";
    }
    leaf total-prefix-deleted {
      type uint32;
      description "total prefix deleted";
    }
    leaf total-paths-deleted {
      type uint32;
      description "total paths deleted";
    }
    leaf last-purge {
      type uint64;
      description "last purge";
    }
  }

  grouping RIB-EDM-STATS-COMPLETE-UPDATE {
    description "Batch complete update statistic";
    leaf total-complete {
      type uint32;
      description "total complete";
    }
    leaf insync {
      type uint32;
      description "insync";
    }
    leaf last-insync {
      type uint64;
      description "last insync";
    }
    leaf bad-args {
      type uint32;
      description "bad args";
    }
    leaf success {
      type uint32;
      description "success";
    }
    leaf last-complete-msg {
      type uint64;
      description "last complete msg";
    }
  }

  grouping RIB-EDM-STATS-BATCH-CONVERGE {
    description "Batch converge operation statistics";
    leaf total-converge {
      type uint32;
      description "total converge";
    }
    leaf insync {
      type uint32;
      description "insync";
    }
    leaf last-insync {
      type uint64;
      description "last insync";
    }
    leaf bad-args {
      type uint32;
      description "bad args";
    }
    leaf success {
      type uint32;
      description "success";
    }
    leaf last-converge-msg {
      type uint64;
      description "last converge msg";
    }
  }

  grouping RIB-EDM-STATS-BATCH-COMPLETE {
    description "Batch complete operation statistic";
    leaf total-complete {
      type uint32;
      description "total complete";
    }
    leaf insync {
      type uint32;
      description "insync";
    }
    leaf last-insync {
      type uint64;
      description "last insync";
    }
    leaf last-complete-msg {
      type uint64;
      description "last complete msg";
    }
  }

  grouping RIB-EDM-STATS-ADVERTISEMENT {
    description "Advertisement statistic";
    leaf total-adv {
      type uint32;
      description "total adv";
    }
    leaf new-adv {
      type uint32;
      description "new adv";
    }
    leaf modification {
      type uint32;
      description "modification";
    }
    leaf delete {
      type uint32;
      description "delete";
    }
    leaf success {
      type uint32;
      description "success";
    }
    leaf last-result {
      type boolean;
      description "last result";
    }
    leaf last-adv-time {
      type uint64;
      description "last adv time";
    }
  }

  grouping RIB-EDM-STATS-ROUTE-OP {
    description "Route operation statistics";
    leaf paths-add-op {
      type uint32;
      description "paths add op";
    }
    leaf prefix-added {
      type uint32;
      description "prefix added";
    }
    leaf paths-added {
      type uint32;
      description "paths added";
    }
    leaf prefix-modified-add {
      type uint32;
      description "prefix modified add";
    }
    leaf paths-delete-op {
      type uint32;
      description "paths delete op";
    }
    leaf prefix-deleted {
      type uint32;
      description "prefix deleted";
    }
    leaf paths-deleted {
      type uint32;
      description "paths deleted";
    }
    leaf prefix-modified-del {
      type uint32;
      description "prefix modified del";
    }
    leaf prefix-flushed {
      type uint32;
      description "prefix flushed";
    }
    leaf paths-flushed {
      type uint32;
      description "paths flushed";
    }
    leaf invalid-op {
      type uint32;
      description "invalid op";
    }
    leaf flushed {
      type uint32;
      description "flushed";
    }
    leaf too-manypaths {
      type uint32;
      description "too manypaths";
    }
    leaf invalid-parameter {
      type uint32;
      description "invalid parameter";
    }
    leaf no-ecmp-support {
      type uint32;
      description "no ecmp support";
    }
    leaf mem-alloc-error {
      type uint32;
      description "mem alloc error";
    }
    leaf path-backup {
      type uint32;
      description "path backup";
    }
    leaf path-active {
      type uint32;
      description "path active";
    }
    leaf path-change {
      type uint32;
      description "path change";
    }
    leaf path-nochange {
      type uint32;
      description "path nochange";
    }
    leaf table-limit {
      type uint32;
      description "table limit";
    }
    leaf outsync {
      type uint32;
      description "outsync";
    }
    leaf last-outsync {
      type uint64;
      description "last outsync";
    }
    leaf last-route-opt {
      type uint16;
      description "last route opt";
    }
    leaf last-result {
      type uint32;
      description "last result";
    }
    leaf last-opt-time {
      type uint64;
      description "last opt time";
    }
    leaf attribute-not-found {
      type uint32;
      description "attribute not found";
    }
    leaf last-attribute-not-found-time {
      type uint64;
      description "last attribute not found time";
    }
    leaf num-fb-cookies {
      type uint32;
      description "num fb cookies";
    }
    leaf last-fb-cookie-op {
      type uint64;
      description "last fb cookie op";
    }
    leaf invalid-path-combination {
      type uint32;
      description "invalid path combination";
    }
    leaf invalid-pathid-change {
      type uint32;
      description "invalid pathid change";
    }
    leaf path-attribute-too-large {
      type uint32;
      description "path attribute too large";
    }
    leaf explicit-del-created {
      type uint32;
      description "explicit del created";
    }
    leaf explicit-del-ignored {
      type uint32;
      description "explicit del ignored";
    }
  }

  grouping IPV4-RIB-EDM-CLIENT-PROTO-STATS-SUMMARY {
    description "Summary of RIB client protocol statistic summary";

    container route-op-stats {
      description "route op stats";
      uses RIB-EDM-STATS-ROUTE-OP;
    }

    container adv {
      description "adv";
      uses RIB-EDM-STATS-ADVERTISEMENT;
    }

    container complete-stats {
      description "complete stats";
      uses RIB-EDM-STATS-BATCH-COMPLETE;
    }

    container converge-stats {
      description "converge stats";
      uses RIB-EDM-STATS-BATCH-CONVERGE;
    }

    container complete-update-stats {
      description "complete update stats";
      uses RIB-EDM-STATS-COMPLETE-UPDATE;
    }

    container purge-stats {
      description "purge stats";
      uses RIB-EDM-STATS-PURGE;
    }

    container nh-stats {
      description "nh stats";
      uses IPV4-RIB-EDM-STATS-NEXTHOP;
    }
    leaf protocol-name {
      type string;
      description " Name of Protocol";
    }
    leaf instance {
      type string;
      description "Instance name";
    }

    list opaque-stat {
      max-elements "22";
      description "opaque stat";
      uses RIB-EDM-STATS-OPAQUE;
    }
  }

  grouping RIB-EDM-STATS-CLIENT-UG-START {
    description "BCDL update group notify timer statistics";
    leaf bcdl-ug-notify-num-not-started {
      type uint32;
      description "bcdl ug notify num not started";
    }
    leaf bcdl-ug-last-notify-not-started-time {
      type uint64;
      description "bcdl ug last notify not started time";
    }
  }

  grouping RIB-EDM-STATS-CLIENT-FIB-UG-UPD {
    description "FIB update group updates statistics";
    leaf fib-ug-updates {
      type uint32;
      description "fib ug updates";
    }
    leaf fib-ug-total-nodes {
      type uint32;
      description "fib ug total nodes";
    }
  }

  grouping RIB-EDM-STATS-CLIENT-LOOKUPS {
    description "Lookup statistics";
    leaf best-local-address {
      type uint32;
      description "best local address";
    }
    leaf is-connected {
      type uint32;
      description "is connected";
    }
    leaf route-lookups {
      type uint32;
      description "route lookups";
    }
    leaf next-hop-lookups {
      type uint32;
      description "next hop lookups";
    }
    leaf default-source {
      type uint32;
      description "default source";
    }
  }

  grouping RIB-EDM-STATS-CLIENT-ATTRIBUTE {
    description "Attribute operation statistics";
    leaf total-registration {
      type uint32;
      description "total registration";
    }
    leaf total-add {
      type uint32;
      description "total add";
    }
    leaf success {
      type uint32;
      description "success";
    }
    leaf last-result {
      type boolean;
      description "last result";
    }
    leaf last-registration {
      type uint64;
      description "last registration";
    }
  }

  grouping RIB-EDM-STATS-CLIENT-REDIST-TBL {
    description "Table redistribution statistics";
    leaf total-table-redist {
      type uint32;
      description "total table redist";
    }
    leaf table-created {
      type uint32;
      description "table created";
    }
    leaf table-full {
      type uint32;
      description "table full";
    }
    leaf has-space {
      type uint32;
      description "has space";
    }
    leaf last-redist {
      type uint8;
      description "last redist";
    }
    leaf last-redist-time {
      type uint64;
      description "last redist time";
    }
  }

  grouping RIB-EDM-STATS-CLIENT-TBL {
    description "Table operation statistics";
    leaf total-table-register {
      type uint32;
      description "total table register";
    }
    leaf new-table {
      type uint32;
      description "new table";
    }
    leaf modification {
      type uint32;
      description "modification";
    }
    leaf deletion {
      type uint32;
      description "deletion";
    }
    leaf cl-lookup-err {
      type uint32;
      description "cl lookup err";
    }
    leaf tbl-lookup-err {
      type uint32;
      description "tbl lookup err";
    }
    leaf invalid-id-lookup-err {
      type uint32;
      description "invalid id lookup err";
    }
    leaf tbl-create-err {
      type uint32;
      description "tbl create err";
    }
    leaf success {
      type uint32;
      description "success";
    }
    leaf last-result {
      type boolean;
      description "last result";
    }
    leaf last-registration {
      type uint64;
      description "last registration";
    }
  }

  grouping RIB-EDM-STATS-CLIENT-REDIST {
    description "Client redistribution stats";
    leaf total-redist {
      type uint32;
      description "total redist";
    }
    leaf last-redist {
      type uint64;
      description "last redist";
    }
  }

  grouping EVT-HIST-ENTRY {
    description "Event history Entry";
    leaf evt-timestamp {
      type string;
      description "The timestamp of the event";
    }
    leaf evt-name {
      type string;
      description "Event name";
    }
    leaf evt-type {
      type uint8;
      description "Event type";
    }
    leaf evt-many {
      type boolean;
      description "Multiple instance flag";
    }
    leaf evt-sticky {
      type boolean;
      description "Sticky flag";
    }
    list evt-data {
      description "Optional data";
        leaf entry {
                  type uint32;

                  description "Optional data";
        }
    }
  }

  grouping EVT-HIST-INFO {
    description "Per object event history";
    leaf evt-class-name {
      type string;
      description "Class name string";
    }

    list evt-entry {
      description "Array of event entries";
      uses EVT-HIST-ENTRY;
    }
  }

  grouping RIB-EDM-STATS-CLIENT-NOTF {
    description "RIB pulse statistics";

    container evt-hist {
      description "evt hist";
      uses EVT-HIST-INFO;
    }
    leaf total-notifications {
      type uint32;
      description "total notifications";
    }
    leaf clear {
      type uint32;
      description "clear";
    }
    leaf nexthop-critical {
      type uint32;
      description "nexthop critical";
    }
    leaf nexthop-noncritical {
      type uint32;
      description "nexthop noncritical";
    }
    leaf nexthop-converge {
      type uint32;
      description "nexthop converge";
    }
    leaf redist-register {
      type uint32;
      description "redist register";
    }
    leaf redist-reset {
      type uint32;
      description "redist reset";
    }
    leaf preceeding-client {
      type uint32;
      description "preceeding client";
    }
    leaf redist-list {
      type uint32;
      description "redist list";
    }
    leaf gc-proto {
      type uint32;
      description "gc proto";
    }
    leaf gc-db {
      type uint32;
      description "gc db";
    }
    leaf gc-attribute {
      type uint32;
      description "gc attribute";
    }
    leaf table-event {
      type uint32;
      description "table event";
    }
    leaf feedback-cookie {
      type uint32;
      description "feedback cookie";
    }
    leaf fib-ug-update {
      type uint32;
      description "fib ug update";
    }
    leaf critical {
      type uint32;
      description "critical";
    }
    leaf non-critical {
      type uint32;
      description "non critical";
    }
    leaf delay-timer {
      type uint32;
      description "delay timer";
    }
    leaf skip-notification {
      type uint32;
      description "skip notification";
    }
    leaf end-of-data {
      type uint32;
      description "end of data";
    }
    leaf disconnect {
      type uint32;
      description "disconnect";
    }
    leaf srv6-redist-register {
      type uint32;
      description "srv6 redist register";
    }
    leaf srv6-cfg-updt {
      type uint32;
      description "srv6 cfg updt";
    }
    leaf srv6-opcode-updt {
      type uint32;
      description "srv6 opcode updt";
    }
    leaf state-sync-done {
      type uint32;
      description "state sync done";
    }
    leaf last-notification {
      type uint64;
      description "last notification";
    }
    leaf last-eod {
      type uint64;
      description "last eod";
    }
    leaf total-pulse {
      type uint64;
      description "total pulse";
    }
    leaf total-select {
      type uint64;
      description "total select";
    }
    leaf total-read {
      type uint64;
      description "total read";
    }
  }

  grouping IPV4-RIB-EDM-CLIENT-STATS-SUMMARY {
    description "Summary of RIB client statistics";

    container notification {
      description "notification";
      uses RIB-EDM-STATS-CLIENT-NOTF;
    }

    container redist {
      description "redist";
      uses RIB-EDM-STATS-CLIENT-REDIST;
    }

    container tbl-stats {
      description "tbl stats";
      uses RIB-EDM-STATS-CLIENT-TBL;
    }

    container redist-tbl {
      description "redist tbl";
      uses RIB-EDM-STATS-CLIENT-REDIST-TBL;
    }

    container attribute {
      description "attribute";
      uses RIB-EDM-STATS-CLIENT-ATTRIBUTE;
    }

    container lookups {
      description "lookups";
      uses RIB-EDM-STATS-CLIENT-LOOKUPS;
    }

    container fib-ug {
      description "fib ug";
      uses RIB-EDM-STATS-CLIENT-FIB-UG-UPD;
    }

    container ug-start-stats {
      description "ug start stats";
      uses RIB-EDM-STATS-CLIENT-UG-START;
    }
    leaf client-id {
      type uint32;
      description "client id";
    }
  }

  grouping RIB-EDM-STATS-REDIST-SRV6 {
    description "SRv6 redistribution statistics";
    leaf total-redist {
      type uint32;
      description "total redist";
    }
    leaf last-redist {
      type uint64;
      description "last redist";
    }
  }

  grouping RIB-EDM-STATS-REDIST-OPAQUE {
    description "Opaque redistribution statistics";
    leaf total-redist {
      type uint32;
      description "total redist";
    }
    leaf total-tbl-entries {
      type uint32;
      description "total tbl entries";
    }
    leaf last-redist {
      type uint64;
      description "last redist";
    }
  }

  grouping RIB-EDM-STATS-REDIST-ATTR {
    description "Attribe redistribution statistics";
    leaf total-redist {
      type uint32;
      description "total redist";
    }
    leaf total-tbl-entries {
      type uint32;
      description "total tbl entries";
    }
    leaf last-redist {
      type uint64;
      description "last redist";
    }
  }

  grouping RIB-EDM-STATS-REDIST-ROUTE {
    description "Route redistribution statistics";
    leaf total-redist {
      type uint32;
      description "total redist";
    }
    leaf update-sent {
      type uint32;
      description "update sent";
    }
    leaf paths-sent {
      type uint32;
      description "paths sent";
    }
    leaf prefixes-deleted {
      type uint32;
      description "prefixes deleted";
    }
    leaf total-advertisment {
      type uint32;
      description "total advertisment";
    }
    leaf last-redist-delete {
      type boolean;
      description "last redist delete";
    }
    leaf last-redist {
      type uint64;
      description "last redist";
    }
  }

  grouping IPV4-RIB-EDM-STATS-REDIST {
    description "Redistribution statistics";

    container route {
      description "route";
      uses RIB-EDM-STATS-REDIST-ROUTE;
    }

    container attr {
      description "attr";
      uses RIB-EDM-STATS-REDIST-ATTR;
    }

    container srv6 {
      description "srv6";
      uses RIB-EDM-STATS-REDIST-SRV6;
    }
    leaf protocol-name {
      type string;
      description " Name of Protocol";
    }
    leaf instance {
      type string;
      description "Instance name";
    }

    list opaque-stat {
      max-elements "22";
      description "opaque stat";
      uses RIB-EDM-STATS-REDIST-OPAQUE;
    }
  }

  grouping IPV4-RIB-EDM-RECURSION-DEPTH-MAX {
    description
      "Information about the maximum recursion depth in
      the RIB";
    leaf current {
      type uint32;
      description "Current maximum recursion depth";
    }
    leaf configured {
      type uint32;
      description "Configured maximum recursion depth";
    }
  }

  grouping RIB-EDM-STATS-GRID-SUMMARY {
    description "RIB EDM STATS GRID SUMMARY";
    leaf num-in-queue {
      type uint32;
      description "num in queue";
    }
    leaf num-enqueue {
      type uint32;
      description "num enqueue";
    }
    leaf num-dequeue {
      type uint32;
      description "num dequeue";
    }
    leaf num-enqueue-del-skipped {
      type uint32;
      description "num enqueue del skipped";
    }
    leaf num-requeue {
      type uint32;
      description "num requeue";
    }
    leaf num-enqueue-del-with-ref {
      type uint32;
      description "num enqueue del with ref";
    }
  }

  grouping RIB-EDM-STATS-NH-BATCH-SUMMARY {
    description "RIB batch nexthop statistics informatio";
    leaf total-nh-batch-requests {
      type uint32;
      description "total nh batch requests";
    }
    leaf total-nh-operations {
      type uint32;
      description "total nh operations";
    }
    leaf batch-init {
      type uint32;
      description "batch init";
    }
    leaf batch-register {
      type uint32;
      description "batch register";
    }
    leaf batch-unregister {
      type uint32;
      description "batch unregister";
    }
    leaf register-complete {
      type uint32;
      description "register complete";
    }
    leaf sync-register {
      type uint32;
      description "sync register";
    }
    leaf batch-finish {
      type uint32;
      description "batch finish";
    }
    leaf batch-null {
      type uint32;
      description "batch null";
    }
    leaf success {
      type uint32;
      description "success";
    }
    leaf last-client {
      type uint32;
      description "last client";
    }
    leaf last-nh-operation {
      type uint32;
      description "last nh operation";
    }
    leaf last-result {
      type boolean;
      description "last result";
    }
    leaf last-nh-time {
      type uint64;
      description "last nh time";
    }
  }

  grouping RIB-EDM-STATS-LWM-SUMMARY {
    description "RIB EDM STATS LWM SUMMARY";
    leaf total-lwm {
      type uint32;
      description "total lwm";
    }
    leaf route-add {
      type uint32;
      description "route add";
    }
    leaf route-delete {
      type uint32;
      description "route delete";
    }
    leaf purge-protocol {
      type uint32;
      description "purge protocol";
    }
    leaf purge-client {
      type uint32;
      description "purge client";
    }
    leaf protocol-register {
      type uint32;
      description "protocol register";
    }
    leaf protocol-unregister {
      type uint32;
      description "protocol unregister";
    }
    leaf protocol-modify {
      type uint32;
      description "protocol modify";
    }
    leaf redist-proto {
      type uint32;
      description "redist proto";
    }
    leaf unreg-redist-proto {
      type uint32;
      description "unreg redist proto";
    }
    leaf redist-reset {
      type uint32;
      description "redist reset";
    }
    leaf update-complete {
      type uint32;
      description "update complete";
    }
    leaf advertisement {
      type uint32;
      description "advertisement";
    }
    leaf unreg-advertisement {
      type uint32;
      description "unreg advertisement";
    }
    leaf next-hop-register {
      type uint32;
      description "next hop register";
    }
    leaf next-hop-unregister {
      type uint32;
      description "next hop unregister";
    }
    leaf bind-data {
      type uint32;
      description "bind data";
    }
    leaf succcess {
      type uint32;
      description "succcess";
    }
    leaf route-lookup {
      type uint32;
      description "route lookup";
    }
    leaf best-local-addr {
      type uint32;
      description "best local addr";
    }
    leaf is-connected {
      type uint32;
      description "is connected";
    }
    leaf first-hop {
      type uint32;
      description "first hop";
    }
    leaf find-proto {
      type uint32;
      description "find proto";
    }
    leaf free-all-srv6-sid {
      type uint32;
      description "free all srv6 sid";
    }
    leaf other {
      type uint32;
      description "other";
    }
    leaf last-client {
      type uint32;
      description "last client";
    }
    leaf last-operation {
      type uint32;
      description "last operation";
    }
    leaf last-oper-result {
      type boolean;
      description "last oper result";
    }
    leaf last-lwm-time {
      type uint64;
      description "last lwm time";
    }
    leaf clear-aft {
      type uint32;
      description "clear aft";
    }
  }

  grouping RIB-EDM-STATS-BATCH-SUMMARY {
    description "RIB Batch statistic information";
    leaf total-msg-rx {
      type uint32;
      description "total msg rx";
    }
    leaf route-op-arg-rx {
      type uint32;
      description "route op arg rx";
    }
    leaf attribute-arg-rx {
      type uint32;
      description "attribute arg rx";
    }
    leaf complete-arg-rx {
      type uint32;
      description "complete arg rx";
    }
    leaf converge-arg-rx {
      type uint32;
      description "converge arg rx";
    }
    leaf opaque-arg-rx {
      type uint32;
      description "opaque arg rx";
    }
    leaf total-fwd-ref {
      type uint32;
      description "total fwd ref";
    }
    leaf invalid-client-id-error {
      type uint32;
      description "invalid client id error";
    }
    leaf mem-alloc-error {
      type uint32;
      description "mem alloc error";
    }
    leaf client-lookup-error {
      type uint32;
      description "client lookup error";
    }
    leaf db-lookup-error {
      type uint32;
      description "db lookup error";
    }
    leaf proto-lookup-error {
      type uint32;
      description "proto lookup error";
    }
    leaf client-proto-lookup-error {
      type uint32;
      description "client proto lookup error";
    }
    leaf table-missing-error {
      type uint32;
      description "table missing error";
    }
    leaf unknown-arg {
      type uint32;
      description "unknown arg";
    }
    leaf success {
      type uint32;
      description "success";
    }
    leaf last-result {
      type uint32;
      description "last result";
    }
    leaf last-operation {
      type uint32;
      description "last operation";
    }
    leaf last-client {
      type uint32;
      description "last client";
    }
    leaf last-msg-rx-time {
      type uint64;
      description "last msg rx time";
    }
  }

  grouping IPV4-RIB-EDM-STATS-SUMMARY {
    description "Summary of RIB statistic information";

    container batch-stats {
      description "batch stats";
      uses RIB-EDM-STATS-BATCH-SUMMARY;
    }

    container lwm-stats {
      description "lwm stats";
      uses RIB-EDM-STATS-LWM-SUMMARY;
    }

    container nh-batch-stats {
      description "nh batch stats";
      uses RIB-EDM-STATS-NH-BATCH-SUMMARY;
    }

    container grid-stats {
      description "grid stats";
      uses RIB-EDM-STATS-GRID-SUMMARY;
    }
  }

  grouping IPV4-RIB-EDM-NHID-OBJ {
    description "Information of nhid objects";

    container nh-addr {
      description "nh addr";
      uses RIB-EDM-IP-ADDR;
    }
    leaf nhid {
      type uint32;
      description "nhid";
    }
    leaf feid {
      type uint64;
      description "feid";
    }
    leaf ifindex {
      type xr:Interface-name;
      description "ifindex";
    }
    leaf chkpt-obj-id {
      type uint32;
      description "chkpt obj id";
    }
    leaf ref-count {
      type uint32;
      description "ref count";
    }
    leaf feature-type {
      type uint8;
      description "feature type";
    }
    leaf priority {
      type uint8;
      description "priority";
    }
    leaf inserted {
      type boolean;
      description "inserted";
    }

    list srv6-carrier {
      description "List of SRv6 Carriers with one or more SIDs";
      uses MGMT-SRV6-SID;
    }
  }

  grouping RIB-EDM-RPF-NBR-OBJ {
    description "Information of the rpf nbr data";

    container ip-address {
      description "ip address";
      uses RIB-EDM-IP-ADDR;
    }
    leaf afi {
      type Rib-edm-afi-id;
      description "afi";
    }
  }

  grouping IPV4-RIB-EDM-RPFLIST-OBJ {
    description "Informaton of rpf list objects";
    leaf label {
      type uint32;
      description "label";
    }
    leaf flags {
      type uint32;
      description "flags";
    }
    leaf ref-count {
      type uint32;
      description "ref count";
    }
    leaf sent-to-fib {
      type boolean;
      description "sent to fib";
    }

    list nbr {
      description "nbr";
      uses RIB-EDM-RPF-NBR-OBJ;
    }
  }

  grouping IPV4-RIB-EDM-NH-STATS {
    description "Nexthop statistics for a table";
    leaf num-resolved-nh {
      type uint32;
      description "Number of resolved nexthop";
    }
    leaf num-unresolved-nh {
      type uint32;
      description "Number of unresolved nexthop";
    }
  }

  grouping RIB-PATH-SHARED-DB-STATS {
    description "Per table path sharing stats";
    leaf num-mutable-paths {
      type uint32;
      description "Number of mutable paths";
    }
    leaf num-total-mutable-alloc {
      type uint32;
      description "Running count of mutable path allocation calls";
    }
    leaf num-total-mutable-cleanup {
      type uint32;
      description "Running count of mutable path frees";
    }
    leaf num-path-clone-ops {
      type uint32;
      description "Count of path clone operations";
    }
    leaf num-path-save-ops {
      type uint32;
      description "Count of path save operations";
    }
    leaf num-shr-refcnt-incr {
      type uint32;
      description "Number of refcount increment operations";
    }
    leaf num-shr-refcnt-decr {
      type uint32;
      description "Number of refcount decrements operations";
    }
    leaf num-current-shared-paths {
      type uint32;
      description "Current number of shared paths";
    }
    leaf max-share-refcnt {
      type uint32;
      description
        "The highest sharing factor by any path,
        high-water";
    }
    leaf max-paths-in-db {
      type uint32;
      description "Largest number of paths in DB high-water";
    }
    leaf num-shared-path-search-miss {
      type uint32;
      description
        "Number of MISS operations searching for shared
        path";
    }
    leaf num-shared-path-search-hit {
      type uint32;
      description
        "Number of HIT operations searching for shared
        path";
    }
    leaf num-total-shared-path-create {
      type uint32;
      description "Number of path create operations";
    }
    leaf num-total-shared-path-delete {
      type uint32;
      description "Number of path delete operations";
    }
    leaf sum-of-all-refcounts {
      type uint32;
      description "Sum of all path refcounts in the shared db";
    }
    leaf avg-path-shares {
      type uint32;
      description "Average number of pathlists using a shared path";
    }
  }

  grouping RIB-PATHLIST-SHARED-DB-STATS {
    description " Per table pathlist sharing stats";
    leaf num-mutable-pathlists {
      type uint32;
      description "Number of mutable pathlists";
    }
    leaf num-immutable-pathlists {
      type uint32;
      description "Number of immutable pathlists";
    }
    leaf num-cumulative-pathlist-creates {
      type uint32;
      description "Cumulative number of pathlist-CREATES";
    }
    leaf num-pathlist-clone-ops {
      type uint32;
      description "Count of pathlist clone operations";
    }
    leaf num-pathlist-save-ops {
      type uint32;
      description "Count of pathlist save operations";
    }
    leaf max-share-refcnt {
      type uint32;
      description
        "The max sharing factor by any pathlist,
        high-water";
    }
    leaf max-pathlists-in-db {
      type uint32;
      description "Largest number of pathlists in DB, high-water";
    }
    leaf num-shared-pathlist-search-hit {
      type uint32;
      description
        "number of HIT operations searching for a shared
        pathlist";
    }
    leaf num-shared-pathlist-search-miss {
      type uint32;
      description
        "number of MISS operations searching for a shared
        pathlist";
    }
    leaf sum-of-all-refcounts {
      type uint32;
      description "Sum of all pathlist refcounts in the shared db";
    }
    leaf avg-pathlist-shares {
      type uint32;
      description
        "Average number of routes using a shared pathlist";
    }
  }

  grouping IPV4-RIB-EDM-TABLE {
    description "Information of a routing table";

    container pathlist-stats {
      description "Pathlist Statistics";
      uses RIB-PATHLIST-SHARED-DB-STATS;
    }

    container path-stats {
      description "Path Statistics";
      uses RIB-PATH-SHARED-DB-STATS;
    }
    leaf tableid {
      type uint32;
      description "Table id";
    }
    leaf afi {
      type Rib-edm-afi-id;
      description "Address Family";
    }
    leaf safi {
      type Rib-edm-safi-id;
      description "sub Address Family";
    }
    leaf vrf-name {
      type string;
      description "VRF Name of the table";
    }
    leaf table-name {
      type string;
      description "Name of the table";
    }
    leaf version {
      type uint64;
      description "Table version";
    }
    leaf conf-prefix-limit {
      type uint32;
      description "Configured prefix limit";
    }
    leaf current-prefix-count {
      type uint32;
      description "Num prefixes in table";
    }
    leaf num-svdlcl-prefix {
      type uint32;
      description "Num SVD local prefixes";
    }
    leaf num-svdrem-prefix {
      type uint32;
      description "Num SVD remote prefixes";
    }
    leaf table-version {
      type uint64;
      description "Version no. of the table";
    }
    leaf prefix-limit-notified {
      type boolean;
      description "Prefix limit state indicator";
    }
    leaf fwd-referenced {
      type boolean;
      description "Table in fwd reference state?";
    }
    leaf deleted {
      type boolean;
      description "Table deleted?";
    }
    leaf initial-converge {
      type boolean;
      description "Table has reached convergence";
    }
  }

  grouping RIB-EDM-ROUTE-COUNT {
    description "Specifics of route count";
    leaf active-routes-count {
      type uint32;
      description "Number of active routes";
    }
    leaf num-backup-routes {
      type uint32;
      description "Number of backup (inactive) routes";
    }
    leaf num-active-paths {
      type uint32;
      description "Number of paths to active routes";
    }
    leaf num-backup-paths {
      type uint32;
      description "Number of paths to backup routes";
    }
  }

  grouping RIB-EDM-PROTO-ROUTE-SUMM-DETAIL {
    description "Details of Protocol route types";

    container proto-route-count {
      description "Count for proto. instance";
      uses RIB-EDM-ROUTE-COUNT;
    }

    container rtype-none {
      description "No route type";
      uses RIB-EDM-ROUTE-COUNT;
    }

    container rtype-other {
      description "Unknown route type";
      uses RIB-EDM-ROUTE-COUNT;
    }

    container rtype-ospf-intra {
      description "OSPF route within an area";
      uses RIB-EDM-ROUTE-COUNT;
    }

    container rtype-ospf-inter {
      description "OSPF route across diff. areas";
      uses RIB-EDM-ROUTE-COUNT;
    }

    container rtype-ospf-extern1 {
      description "OSPF external route of type 1";
      uses RIB-EDM-ROUTE-COUNT;
    }

    container rtype-ospf-extern2 {
      description "OSPF external route of type 2";
      uses RIB-EDM-ROUTE-COUNT;
    }

    container rtype-isis-sum {
      description "IS-IS summary route";
      uses RIB-EDM-ROUTE-COUNT;
    }

    container rtype-isis-l1 {
      description "IS-IS level 1 route";
      uses RIB-EDM-ROUTE-COUNT;
    }

    container rtype-isis-l2 {
      description "IS-IS level 2 route";
      uses RIB-EDM-ROUTE-COUNT;
    }

    container rtype-isis-l1-ia {
      description "IS-IS level1 inter-area route";
      uses RIB-EDM-ROUTE-COUNT;
    }

    container rtype-bgp-int {
      description "iBGP route";
      uses RIB-EDM-ROUTE-COUNT;
    }

    container rtype-bgp-ext {
      description "eBGP route";
      uses RIB-EDM-ROUTE-COUNT;
    }

    container rtype-bgp-loc {
      description "BGP local route";
      uses RIB-EDM-ROUTE-COUNT;
    }

    container rtype-ospf-nssa1 {
      description "OSPF NSSA ext. route type 1";
      uses RIB-EDM-ROUTE-COUNT;
    }

    container rtype-ospf-nssa2 {
      description "OSPF NSSA ext. route type 2";
      uses RIB-EDM-ROUTE-COUNT;
    }

    container rtype-igrp2-int {
      description "EIGRP internal route";
      uses RIB-EDM-ROUTE-COUNT;
    }

    container rtype-igrp2-ext {
      description "EIGRP external route";
      uses RIB-EDM-ROUTE-COUNT;
    }
    leaf name {
      type string;
      description "Proto name";
    }
    leaf instance {
      type string;
      description "Instance name of the protocol";
    }
  }

  grouping IPV4-RIB-EDM-ADVERT {
    description "Route advertisement information";

    list ipv4-rib-edm-advert {
      description "Next advertising proto";
      leaf protocol-id {
        type uint32;
        description "Protocol advertising the route";
      }
      leaf client-id {
        type uint32;
        description "  Client advertising the route";
      }
      leaf number-of-extended-communities {
        type uint32;
        description
          "Number of extended communities attached by
          advertiser";
      }
      leaf extended-communities {
        type yang:hex-string;
        description
          "Extended communities attached by the advertiser";
      }
      leaf protocol-opaque-flags {
        type uint8;
        description "OSPF area-id flags";
      }
      leaf protocol-opaque {
        type uint32;
        description "OSPF area-id";
      }
      leaf code {
        type int8;
        description "Protocol code";
      }
      leaf instance-name {
        type string {
          length "0..41";
        }
        description
          "Instance name of the protocol advertising the
          route";
      }
    }
  }

  grouping RIB-EDM-NH-PATH {
    description "Information of a nexthop notification client";

    container address {
      description "address";
      uses RIB-EDM-IP-ADDR;
    }
    leaf interface {
      type uint32;
      description "interface";
    }
    leaf tableid {
      type uint32;
      description "tableid";
    }
    leaf vrf-name {
      type string;
      description "VRF Name of the nh table";
    }
  }

  grouping RIB-EDM-NH-CLIENT {
    description "Information of a nexthop notification client";

    list rib-edm-nh-client {
      description "Next client";
      leaf id {
        type uint32;
        description "Client id";
      }
      leaf ref-count {
        type uint32;
        description "The number NH reference this client";
      }
      leaf nh-create-age {
        type uint32;
        description "How long has client has been created";
      }
      leaf nh-create-time {
        type uint64;
        description "Client creation time";
      }
      leaf nh-read-age {
        type uint32;
        description "How long ago client read this notification";
      }
      leaf nh-read-time {
        type uint64;
        description "Client notification read time";
      }
      leaf pack-mvpn {
        type boolean;
        description "Pack MVPN";
      }
      leaf pack-path-rt {
        type boolean;
        description "Pack path RT";
      }
      leaf pack-vrf-import-rt {
        type boolean;
        description "Pack VRF import RT";
      }
      leaf pack-source-as-rt {
        type boolean;
        description "Pack source AS RT";
      }
      leaf pack-source-rd {
        type boolean;
        description "Pack source RD";
      }
      leaf pack-mldp-root {
        type boolean;
        description "Pack MLDP root";
      }
      leaf pack-seg-nh {
        type boolean;
        description "Pack seg NH";
      }
      leaf notify-reregister {
        type boolean;
        description "Notify Reregister";
      }
    }
  }

  grouping IPV4-RIB-EDM-NH-ADDR {
    description
      "Information of a registered nexthop notification
      address";

    container prefix {
      description "Route prefix and length";
      uses RIB-EDM-IP-PFX;
    }

    container dest-addr {
      description "Destination address";
      uses RIB-EDM-IP-ADDR;
    }

    container clients {
      description "Client(s) of the address";
      uses RIB-EDM-NH-CLIENT;
    }

    container resolved-route {
      description "Route resolved this nexthop";
      uses IPV4-RIB-EDM-ROUTE;
    }
    leaf dest-intf {
      type uint32;
      description "Destination interface";
    }
    leaf dest-tableid {
      type uint32;
      description "Destination tableid";
    }
    leaf dest-metric {
      type uint32;
      description "Destination metric";
    }
    leaf dest-vrf-name {
      type string;
      description "VRF Name of the nh table";
    }
    leaf damped {
      type boolean;
      description "Nexthop being damped?";
    }
    leaf exact-match-xr {
      type boolean;
      description "Exact match";
    }
    leaf allow-default-xr {
      type boolean;
      description "Allow default flag";
    }
    leaf recurse-xr {
      type boolean;
      description "Allow recurse flag";
    }
    leaf xtable {
      type boolean;
      description "Cross table nexthop";
    }
    leaf pack-sf-xr {
      type boolean;
      description "Pack SFS paths for multicast";
    }
    leaf pack-backup {
      type boolean;
      description "Pack backup paths";
    }
    leaf backup-route-xr {
      type boolean;
      description "Backup route notifications";
    }
    leaf best-metric-xr {
      type boolean;
      description "Return lowest metric for dest. metric";
    }
    leaf unres-nh-tree {
      type boolean;
      description "Context about which tree the server should walk";
    }
    leaf flags {
      type uint16;
      description "nh_entry flags";
    }
    leaf dest-path-count {
      type uint32;
      description "Number of destination paths";
    }
    leaf accrued-penalty {
      type uint16;
      description "Damped accured penalty";
    }
    leaf num-algo-label {
      type uint16;
      description "Destination number of Algorithm Labels";
    }
    leaf expiration-age {
      type uint32;
      description "How soon the nexthop is undamped";
    }
    leaf expiration-time {
      type uint64;
      description "Time where the first is undamped";
    }
    leaf min-damped-threshold {
      type uint32;
      description "Minimum damped threshold";
    }
    leaf max-damped-penalty {
      type uint32;
      description "Maximum damped threshold";
    }
    leaf decay-rate {
      type uint32;
      description "Damped decay rate";
    }
    leaf version {
      type uint32;
      description "Event version";
    }
    leaf last-event-age {
      type uint32;
      description "How long since last event occured";
    }
    leaf last-event-time {
      type uint64;
      description "Time at which last event occured";
    }

    list dest-path {
      description "Path(s) of the route";
      uses RIB-EDM-NH-PATH;
    }

    list algo-label-set {
      description "Destination list of Algorithm Labels";
      uses RIB-EDM-ALGO-LABEL-SET;
    }
  }

  grouping RIB-EDM-OPAQUE-OBJ {
    description "Informaton of an opaque data";
    leaf key {
      type yang:hex-string;
      description
        "The unique ID assigned to the opaque object by
        client";
    }
    leaf data {
      type yang:hex-string;
      description "The data part of the opaque object";
    }
    leaf protocol-id {
      type uint32;
      description "Protocol installing opaque";
    }
    leaf client-id {
      type uint32;
      description "Client installing opaque";
    }
    leaf distance {
      type uint32;
      description "Opaque distance";
    }
    leaf flags {
      type uint32;
      description "Opaque flags";
    }
    leaf num-backups {
      type uint32;
      description "Number of backup opaques installed";
    }
    leaf type {
      type Rib-opaque;
      description "Opaque Type";
    }
    leaf decoded-key {
      type string;
      description "Decoded opaque key string";
    }
    leaf decoded-data {
      type string;
      description "Decoded opaque data string";
    }
  }

  grouping RIB-EDM-PATH-SL-ID-INFO {
    description "Information of Segment List Identifier";
    leaf type {
      type Rib-edm-sl-id;
      description "Segment List ID type";
    }
    leaf sl-id {
      type uint32;
      description "Segment List ID";
    }
  }

  grouping RIB-EDM-PATH-VIA-AFT-ID {
    description "Information of Via aft ID attribute in path";
    leaf aft-id {
      type uint64;
      description "AFT ID for this path";
    }
    leaf vrf-id {
      type uint32;
      description "VRF ID for this path";
    }
    leaf type {
      type Rib-via-aft-id;
      description "Type of AFT ID";
    }
    leaf vrf-name {
      type string;
      description "VRF name";
    }
  }

  grouping RIB-EDM-PATH-IP-TUNNEL-INFO {
    description "Information of IP tunnel Info attribute in path";

    container src-ip-addr {
      description "Source IP Address";
      uses RIB-EDM-IP-ADDR;
    }

    container dst-ip-addr {
      description "Destination IP Address";
      uses RIB-EDM-IP-ADDR;
    }
    leaf auto-created {
      type boolean;
      description "Tunnel is auto created";
    }
    leaf tunnel-type {
      type string;
      description "Tunnel Type";
    }
    leaf has-evni {
      type boolean;
      description "Egress VXLAN Network Identifier present";
    }
    leaf evni {
      type uint32;
      description "Egress VXLAN Network Identifier";
    }
    leaf has-tunnel-id {
      type boolean;
      description "Tunnel ID present";
    }
    leaf tunnel-id {
      type uint32;
      description "Tunnel ID";
    }
    leaf has-vni {
      type boolean;
      description "VXLAN Network Identifier present";
    }
    leaf vni {
      type uint32;
      description "VXLAN Network Identifier";
    }
    leaf has-rtep-id {
      type boolean;
      description "Remote Tunnel End Point ID present";
    }
    leaf rtep-id {
      type uint64;
      description "Remote Tunnel End Point ID";
    }
    leaf flags {
      type uint32;
      description "VXLAN Network Identifier Flags";
    }
    leaf has-src-mac {
      type boolean;
      description "Source MAC Address present";
    }
    leaf src-mac {
      type yang:mac-address;
      description "Source MAC Address";
    }
    leaf has-dst-mac {
      type boolean;
      description "Destination MAC Address present";
    }
    leaf dst-mac {
      type yang:mac-address;
      description "Destination MAC Address";
    }
    leaf has-src-ip {
      type boolean;
      description "Source IP Address present";
    }
    leaf src-ip-afi {
      type uint32;
      description "Source IP AFI";
    }
    leaf has-dst-ip {
      type boolean;
      description "Destination IP Address present";
    }
    leaf dst-ip-afi {
      type uint32;
      description "Destination IP AFI";
    }
  }

  grouping RIB-EDM-VIA-SRV6-SID {
    description "Information related to Via-SRv6-SID";
    leaf sid {
      type inet:ipv6-address;
      description "Via-SRv6-SID value";
    }
    leaf resolution-length {
      type uint8;
      description "FIB Resolution length";
    }
  }

  grouping MGMT-SRV6-HEADEND-BEHAVIOR {
    description "SRv6 Headend Behavior Info";
    leaf type {
      type Mgmt-srv6-headend;
      description "Behavior type";
    }
    leaf description {
      type string;
      description "Behavior description";
    }
  }

  grouping RIB-EDM-PATH-SRV6-INFO {
    description "RIB path's SRv6 related information";

    container srv6-carrier-format {
      description "SRv6 Carrier Format";
      uses MGMT-SRV6-SID-FMT;
    }

    container srv6-headend-behavior {
      description "SRv6 headend behavior/type info";
      uses MGMT-SRV6-HEADEND-BEHAVIOR;
    }

    container via-srv6-sid {
      description "Via-SRv6-SID value";
      uses RIB-EDM-VIA-SRV6-SID;
    }
    leaf number-of-srv6-carriers {
      type uint8;
      description "Number of SRv6 Carriers";
    }
    leaf has-srv6-headend-behavior {
      type boolean;
      description "Path has some SRv6 head-end behavior associated";
    }
    leaf has-via-srv6-sid {
      type boolean;
      description "Via-SRv6-SID is present";
    }

    list srv6-carrier {
      description "List of SRv6 Carriers with one or more SIDs";
      uses MGMT-SRV6-SID;
    }
  }

  grouping RIB-EDM-PATH-GROUPING-INFO {
    description "Information of Path Grouping";
    leaf grouping-id {
      type uint32;
      description "Grouping ID for this path";
    }
  }

  grouping RIB-EDM-PATH-L2-INFO {
    description "Information of L2 Info attribute in path";
    leaf xcid {
      type uint32;
      description "L2 Cross Connect ID for this path";
    }
    leaf ac-interface {
      type xr:Interface-name;
      description "L2 AC Interface";
    }
    leaf split-horizon-group-id {
      type uint32;
      description "L2 Split Horizon Group ID";
    }
    leaf bridge-id {
      type uint32;
      description "L2 Bridge ID";
    }
  }

  grouping RIB-EDM-NNH {
    description "Information of a NNH in path installed in RIB";
    leaf type {
      type Rib-edm-nnh;
      description "type";
    }
    leaf unknownval {
      when "../type = 'unknown'" {
        description "../type = 'Unknown'";
      }
      type uint32;
      description "Unknown Value";
    }
    leaf address {
      when "../type = 'ipv4-address'" {
        description "../type = 'IPv4Address'";
      }
      type inet:ipv4-address;
      description "IPv4 Address";
    }
    leaf interface-index {
      when "../type = 'if-index'" {
        description "../type = 'IfIndex'";
      }
      type uint32;
      description "Interface Index";
    }
  }

  grouping IPV4-RIB-EDM-PATH {
    description "Information of a rib path";

    list ipv4-rib-edm-path {
      description "Next path";

      container address {
        xr:event-telemetry "Subscribe Telemetry Event";
        description "Nexthop";
        uses RIB-EDM-IP-ADDR;
      }

      container information-source {
        xr:event-telemetry "Subscribe Telemetry Event";
        description "Infosource";
        uses RIB-EDM-IP-ADDR;
      }

      container iid {
        description "Internal ID attribute";
        uses RIB-EDM-IP-ADDR;
      }

      container l2-info {
        description "L2 Info for this path";
        uses RIB-EDM-PATH-L2-INFO;
      }

      container path-grouping-info {
        description "Grouping Info for this path";
        uses RIB-EDM-PATH-GROUPING-INFO;
      }

      container srv6-info {
        description "SRv6 related information";
        uses RIB-EDM-PATH-SRV6-INFO;
      }

      container ip-tunnel-info {
        description "IP Tunnel Info for this path";
        uses RIB-EDM-PATH-IP-TUNNEL-INFO;
      }

      container via-aft-id {
        description "Via AFT ID info for this path";
        uses RIB-EDM-PATH-VIA-AFT-ID;
      }

      container segment-list-id-info {
        description "Segment List ID Info";
        uses RIB-EDM-PATH-SL-ID-INFO;
      }
      leaf interface-name {
        xr:event-telemetry "Subscribe Telemetry Event";
        type xr:Interface-name;
        description "Interface handle for the path's nexthop";
      }
      leaf metric {
        xr:event-telemetry "Subscribe Telemetry Event";
        type uint32;
        description "Metrics";
      }
      leaf load-metric {
        xr:event-telemetry "Subscribe Telemetry Event";
        type uint32;
        description "Load Metrics";
      }
      leaf flags64 {
        type uint64;
        description "Flags extended to 64 bits";
      }
      leaf flags {
        xr:event-telemetry "Subscribe Telemetry Event";
        type uint16;
        description "Flags";
      }
      leaf private-flags {
        type uint16;
        description "Private Flags, used internally by RIB";
      }
      leaf minimum-recurse-length {
        type uint8;
        description
          "Minimum netmask length of recursive resolving
          route";
      }
      leaf looped {
        type boolean;
        description "Looping path";
      }
      leaf next-hop-table-id {
        xr:event-telemetry "Subscribe Telemetry Event";
        type uint32;
        description "The table to which the next hop belongs";
      }
      leaf next-hop-vrf-name {
        xr:event-telemetry "Subscribe Telemetry Event";
        type string;
        description "VRF Name of the nh table";
      }
      leaf next-hop-table-name {
        xr:event-telemetry "Subscribe Telemetry Event";
        type string;
        description "NH table name";
      }
      leaf next-hop-afi {
        xr:event-telemetry "Subscribe Telemetry Event";
        type Rib-edm-afi-id;
        description "NH Address Family";
      }
      leaf next-hop-safi {
        xr:event-telemetry "Subscribe Telemetry Event";
        type Rib-edm-safi-id;
        description "NH Sub Address Family";
      }
      leaf route-label {
        xr:event-telemetry "Subscribe Telemetry Event";
        type uint32;
        description "Label associated with this path";
      }
      leaf tunnel-id {
        xr:event-telemetry "Subscribe Telemetry Event";
        type uint32;
        description "Tunnel ID associated with this path";
      }
      leaf pathid {
        xr:event-telemetry "Subscribe Telemetry Event";
        type uint32;
        description "Path id of this path";
      }
      leaf backup-pathid {
        xr:event-telemetry "Subscribe Telemetry Event";
        type uint32;
        description "Path id of this path's backup";
      }
      leaf ref-cnt-of-backup {
        type uint32;
        description
          "For backup paths, the number of active paths
          protected by the backup path";
      }
      leaf number-of-extended-communities {
        xr:event-telemetry "Subscribe Telemetry Event";
        type uint32;
        description
          "Number of extended communities associated with
          this path";
      }
      leaf mvpn-present {
        xr:event-telemetry "Subscribe Telemetry Event";
        type boolean;
        description "MVPN attribute present";
      }
      leaf path-rt-present {
        type boolean;
        description "Path RT present";
      }
      leaf vrf-import-rt-present {
        xr:event-telemetry "Subscribe Telemetry Event";
        type boolean;
        description "VRFIMPORTRTPresent";
      }
      leaf source-asrt-present {
        xr:event-telemetry "Subscribe Telemetry Event";
        type boolean;
        description "SOURCEASRTPresent";
      }
      leaf source-rd-present {
        xr:event-telemetry "Subscribe Telemetry Event";
        type boolean;
        description "SOURCERDPresent";
      }
      leaf segmented-nexthop-present {
        xr:event-telemetry "Subscribe Telemetry Event";
        type boolean;
        description "Segmented NH attributes present for this path";
      }
      leaf number-of-nnh {
        type uint32;
        description "Number of Next Next Hops";
      }
      leaf next-hop-id {
        xr:event-telemetry "Subscribe Telemetry Event";
        type uint32;
        description "NHID associated with this path";
      }
      leaf next-hop-id-refcount {
        type uint32;
        description "NHID references";
      }
      leaf stats-next-hop-id {
        type uint32;
        description "Path NHID used for StatsID";
      }
      leaf stats-next-hop-id-refcount {
        type uint32;
        description "Stats NHID references";
      }
      leaf ospf-area-id {
        xr:event-telemetry "Subscribe Telemetry Event";
        type string;
        description "OSPF area associated with the path";
      }
      leaf has-labelstk {
        xr:event-telemetry "Subscribe Telemetry Event";
        type boolean;
        description "Path has a label stack";
      }
      leaf num-labels {
        xr:event-telemetry "Subscribe Telemetry Event";
        type uint8;
        description "Number of labels in stack";
      }
      leaf binding-label {
        xr:event-telemetry "Subscribe Telemetry Event";
        type uint32;
        description "binding Label for this path";
      }
      leaf nhid-feid {
        type uint64;
        description "Fib nhid encap id";
      }
      leaf mpls-feid {
        type uint64;
        description "Fib mpls encap id";
      }
      leaf has-vxlan-network-id {
        type boolean;
        description "VXLAN Network Identifier exists for this path";
      }
      leaf vxlan-network-id {
        type uint32;
        description "VXLAN Network Identifier for this path";
      }
      leaf has-xcid {
        type boolean;
        description "L2 Cross Connect ID exists for this path";
      }
      leaf xcid {
        type uint32;
        description "L2 Cross Connect ID for this path";
      }
      leaf has-span-diag-interface {
        type boolean;
        description
          "SPAN Diagnostics Interface exists for this path";
      }
      leaf span-diag-interface {
        type xr:Interface-name;
        description "SPAN Diagnostics Interface for this path";
      }
      leaf has-subscriber-parent-interface {
        type boolean;
        description
          "Subscriber Parent Interface exists for this
          path";
      }
      leaf subscriber-parent-interface {
        type xr:Interface-name;
        description "Subscriber Parent Interface for this path";
      }
      leaf interface-index-present {
        type boolean;
        description
          "Flag to indicate if interface index attribute
          is present for this path";
      }
      leaf interface-index-attribute {
        type uint32;
        description "Interface Index attribute";
      }
      leaf iid-present {
        type boolean;
        description "Internal ID present";
      }
      leaf has-l2-info {
        type boolean;
        description "L2 Info present for this path";
      }
      leaf has-path-grouping-info {
        type boolean;
        description "Grouping Info present for this path";
      }
      leaf has-ip-tunnel-info {
        type boolean;
        description "IP Tunnel Info present for this path";
      }
      leaf has-via-aft-id {
        type boolean;
        description "Via AFT ID present for this path";
      }
      leaf has-segment-list-id-info {
        type boolean;
        description "Segment List ID Info present for this path";
      }
      list labelstk {
        description "Outgoing label stack for this path";
          leaf entry {
                      xr:event-telemetry "Subscribe Telemetry Event";

                      type uint32;

                      description "Outgoing label stack for this path";
          }
      }

      list next-next-hop {
        description "List of Next Next Hops";
        uses RIB-EDM-NNH;
      }

      list remote-backup-addr {
        max-elements "2";
        description "Remote backup node address";
        uses RIB-EDM-IP-ADDR;
      }
    }
  }

  grouping RIB-EDM-ROUTE-AFT-INFO {
    description "RIB route's AFT info";
    leaf aft-id {
      type uint64;
      description "AFT ID for this route";
    }
    leaf vrf-id {
      type uint32;
      description "VRF ID for this route";
    }
    leaf transaction-id {
      type uint64;
      description "Transaction ID";
    }
    leaf vrf-name {
      type string;
      description "VRF Name";
    }
  }

  grouping MGMT-SRV6-SID-FMT {
    description "SRv6 SID Format Info";
    leaf type {
      type Mgmt-srv6-sid-fmt;
      description "Format type";
    }
    leaf description {
      type string;
      description "Format description";
    }
  }

  grouping MGMT-SRV6-ENDPOINT-BEHAVIOR {
    description "SRv6 Endpoint Behavior Info";
    leaf type {
      type Mgmt-srv6-endpoint;
      description "Behavior type";
    }
    leaf description {
      type string;
      description "Behavior description";
    }
  }

  grouping RIB-EDM-ROUTE-SRV6-INFO {
    description "RIB route's SRv6 related information";

    container srv6-endpoint-behavior {
      description "SRv6 Endpoint behavior/type";
      uses MGMT-SRV6-ENDPOINT-BEHAVIOR;
    }

    container srv6-format {
      description "SRv6 Format";
      uses MGMT-SRV6-SID-FMT;
    }
    leaf is-srv6-endpoint {
      type boolean;
      description "Route is an SRv6 Endpoint (local SID)";
    }
    leaf is-srv6-locator {
      type boolean;
      description "Route corresponds to an SRv6 remote locator";
    }
    leaf srv6-locator-algo {
      type uint8;
      description "SRv6 Algo corresponding to SRv6 remote locator";
    }
  }

  grouping RIB-EDM-ALGO-LABEL-SET {
    description "Algorithm ID to Local Label information";
    leaf algorithm-id {
      type uint8;
      description "Algorithm Identifier";
    }
    leaf label {
      type uint32;
      description "Local label";
    }
    leaf metric {
      type uint32;
      description
        "Route Metric associated with Algorithm
        Identifier";
    }
  }

  grouping RIB-EDM-IP-PFX {
    description "IPv4/IPv6 IP address and Prefix length";

    container ip-address {
      description "IPv4/IPv6 address";
      uses RIB-EDM-IP-ADDR;
    }
    leaf prefix-length {
      type uint8;
      description "Prefix length";
    }
  }

  grouping IPV4-RIB-EDM-ROUTE {
    description
      "Information of a rib route head and rib proto
      route";

    container prefix {
      description "Route prefix";
      uses RIB-EDM-IP-PFX;
    }

    container srv6-info {
      description "SRv6 related information";
      uses RIB-EDM-ROUTE-SRV6-INFO;
    }

    container aft {
      description "Route AFT info";
      uses RIB-EDM-ROUTE-AFT-INFO;
    }

    container route-path {
      description "Path(s) of the route";
      uses IPV4-RIB-EDM-PATH;
    }
    leaf route-version {
      type uint32;
      description
        "Route version, incremented by one on each active
        route change";
    }
    leaf protocol-id {
      xr:event-telemetry "Subscribe Telemetry Event";
      type uint32;
      description "Protocol advertising the route";
    }
    leaf protocol-name {
      xr:event-telemetry "Subscribe Telemetry Event";
      type string;
      description " Name of Protocol";
    }
    leaf instance {
      type string;
      description "Instance name";
    }
    leaf client-id {
      type uint32;
      description "Client adding the route to RIB";
    }
    leaf mirrored {
      type boolean;
      description "Mirrored";
    }
    leaf route-type {
      xr:event-telemetry "Subscribe Telemetry Event";
      type uint16;
      description "Type of route installed in RIB";
    }
    leaf priority {
      xr:event-telemetry "Subscribe Telemetry Event";
      type uint8;
      description "Route priority";
    }
    leaf svd-type {
      type uint8;
      description "SVD Type of route";
    }
    leaf l2-route-type {
      type uint8;
      description "Type of route associated with L2 Service";
    }
    leaf flags {
      xr:event-telemetry "Subscribe Telemetry Event";
      type uint32;
      description "Route flags";
    }
    leaf extended-flags {
      xr:event-telemetry "Subscribe Telemetry Event";
      type uint64;
      description "Extended Route flags";
    }
    leaf tag {
      xr:event-telemetry "Subscribe Telemetry Event";
      type uint32;
      description "Opaque proto specific info";
    }
    leaf distance {
      xr:event-telemetry "Subscribe Telemetry Event";
      type uint32;
      description "Distance of the route";
    }
    leaf diversion-distance {
      type uint32;
      description "Diversion distance of the route";
    }
    leaf metric {
      xr:event-telemetry "Subscribe Telemetry Event";
      type uint32;
      description "Route metric";
    }
    leaf paths-count {
      xr:event-telemetry "Subscribe Telemetry Event";
      type uint32;
      description "Number of paths";
    }
    leaf attribute-identity {
      type uint32;
      description "BGP Attribute ID";
    }
    leaf traffic-index {
      type uint8;
      description "BGP Traffic Index";
    }
    leaf route-precedence {
      xr:event-telemetry "Subscribe Telemetry Event";
      type uint8;
      description "IP precedence for this route";
    }
    leaf qos-group {
      xr:event-telemetry "Subscribe Telemetry Event";
      type uint8;
      description "Route qos group";
    }
    leaf flow-tag {
      xr:event-telemetry "Subscribe Telemetry Event";
      type uint8;
      description "Flow tag for this route";
    }
    leaf fwd-class {
      xr:event-telemetry "Subscribe Telemetry Event";
      type uint8;
      description "Forward Class";
    }
    leaf pic-count {
      type uint8;
      description "Number of pic paths in this route";
    }
    leaf active {
      type boolean;
      description "Is the route active or backup";
    }
    leaf diversion {
      type boolean;
      description "Route has a diversion path";
    }
    leaf diversion-proto-name {
      type string;
      description "Diversion route protocol name";
    }
    leaf route-age {
      type uint32;
      units "second";
      description "Age of route (seconds)";
    }
    leaf route-label {
      type uint32;
      description "Local label of the route";
    }
    leaf version {
      type uint32;
      description "Route Version";
    }
    leaf tbl-version {
      type uint64;
      description "Table Version";
    }
    leaf route-modify-time {
      type uint64;
      units "nanosecond";
      description "Route modification time(nanoseconds)";
    }
    leaf prefix-feid {
      type uint64;
      description "Fib per-prefix encap id";
    }
    leaf number-of-algorithm-labels {
      type uint16;
      description
        "Number of Algorithm Labels associated with this
        prefix";
    }
    leaf no-fib-redist {
      type boolean;
      description "Should the route be redistributed to FIB";
    }
    leaf flexible-algorithm {
      type uint8;
      description "Flexible Algorithm associated with route";
    }
    leaf has-aft {
      type boolean;
      description "Route AFT info is valid";
    }

    list algorithm-label {
      description
        "List of Algorithm Labels associated with this
        Prefix";
      uses RIB-EDM-ALGO-LABEL-SET;
    }
  }

  grouping IPV4-RIB-EDM-UG-PRUNED-NODES {
    description "RIB updategroup pruned nodes information";
    leaf num-pruned-nodes {
      type uint32;
      description "Number of pruned nodes";
    }
    list pruned-node {
      max-elements "256";

      description "Pruned nodes ID";
        leaf entry {
                  type uint32;

                  description "Pruned nodes ID";
        }
    }
  }

  grouping IPV4-RIB-EDM-UG {
    description "RIB updategroup information";
    leaf ug-id {
      type uint32;
      description "Update Group ID";
    }
    leaf client-id {
      type uint32;
      description "ClientId associated with UG";
    }
    leaf parent-id {
      type int32;
      description "UG's parent if child";
    }
    leaf insync {
      type boolean;
      description "Is this ug insync with RIB";
    }
    leaf freezecnt {
      type uint32;
      description "Freeze count if frozen";
    }
  }

  grouping MGMT-SRV6-SID {
    description "SRv6 SID";
    leaf sid {
      type inet:ipv6-address;
      description "SID value";
    }
  }

  grouping RIB-EDM-IP-ADDR {
    description "RIB EDM IP ADDR";
    leaf afi {
      type Rib-edm-afi-id;
      description "AFI";
    }
    leaf none {
      when "../afi = 'none'" {
        description "../AFI = 'None'";
      }
      type uint8;
      description "No address family";
    }
    leaf ipv4 {
      when "../afi = 'ipv4'" {
        description "../AFI = 'IPv4'";
      }
      type Rib-in4-addr;
      description "IPv4 address type";
    }
    leaf ipv6 {
      when "../afi = 'ipv6'" {
        description "../AFI = 'IPv6'";
      }
      type Rib-in6-addr;
      description "IPv6 address type";
    }
  }

  grouping IPV4-RIB-EDM-NHID-HIST-OBJ {
    description "Information of nhid history objects";

    container nh-addr {
      description "nh addr";
      uses RIB-EDM-IP-ADDR;
    }

    container first-srv6-carrier {
      description "First SRv6 Carrier";
      uses MGMT-SRV6-SID;
    }
    leaf nhid {
      type uint32;
      description "nhid";
    }
    leaf ifindex {
      type xr:Interface-name;
      description "ifindex";
    }
    leaf tableid {
      type uint32;
      description "tableid";
    }
    leaf operation {
      type uint32;
      description "operation";
    }
    leaf update {
      type uint32;
      description "update";
    }
    leaf oper-time {
      type uint64;
      description "oper time";
    }
    leaf feature-type {
      type uint8;
      description "feature type";
    }
    leaf chkpt-obj-id {
      type uint32;
      description "chkpt obj id";
    }
    leaf number-of-srv6-carriers {
      type uint8;
      description "Number of SRv6 Carriers";
    }
  }
}
