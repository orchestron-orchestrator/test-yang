module Cisco-IOS-XR-ha-eem-policy-oper {

  /*** NAMESPACE / PREFIX DEFINITION ***/

  namespace "http://cisco.com/ns"+
    "/yang/Cisco-IOS-XR-ha-eem-policy-oper";


  prefix "ha-eem-policy-oper";

  /*** LINKAGE (IMPORTS / INCLUDES) ***/

  import Cisco-IOS-XR-types { prefix "xr"; }

  import cisco-semver { prefix "semver"; }

  include Cisco-IOS-XR-ha-eem-policy-oper-sub1 {
    revision-date 2019-04-05;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ha-eem-policy package operational data.

     This module contains definitions
     for the following management objects:
       eem: EEM operational data

     Copyright (c) 2013-2019 by Cisco Systems, Inc.
     All rights reserved.";

  revision "2019-04-05" {
    description
      "Establish semantic version baseline.";
    semver:module-version "1.0.0";
  }

  revision "2016-02-05" {
    description
      "IOS XR 6.0.1 revision.";
  }

  revision "2015-11-09" {
    description
      "IOS XR 6.0 revision.";
  }

  container eem {
    config false;
    description "EEM operational data";

    container dir-user {
      description "directory user";

      container library {
        description "directory user library";
        uses EEM-DIR-USR;
      }

      container policy {
        description "directory user policy";
        uses EEM-DIR-USR;
      }
    }

    container env-variables {
      description "list of environmental variables";

      list env-variable {
        key "name";
        description "environmental variables name and value ";
        leaf name {
          type xr:Cisco-ios-xr-string;
          description "Environmental variable name";
        }
        uses EEM-ENV;
      }
    }

    container refresh-time {
      description "Refresh time";
      uses EEM-REFRESH-TIME;
    }

    container reg-policies {
      description "list the registered policies";

      list reg-policy {
        key "name";
        description "policy name and create time ";
        leaf name {
          type xr:Cisco-ios-xr-string;
          description "policy name";
        }
        uses EEM-POLICY-REG;
      }
    }

    container avl-policies {
      description "list the available policies";

      list avl-policy {
        key "name";
        description "policy name and create time ";
        leaf name {
          type xr:Cisco-ios-xr-string;
          description "System policy name";
        }
        uses EEM-POLICY;
      }
    }
  }
}
