submodule Cisco-IOS-XR-tamsvcs-oper-sub1 {

  belongs-to Cisco-IOS-XR-tamsvcs-oper {
    prefix Cisco-IOS-XR-tamsvcs-oper;
  }

  /*** LINKAGE (IMPORTS / INCLUDES) ***/

  import cisco-semver { prefix "semver"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR tamsvcs package operational data.

     Copyright (c) 2013-2022 by Cisco Systems, Inc.
     All rights reserved.";

  revision "2022-08-30" {
    description
      "Show ha-sudi certs support for tam";
    semver:module-version "1.3.0";
  }

  revision "2021-06-25" {
    description
      "3rd Party Key Package support in XR";
    semver:module-version "1.2.0";
  }

  revision "2020-11-15" {
    description
      "Show device info and sudi certs support for tam";
    semver:module-version "1.1.0";
  }

  revision "2019-04-05" {
    description
      "Establish semantic version baseline.";
    semver:module-version "1.0.1";
  }

  revision "2015-11-09" {
    description
      "IOS XR 6.0 revision.";
  }

  grouping TAMSVCS-SUDI-CERTS {
    description "Tam Sudi certs bag";
    leaf sudi-root-cert {
      type string;
      description "Sudi Root Certificate";
    }
    leaf sudi-subca-cert {
      type string;
      description "Sudi SubCA Certificate";
    }
    leaf sudi-cert {
      type string;
      description "Sudi Certificate of Tam Device";
    }
  }

  grouping TAMSVCS-DEVICE-INFO {
    description "Tam device info bag";
    leaf device-type {
      type string;
      description "Type of Tam Device";
    }
    leaf device-pid {
      type string;
      description "Pid of Tam Device";
    }
    leaf device-serial {
      type string;
      description "Serial Number of Tam Device";
    }
    leaf device-firware-version {
      type string;
      description "Firmware version of the device";
    }
    leaf server-version {
      type string;
      description "Tam Server Version";
    }
    leaf server-package-version {
      type string;
      description "Tam Services Server Package Version";
    }
    leaf client-package-version {
      type string;
      description "Tam Services Client Package Version";
    }
  }

  grouping TAMSVCS-PUBKEYS-REVOKED {
    description "TAM Revoked Public Key List ";

    list revoked {
      description "Revoked list of Public Key";
      uses TAMSVCS-PUBKEYS;
    }
  }

  grouping TAMSVCS-INFO-ALL {
    description "Tam All info bag";
    leaf device-type {
      type string;
      description "Type of Tam Device";
    }
    leaf device-pid {
      type string;
      description "Pid of Tam Device";
    }
    leaf device-serial {
      type string;
      description "Serial Number of Tam Device";
    }
    leaf device-firware-version {
      type string;
      description "Firmware version of the device";
    }
    leaf server-version {
      type string;
      description "Tam Server Version";
    }
    leaf server-package-version {
      type string;
      description "Tam Services Server Package Version";
    }
    leaf client-package-version {
      type string;
      description "Tam Services Client Package Version";
    }
    leaf sudi-root-cert {
      type string;
      description "Sudi Root Certificate";
    }
    leaf sudi-subca-cert {
      type string;
      description "Sudi SubCA Certificate";
    }
    leaf sudi-cert {
      type string;
      description "Sudi Leaf Certificate";
    }
    leaf ha-sudi-root-cert {
      type string;
      description "HA Sudi Root Certificate";
    }
    leaf ha-sudi-subca-cert {
      type string;
      description "HA Sudi SubCA Certificate";
    }
    leaf ha-sudi-cert {
      type string;
      description "HA Sudi Leaf Certificate";
    }
  }

  grouping TAMSVCS-PUBKEYS {
    description "TAM Public Key ";
    leaf so-name {
      type string;
      description "Name of Public Key";
    }
    leaf so-data {
      type string;
      description "Content of SO Public Key";
    }
  }

  grouping TAMSVCS-PUBKEYS-ALLOWED {
    description "TAM Allowed Public Key List ";

    list allowed {
      description "Allowed list of Public Key";
      uses TAMSVCS-PUBKEYS;
    }
  }

  grouping TAMSVCS-HA-SUDI-CERTS {
    description "Tam Ha Sudi certs bag";
    leaf ha-sudi-root-cert {
      type string;
      description "HA Sudi Root Certificate";
    }
    leaf ha-sudi-subca-cert {
      type string;
      description "HA Sudi SubCA Certificate";
    }
    leaf ha-sudi-cert {
      type string;
      description "HA Sudi Certificate of Tam Device";
    }
  }
}
