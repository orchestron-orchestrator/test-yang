submodule Cisco-IOS-XR-ip-rib-gribi-oper-sub1 {

  belongs-to Cisco-IOS-XR-ip-rib-gribi-oper {
    prefix Cisco-IOS-XR-ip-rib-gribi-oper;
  }

  /*** LINKAGE (IMPORTS / INCLUDES) ***/

  import ietf-inet-types { prefix "inet"; }

  import ietf-yang-types { prefix "yang"; }

  import Cisco-IOS-XR-types { prefix "xr"; }

  import cisco-semver { prefix "semver"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ip-rib-gribi package operational data.

     Copyright (c) 2013-2022 by Cisco Systems, Inc.
     All rights reserved.";

  revision "2022-12-13" {
    description
      "Modify RIB opaque redist history";
    semver:module-version "1.0.0";
  }

  revision "2022-05-11" {
    description
      "has-aft added to route";
  }

  revision "2022-04-29" {
    description
      "Add AFT NHG info";
  }

  revision "2022-03-02" {
    description
      "Add AFT info";
  }

  revision "2019-04-05" {
    description
      "Establish semantic version baseline.";
  }

  revision "2015-11-09" {
    description
      "IOS XR 6.0 revision.";
  }

  typedef Rib-edm-sl-id {
    type enumeration {
      enum invalid {
        description "Invalid Segment List";
      }
      enum srv6 {
        description "SRv6 Segment List";
      }
      enum mpls {
        description "MPLS Segment List";
      }
    }
    description "Rib edm sl id";
  }
  typedef Rib-via-aft-id {
    type enumeration {
      enum none {
        description "Via None";
      }
      enum via-nh-aft-id {
        description "Via Next-hop AFT ID";
      }
      enum via-nh-group-aft-id {
        description "Via Next-hop Group AFT ID";
      }
    }
    description "Rib via aft id";
  }
  typedef Mgmt-srv6-headend {
    type enumeration {
      enum unknown {
        description "Unknown";
      }
      enum transit {
        description "T (Pure transit)";
      }
      enum h-insert {
        description "H.Insert";
      }
      enum h-insert-red {
        description "H.Insert.Red";
      }
      enum h-encaps {
        description "H.Encaps";
      }
      enum h-encaps-red {
        description "H.Encaps.Red";
      }
      enum h-encaps-l2 {
        description "H.Encaps.L2";
      }
      enum h-encaps-l2-red {
        description "H.Encaps.L2.Red";
      }
    }
    description "SRv6 Headend Behavior Type";
  }
  typedef Rib-edm-nnh {
    type enumeration {
      enum unknown {
        description "Unknown - Invalid";
      }
      enum ipv4-address {
        description "IPv4 Address";
      }
      enum if-index {
        description "Interface Index";
      }
    }
    description "Rib edm nnh";
  }
  typedef Rib-edm-safi-id {
    type enumeration {
      enum none {
        value 0;
        description "No sub-address family";
      }
      enum unicast {
        value 1;
        description "Unicast SAFI";
      }
      enum multicast {
        value 2;
        description "Multicast SAFI";
      }
    }
    description "Rib edm safi id";
  }
  typedef Mgmt-srv6-sid-fmt {
    type enumeration {
      enum none {
        value 0;
        description "No format";
      }
      enum base {
        value 1;
        description "Base Format";
      }
      enum f3216 {
        value 2;
        description "Micro-segment F3216 Format";
      }
    }
    description "SRv6 SID Format Type";
  }
  typedef Mgmt-srv6-endpoint {
    type enumeration {
      enum unknown {
        value 0;
        description "Unknown Endpoint type";
      }
      enum end {
        value 1;
        description "End (no PSP/USP)";
      }
      enum end-with-psp {
        value 2;
        description "End with PSP";
      }
      enum end-with-usp {
        value 3;
        description "End with USP";
      }
      enum end-with-psp-usp {
        value 4;
        description "End with PSP/USP";
      }
      enum end-x {
        value 5;
        description "End.X (no PSP/USP)";
      }
      enum end-x-with-psp {
        value 6;
        description "End.X with PSP";
      }
      enum end-x-with-usp {
        value 7;
        description "End.X with USP";
      }
      enum end-x-with-psp-usp {
        value 8;
        description "End.X with PSP/USP";
      }
      enum end-tbl {
        value 9;
        description "End.T (no PSP/USP)";
      }
      enum end-tbl-with-psp {
        value 10;
        description "End.T with PSP";
      }
      enum end-tbl-with-usp {
        value 11;
        description "End.T with USP";
      }
      enum end-tbl-with-psp-usp {
        value 12;
        description "End.T with PSP/USP";
      }
      enum end-b6-insert {
        value 13;
        description "End.B6.Insert";
      }
      enum end-b6-encaps {
        value 14;
        description "End.B6.Encaps";
      }
      enum end-bm {
        value 15;
        description "End.BM";
      }
      enum end-dx6 {
        value 16;
        description "End.DX6";
      }
      enum end-dx4 {
        value 17;
        description "End.DX4";
      }
      enum end-dt6 {
        value 18;
        description "End.DT6";
      }
      enum end-dt4 {
        value 19;
        description "End.DT4";
      }
      enum end-dt46 {
        value 20;
        description "End.DT46";
      }
      enum end-dx2 {
        value 21;
        description "End.DX2";
      }
      enum end-dx2v {
        value 22;
        description "End.DX2V";
      }
      enum end-dt2u {
        value 23;
        description "End.DT2U";
      }
      enum end-dt2m {
        value 24;
        description "End.DT2M";
      }
      enum end-s {
        value 25;
        description "End.S";
      }
      enum end-b6-insert-red {
        value 26;
        description "End.B6.Insert.Reduced";
      }
      enum end-b6-encaps-red {
        value 27;
        description "End.B6.Encaps.Reduced";
      }
      enum end-with-usd {
        value 28;
        description "End with USD";
      }
      enum end-with-psp-usd {
        value 29;
        description "End with PSP/USD";
      }
      enum end-with-usp-usd {
        value 30;
        description "End with USP/USD";
      }
      enum end-with-psp-usp-usd {
        value 31;
        description "End with PSP/USP/USD";
      }
      enum end-x-with-usd {
        value 32;
        description "End.X with USD";
      }
      enum end-x-with-psp-usd {
        value 33;
        description "End.X with PSP/USD";
      }
      enum end-x-with-usp-usd {
        value 34;
        description "End.X with USP/USD";
      }
      enum end-x-with-psp-usp-usd {
        value 35;
        description "End.X with PSP/USP/USD";
      }
      enum end-tbl-with-usd {
        value 36;
        description "End.T with USD";
      }
      enum end-tbl-with-psp-usd {
        value 37;
        description "End.T with PSP/USD";
      }
      enum end-tbl-with-usp-usd {
        value 38;
        description "End.T with USP/USD";
      }
      enum end-tbl-with-psp-usp-usd {
        value 39;
        description "End.T with PSP/USP/USD";
      }
      enum end-op {
        value 40;
        description "End.OP";
      }
      enum end-otp {
        value 41;
        description "End.OTP";
      }
      enum un-shift-only {
        value 42;
        description "uN Shift-only";
      }
      enum un {
        value 43;
        description "uN";
      }
      enum un-psp {
        value 44;
        description "uN with PSP";
      }
      enum un-usp {
        value 45;
        description "uN with USP";
      }
      enum un-psp-usp {
        value 46;
        description "uN with PSP-USP";
      }
      enum un-usd {
        value 47;
        description "uN with USD";
      }
      enum un-psp-usd {
        value 48;
        description "uN with PSP-USD";
      }
      enum un-usp-usd {
        value 49;
        description "uN with USP-USD";
      }
      enum un-psp-usp-usd {
        value 50;
        description "uN with PSP_USP-USD";
      }
      enum ua-shift-only {
        value 51;
        description "uA Shift-only";
      }
      enum ua {
        value 52;
        description "uA";
      }
      enum ua-psp {
        value 53;
        description "uA with PSP";
      }
      enum ua-usp {
        value 54;
        description "uA with USP";
      }
      enum ua-psp-usp {
        value 55;
        description "uA with PSP-USP";
      }
      enum ua-usd {
        value 56;
        description "uA with USD";
      }
      enum ua-psp-usd {
        value 57;
        description "uA with PSP-USD";
      }
      enum ua-usp-usd {
        value 58;
        description "uA with USP-USD";
      }
      enum ua-psp-usp-usd {
        value 59;
        description "uA with PSP_USP-USD";
      }
      enum udx6 {
        value 60;
        description "uDX6";
      }
      enum udx4 {
        value 61;
        description "uDX4";
      }
      enum udt6 {
        value 62;
        description "uDT6";
      }
      enum udt4 {
        value 63;
        description "uDT4";
      }
      enum udt46 {
        value 64;
        description "uDT46";
      }
      enum udx2 {
        value 65;
        description "uDX2";
      }
      enum udx2v {
        value 66;
        description "uDX2V";
      }
      enum udt2u {
        value 67;
        description "uDT2U";
      }
      enum udt2m {
        value 68;
        description "uDT2M";
      }
      enum ub6-insert {
        value 69;
        description "uB6 Insert";
      }
      enum ub6-encaps {
        value 70;
        description "uB6 Encaps";
      }
      enum ub6-insert-red {
        value 71;
        description "uB6 Insert.Red";
      }
      enum ub6-encaps-red {
        value 72;
        description "uB6 Encaps.Red";
      }
      enum ubm {
        value 73;
        description "uBM";
      }
      enum ub6-psp-usd-insert-red {
        value 79;
        description "uB6 with PSP-USD Insert.Red";
      }
      enum ub6-psp-usd-encaps-red {
        value 80;
        description "uB6 with PSP-USD Encaps.Red";
      }
      enum utef {
        value 81;
        description "PT uTEF";
      }
    }
    description "SRv6 Endpoint Behavior Type";
  }
  typedef Rib-in6-addr {
    type inet:ipv6-address;
    description "Rib in6 addr";
  }
  typedef Rib-in4-addr {
    type inet:ipv4-address;
    description "Rib in4 addr";
  }
  typedef Rib-edm-afi-id {
    type enumeration {
      enum none {
        value 0;
        description "No address family";
      }
      enum ipv4 {
        value 1;
        description "IPv4 AFI";
      }
      enum ipv6 {
        value 2;
        description "IPv6 AFI";
      }
    }
    description "Rib edm afi id";
  }
  typedef Rib-opaque {
    type enumeration {
      enum opaque-attribute {
        value 0;
        description "opaque attribute";
      }
      enum opaque-ipfrr {
        value 1;
        description "opaque ipfrr";
      }
      enum opaque-ip-nh {
        value 2;
        description "opaque ip nh";
      }
      enum opaque-tunnel-nh {
        value 3;
        description "opaque tunnel nh";
      }
      enum opaque-tunnel-safi {
        value 4;
        description "opaque tunnel safi";
      }
      enum opaque-virtual-ll-address {
        value 5;
        description "opaque virtual ll address";
      }
      enum opaque-lisp {
        value 6;
        description "opaque lisp";
      }
      enum opaque-tep-vxlan {
        value 7;
        description "opaque tep vxlan";
      }
      enum opaque-tep-bgp {
        value 8;
        description "opaque tep bgp";
      }
      enum opaque-cofo-s-label {
        value 9;
        description "opaque cofo s label";
      }
      enum opaque-cofo-nnh-if {
        value 10;
        description "opaque cofo nnh if";
      }
      enum opaque-cofo-mcast {
        value 11;
        description "opaque cofo mcast";
      }
      enum opaque-label-range {
        value 12;
        description "opaque label range";
      }
      enum opaque-tep {
        value 13;
        description "opaque tep";
      }
      enum opaque-ipv4-adj {
        value 14;
        description "opaque ipv4 adj";
      }
      enum opaque-ipv6-adj {
        value 15;
        description "opaque ipv6 adj";
      }
      enum opaque-sfi {
        value 16;
        description "opaque sfi";
      }
      enum opaque-ltep {
        value 17;
        description "opaque ltep";
      }
      enum opaque-aft-nh {
        value 18;
        description "opaque aft nh";
      }
      enum opaque-rtep {
        value 19;
        description "opaque rtep";
      }
      enum opaque-encap-id {
        value 20;
        description "opaque encap id";
      }
      enum opaque-policy {
        value 21;
        description "opaque policy";
      }
      enum opaque-max {
        value 22;
        description "opaque max";
      }
    }
    description "Rib opaque";
  }

  grouping RIB-EDM-PATH-SL-ID-INFO {
    description "Information of Segment List Identifier";
    leaf type {
      type Rib-edm-sl-id;
      description "Segment List ID type";
    }
    leaf sl-id {
      type uint32;
      description "Segment List ID";
    }
  }

  grouping RIB-EDM-PATH-VIA-AFT-ID {
    description "Information of Via aft ID attribute in path";
    leaf aft-id {
      type uint64;
      description "AFT ID for this path";
    }
    leaf vrf-id {
      type uint32;
      description "VRF ID for this path";
    }
    leaf type {
      type Rib-via-aft-id;
      description "Type of AFT ID";
    }
    leaf vrf-name {
      type string;
      description "VRF name";
    }
  }

  grouping RIB-EDM-PATH-IP-TUNNEL-INFO {
    description "Information of IP tunnel Info attribute in path";

    container src-ip-addr {
      description "Source IP Address";
      uses RIB-EDM-IP-ADDR;
    }

    container dst-ip-addr {
      description "Destination IP Address";
      uses RIB-EDM-IP-ADDR;
    }
    leaf auto-created {
      type boolean;
      description "Tunnel is auto created";
    }
    leaf tunnel-type {
      type string;
      description "Tunnel Type";
    }
    leaf has-evni {
      type boolean;
      description "Egress VXLAN Network Identifier present";
    }
    leaf evni {
      type uint32;
      description "Egress VXLAN Network Identifier";
    }
    leaf has-tunnel-id {
      type boolean;
      description "Tunnel ID present";
    }
    leaf tunnel-id {
      type uint32;
      description "Tunnel ID";
    }
    leaf has-vni {
      type boolean;
      description "VXLAN Network Identifier present";
    }
    leaf vni {
      type uint32;
      description "VXLAN Network Identifier";
    }
    leaf has-rtep-id {
      type boolean;
      description "Remote Tunnel End Point ID present";
    }
    leaf rtep-id {
      type uint64;
      description "Remote Tunnel End Point ID";
    }
    leaf flags {
      type uint32;
      description "VXLAN Network Identifier Flags";
    }
    leaf has-src-mac {
      type boolean;
      description "Source MAC Address present";
    }
    leaf src-mac {
      type yang:mac-address;
      description "Source MAC Address";
    }
    leaf has-dst-mac {
      type boolean;
      description "Destination MAC Address present";
    }
    leaf dst-mac {
      type yang:mac-address;
      description "Destination MAC Address";
    }
    leaf has-src-ip {
      type boolean;
      description "Source IP Address present";
    }
    leaf src-ip-afi {
      type uint32;
      description "Source IP AFI";
    }
    leaf has-dst-ip {
      type boolean;
      description "Destination IP Address present";
    }
    leaf dst-ip-afi {
      type uint32;
      description "Destination IP AFI";
    }
  }

  grouping RIB-EDM-VIA-SRV6-SID {
    description "Information related to Via-SRv6-SID";
    leaf sid {
      type inet:ipv6-address;
      description "Via-SRv6-SID value";
    }
    leaf resolution-length {
      type uint8;
      description "FIB Resolution length";
    }
  }

  grouping MGMT-SRV6-HEADEND-BEHAVIOR {
    description "SRv6 Headend Behavior Info";
    leaf type {
      type Mgmt-srv6-headend;
      description "Behavior type";
    }
    leaf description {
      type string;
      description "Behavior description";
    }
  }

  grouping MGMT-SRV6-SID {
    description "SRv6 SID";
    leaf sid {
      type inet:ipv6-address;
      description "SID value";
    }
  }

  grouping RIB-EDM-PATH-SRV6-INFO {
    description "RIB path's SRv6 related information";

    container srv6-carrier-format {
      description "SRv6 Carrier Format";
      uses MGMT-SRV6-SID-FMT;
    }

    container srv6-headend-behavior {
      description "SRv6 headend behavior/type info";
      uses MGMT-SRV6-HEADEND-BEHAVIOR;
    }

    container via-srv6-sid {
      description "Via-SRv6-SID value";
      uses RIB-EDM-VIA-SRV6-SID;
    }
    leaf number-of-srv6-carriers {
      type uint8;
      description "Number of SRv6 Carriers";
    }
    leaf has-srv6-headend-behavior {
      type boolean;
      description "Path has some SRv6 head-end behavior associated";
    }
    leaf has-via-srv6-sid {
      type boolean;
      description "Via-SRv6-SID is present";
    }

    list srv6-carrier {
      description "List of SRv6 Carriers with one or more SIDs";
      uses MGMT-SRV6-SID;
    }
  }

  grouping RIB-EDM-PATH-GROUPING-INFO {
    description "Information of Path Grouping";
    leaf grouping-id {
      type uint32;
      description "Grouping ID for this path";
    }
  }

  grouping RIB-EDM-PATH-L2-INFO {
    description "Information of L2 Info attribute in path";
    leaf xcid {
      type uint32;
      description "L2 Cross Connect ID for this path";
    }
    leaf ac-interface {
      type xr:Interface-name;
      description "L2 AC Interface";
    }
    leaf split-horizon-group-id {
      type uint32;
      description "L2 Split Horizon Group ID";
    }
    leaf bridge-id {
      type uint32;
      description "L2 Bridge ID";
    }
  }

  grouping RIB-EDM-NNH {
    description "Information of a NNH in path installed in RIB";
    leaf type {
      type Rib-edm-nnh;
      description "type";
    }
    leaf unknownval {
      when "../type = 'unknown'" {
        description "../type = 'Unknown'";
      }
      type uint32;
      description "Unknown Value";
    }
    leaf address {
      when "../type = 'ipv4-address'" {
        description "../type = 'IPv4Address'";
      }
      type inet:ipv4-address;
      description "IPv4 Address";
    }
    leaf interface-index {
      when "../type = 'if-index'" {
        description "../type = 'IfIndex'";
      }
      type uint32;
      description "Interface Index";
    }
  }

  grouping IPV6-RIB-EDM-PATH {
    description "Information of a rib path";

    list ipv6-rib-edm-path {
      description "Next path";

      container address {
        xr:event-telemetry "Subscribe Telemetry Event";
        description "Nexthop";
        uses RIB-EDM-IP-ADDR;
      }

      container information-source {
        xr:event-telemetry "Subscribe Telemetry Event";
        description "Infosource";
        uses RIB-EDM-IP-ADDR;
      }

      container iid {
        description "Internal ID attribute";
        uses RIB-EDM-IP-ADDR;
      }

      container l2-info {
        description "L2 Info for this path";
        uses RIB-EDM-PATH-L2-INFO;
      }

      container path-grouping-info {
        description "Grouping Info for this path";
        uses RIB-EDM-PATH-GROUPING-INFO;
      }

      container srv6-info {
        description "SRv6 related information";
        uses RIB-EDM-PATH-SRV6-INFO;
      }

      container ip-tunnel-info {
        description "IP Tunnel Info for this path";
        uses RIB-EDM-PATH-IP-TUNNEL-INFO;
      }

      container via-aft-id {
        description "Via AFT ID info for this path";
        uses RIB-EDM-PATH-VIA-AFT-ID;
      }

      container segment-list-id-info {
        description "Segment List ID Info";
        uses RIB-EDM-PATH-SL-ID-INFO;
      }
      leaf interface-name {
        xr:event-telemetry "Subscribe Telemetry Event";
        type xr:Interface-name;
        description "Interface handle for the path's nexthop";
      }
      leaf metric {
        xr:event-telemetry "Subscribe Telemetry Event";
        type uint32;
        description "Metrics";
      }
      leaf load-metric {
        xr:event-telemetry "Subscribe Telemetry Event";
        type uint32;
        description "Load Metrics";
      }
      leaf flags64 {
        type uint64;
        description "Flags extended to 64 bits";
      }
      leaf flags {
        xr:event-telemetry "Subscribe Telemetry Event";
        type uint16;
        description "Flags";
      }
      leaf private-flags {
        type uint16;
        description "Private Flags, used internally by RIB";
      }
      leaf minimum-recurse-length {
        type uint8;
        description
          "Minimum netmask length of recursive resolving
          route";
      }
      leaf looped {
        type boolean;
        description "Looping path";
      }
      leaf next-hop-table-id {
        xr:event-telemetry "Subscribe Telemetry Event";
        type uint32;
        description "The table to which the next hop belongs";
      }
      leaf next-hop-vrf-name {
        xr:event-telemetry "Subscribe Telemetry Event";
        type string;
        description "VRF Name of the nh table";
      }
      leaf next-hop-table-name {
        xr:event-telemetry "Subscribe Telemetry Event";
        type string;
        description "NH table name";
      }
      leaf next-hop-afi {
        xr:event-telemetry "Subscribe Telemetry Event";
        type Rib-edm-afi-id;
        description "NH Address Family";
      }
      leaf next-hop-safi {
        xr:event-telemetry "Subscribe Telemetry Event";
        type Rib-edm-safi-id;
        description "NH Sub Address Family";
      }
      leaf route-label {
        xr:event-telemetry "Subscribe Telemetry Event";
        type uint32;
        description "Label associated with this path";
      }
      leaf tunnel-id {
        xr:event-telemetry "Subscribe Telemetry Event";
        type uint32;
        description "Tunnel ID associated with this path";
      }
      leaf pathid {
        xr:event-telemetry "Subscribe Telemetry Event";
        type uint32;
        description "Path id of this path";
      }
      leaf backup-pathid {
        xr:event-telemetry "Subscribe Telemetry Event";
        type uint32;
        description "Path id of this path's backup";
      }
      leaf ref-cnt-of-backup {
        type uint32;
        description
          "For backup paths, the number of active paths
          protected by the backup path";
      }
      leaf number-of-extended-communities {
        xr:event-telemetry "Subscribe Telemetry Event";
        type uint32;
        description
          "Number of extended communities associated with
          this path";
      }
      leaf mvpn-present {
        xr:event-telemetry "Subscribe Telemetry Event";
        type boolean;
        description "MVPN attribute present";
      }
      leaf path-rt-present {
        type boolean;
        description "Path RT present";
      }
      leaf vrf-import-rt-present {
        xr:event-telemetry "Subscribe Telemetry Event";
        type boolean;
        description "VRFIMPORTRTPresent";
      }
      leaf source-asrt-present {
        xr:event-telemetry "Subscribe Telemetry Event";
        type boolean;
        description "SOURCEASRTPresent";
      }
      leaf source-rd-present {
        xr:event-telemetry "Subscribe Telemetry Event";
        type boolean;
        description "SOURCERDPresent";
      }
      leaf segmented-nexthop-present {
        xr:event-telemetry "Subscribe Telemetry Event";
        type boolean;
        description "Segmented NH attributes present for this path";
      }
      leaf number-of-nnh {
        type uint32;
        description "Number of Next Next Hops";
      }
      leaf next-hop-id {
        xr:event-telemetry "Subscribe Telemetry Event";
        type uint32;
        description "NHID associated with this path";
      }
      leaf next-hop-id-refcount {
        type uint32;
        description "NHID references";
      }
      leaf stats-next-hop-id {
        type uint32;
        description "Path NHID used for StatsID";
      }
      leaf stats-next-hop-id-refcount {
        type uint32;
        description "Stats NHID references";
      }
      leaf ospf-area-id {
        xr:event-telemetry "Subscribe Telemetry Event";
        type string;
        description "OSPF area associated with the path";
      }
      leaf has-labelstk {
        xr:event-telemetry "Subscribe Telemetry Event";
        type boolean;
        description "Path has a label stack";
      }
      leaf num-labels {
        xr:event-telemetry "Subscribe Telemetry Event";
        type uint8;
        description "Number of labels in stack";
      }
      leaf binding-label {
        xr:event-telemetry "Subscribe Telemetry Event";
        type uint32;
        description "binding Label for this path";
      }
      leaf nhid-feid {
        type uint64;
        description "Fib nhid encap id";
      }
      leaf mpls-feid {
        type uint64;
        description "Fib mpls encap id";
      }
      leaf has-vxlan-network-id {
        type boolean;
        description "VXLAN Network Identifier exists for this path";
      }
      leaf vxlan-network-id {
        type uint32;
        description "VXLAN Network Identifier for this path";
      }
      leaf has-xcid {
        type boolean;
        description "L2 Cross Connect ID exists for this path";
      }
      leaf xcid {
        type uint32;
        description "L2 Cross Connect ID for this path";
      }
      leaf has-span-diag-interface {
        type boolean;
        description
          "SPAN Diagnostics Interface exists for this path";
      }
      leaf span-diag-interface {
        type xr:Interface-name;
        description "SPAN Diagnostics Interface for this path";
      }
      leaf has-subscriber-parent-interface {
        type boolean;
        description
          "Subscriber Parent Interface exists for this
          path";
      }
      leaf subscriber-parent-interface {
        type xr:Interface-name;
        description "Subscriber Parent Interface for this path";
      }
      leaf interface-index-present {
        type boolean;
        description
          "Flag to indicate if interface index attribute
          is present for this path";
      }
      leaf interface-index-attribute {
        type uint32;
        description "Interface Index attribute";
      }
      leaf iid-present {
        type boolean;
        description "Internal ID present";
      }
      leaf has-l2-info {
        type boolean;
        description "L2 Info present for this path";
      }
      leaf has-path-grouping-info {
        type boolean;
        description "Grouping Info present for this path";
      }
      leaf has-ip-tunnel-info {
        type boolean;
        description "IP Tunnel Info present for this path";
      }
      leaf has-via-aft-id {
        type boolean;
        description "Via AFT ID present for this path";
      }
      leaf has-segment-list-id-info {
        type boolean;
        description "Segment List ID Info present for this path";
      }
      leaf-list labelstk {
        xr:event-telemetry "Subscribe Telemetry Event";
        type uint32;
        description "Outgoing label stack for this path";
      }

      list next-next-hop {
        description "List of Next Next Hops";
        uses RIB-EDM-NNH;
      }

      list remote-backup-addr {
        max-elements "2";
        description "Remote backup node address";
        uses RIB-EDM-IP-ADDR;
      }
    }
  }

  grouping RIB-EDM-ROUTE-AFT-INFO {
    description "RIB route's AFT info";
    leaf aft-id {
      type uint64;
      description "AFT ID for this route";
    }
    leaf vrf-id {
      type uint32;
      description "VRF ID for this route";
    }
    leaf transaction-id {
      type uint64;
      description "Transaction ID";
    }
    leaf vrf-name {
      type string;
      description "VRF Name";
    }
  }

  grouping MGMT-SRV6-SID-FMT {
    description "SRv6 SID Format Info";
    leaf type {
      type Mgmt-srv6-sid-fmt;
      description "Format type";
    }
    leaf description {
      type string;
      description "Format description";
    }
  }

  grouping MGMT-SRV6-ENDPOINT-BEHAVIOR {
    description "SRv6 Endpoint Behavior Info";
    leaf type {
      type Mgmt-srv6-endpoint;
      description "Behavior type";
    }
    leaf description {
      type string;
      description "Behavior description";
    }
  }

  grouping RIB-EDM-ROUTE-SRV6-INFO {
    description "RIB route's SRv6 related information";

    container srv6-endpoint-behavior {
      description "SRv6 Endpoint behavior/type";
      uses MGMT-SRV6-ENDPOINT-BEHAVIOR;
    }

    container srv6-format {
      description "SRv6 Format";
      uses MGMT-SRV6-SID-FMT;
    }
    leaf is-srv6-endpoint {
      type boolean;
      description "Route is an SRv6 Endpoint (local SID)";
    }
    leaf is-srv6-locator {
      type boolean;
      description "Route corresponds to an SRv6 remote locator";
    }
    leaf srv6-locator-algo {
      type uint8;
      description "SRv6 Algo corresponding to SRv6 remote locator";
    }
  }

  grouping RIB-EDM-ALGO-LABEL-SET {
    description "Algorithm ID to Local Label information";
    leaf algorithm-id {
      type uint8;
      description "Algorithm Identifier";
    }
    leaf label {
      type uint32;
      description "Local label";
    }
    leaf metric {
      type uint32;
      description
        "Route Metric associated with Algorithm
        Identifier";
    }
  }

  grouping RIB-EDM-IP-ADDR {
    description "RIB EDM IP ADDR";
    leaf afi {
      type Rib-edm-afi-id;
      description "AFI";
    }
    leaf none {
      when "../afi = 'none'" {
        description "../AFI = 'None'";
      }
      type uint8;
      description "No address family";
    }
    leaf ipv4 {
      when "../afi = 'ipv4'" {
        description "../AFI = 'IPv4'";
      }
      type Rib-in4-addr;
      description "IPv4 address type";
    }
    leaf ipv6 {
      when "../afi = 'ipv6'" {
        description "../AFI = 'IPv6'";
      }
      type Rib-in6-addr;
      description "IPv6 address type";
    }
  }

  grouping RIB-EDM-IP-PFX {
    description "IPv4/IPv6 IP address and Prefix length";

    container ip-address {
      description "IPv4/IPv6 address";
      uses RIB-EDM-IP-ADDR;
    }
    leaf prefix-length {
      type uint8;
      description "Prefix length";
    }
  }

  grouping IPV6-RIB-EDM-ROUTE {
    description
      "Information of a rib route head and rib proto
      route";

    container prefix {
      description "Route prefix";
      uses RIB-EDM-IP-PFX;
    }

    container srv6-info {
      description "SRv6 related information";
      uses RIB-EDM-ROUTE-SRV6-INFO;
    }

    container aft {
      description "Route AFT info";
      uses RIB-EDM-ROUTE-AFT-INFO;
    }

    container route-path {
      description "Path(s) of the route";
      uses IPV6-RIB-EDM-PATH;
    }
    leaf route-version {
      type uint32;
      description
        "Route version, incremented by one on each active
        route change";
    }
    leaf protocol-id {
      xr:event-telemetry "Subscribe Telemetry Event";
      type uint32;
      description "Protocol advertising the route";
    }
    leaf protocol-name {
      xr:event-telemetry "Subscribe Telemetry Event";
      type string;
      description " Name of Protocol";
    }
    leaf instance {
      type string;
      description "Instance name";
    }
    leaf client-id {
      type uint32;
      description "Client adding the route to RIB";
    }
    leaf mirrored {
      type boolean;
      description "Mirrored";
    }
    leaf route-type {
      xr:event-telemetry "Subscribe Telemetry Event";
      type uint16;
      description "Type of route installed in RIB";
    }
    leaf priority {
      xr:event-telemetry "Subscribe Telemetry Event";
      type uint8;
      description "Route priority";
    }
    leaf svd-type {
      type uint8;
      description "SVD Type of route";
    }
    leaf l2-route-type {
      type uint8;
      description "Type of route associated with L2 Service";
    }
    leaf flags {
      xr:event-telemetry "Subscribe Telemetry Event";
      type uint32;
      description "Route flags";
    }
    leaf extended-flags {
      xr:event-telemetry "Subscribe Telemetry Event";
      type uint64;
      description "Extended Route flags";
    }
    leaf tag {
      xr:event-telemetry "Subscribe Telemetry Event";
      type uint32;
      description "Opaque proto specific info";
    }
    leaf distance {
      xr:event-telemetry "Subscribe Telemetry Event";
      type uint32;
      description "Distance of the route";
    }
    leaf diversion-distance {
      type uint32;
      description "Diversion distance of the route";
    }
    leaf metric {
      xr:event-telemetry "Subscribe Telemetry Event";
      type uint32;
      description "Route metric";
    }
    leaf paths-count {
      xr:event-telemetry "Subscribe Telemetry Event";
      type uint32;
      description "Number of paths";
    }
    leaf attribute-identity {
      type uint32;
      description "BGP Attribute ID";
    }
    leaf traffic-index {
      type uint8;
      description "BGP Traffic Index";
    }
    leaf route-precedence {
      xr:event-telemetry "Subscribe Telemetry Event";
      type uint8;
      description "IP precedence for this route";
    }
    leaf qos-group {
      xr:event-telemetry "Subscribe Telemetry Event";
      type uint8;
      description "Route qos group";
    }
    leaf flow-tag {
      xr:event-telemetry "Subscribe Telemetry Event";
      type uint8;
      description "Flow tag for this route";
    }
    leaf fwd-class {
      xr:event-telemetry "Subscribe Telemetry Event";
      type uint8;
      description "Forward Class";
    }
    leaf pic-count {
      type uint8;
      description "Number of pic paths in this route";
    }
    leaf active {
      type boolean;
      description "Is the route active or backup";
    }
    leaf diversion {
      type boolean;
      description "Route has a diversion path";
    }
    leaf diversion-proto-name {
      type string;
      description "Diversion route protocol name";
    }
    leaf route-age {
      type uint32;
      units "second";
      description "Age of route (seconds)";
    }
    leaf route-label {
      type uint32;
      description "Local label of the route";
    }
    leaf version {
      type uint32;
      description "Route Version";
    }
    leaf tbl-version {
      type uint64;
      description "Table Version";
    }
    leaf route-modify-time {
      type uint64;
      units "nanosecond";
      description "Route modification time(nanoseconds)";
    }
    leaf prefix-feid {
      type uint64;
      description "Fib per-prefix encap id";
    }
    leaf number-of-algorithm-labels {
      type uint16;
      description
        "Number of Algorithm Labels associated with this
        prefix";
    }
    leaf no-fib-redist {
      type boolean;
      description "Should the route be redistributed to FIB";
    }
    leaf flexible-algorithm {
      type uint8;
      description "Flexible Algorithm associated with route";
    }
    leaf has-aft {
      type boolean;
      description "Route AFT info is valid";
    }

    list algorithm-label {
      description
        "List of Algorithm Labels associated with this
        Prefix";
      uses RIB-EDM-ALGO-LABEL-SET;
    }
  }

  grouping IPV6-RIB-EDM-OPAQUE-OBJ {
    description "Informaton of an opaque data";
    leaf key {
      type yang:hex-string;
      description
        "The unique ID assigned to the opaque object by
        client";
    }
    leaf data {
      type yang:hex-string;
      description "The data part of the opaque object";
    }
    leaf protocol-id {
      type uint32;
      description "Protocol installing opaque";
    }
    leaf client-id {
      type uint32;
      description "Client installing opaque";
    }
    leaf distance {
      type uint32;
      description "Opaque distance";
    }
    leaf flags {
      type uint32;
      description "Opaque flags";
    }
    leaf num-backups {
      type uint32;
      description "Number of backup opaques installed";
    }
    leaf type {
      type Rib-opaque;
      description "Opaque Type";
    }
    leaf decoded-key {
      type string;
      description "Decoded opaque key string";
    }
    leaf decoded-data {
      type string;
      description "Decoded opaque data string";
    }
  }
}
