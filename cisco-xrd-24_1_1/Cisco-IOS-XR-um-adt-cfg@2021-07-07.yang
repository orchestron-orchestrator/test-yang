module Cisco-IOS-XR-um-adt-cfg {

  /*** NAMESPACE / PREFIX DEFINITION ***/

  namespace "http://cisco.com/ns/yang/Cisco-IOS-XR-um-adt-cfg";
  prefix um-adt-cfg;

  /*** LINKAGE (IMPORTS / INCLUDES) ***/

  import Cisco-IOS-XR-types {
    prefix xr;
  }

  import cisco-semver { prefix "semver"; }

  /*** META INFORMATION ***/

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR adt package configuration.

     This YANG module augments the
     modules with configuration data.

     Copyright (c) 2021-2022 by Cisco Systems, Inc.
     All rights reserved.";

  revision 2021-07-07 {
    description
      "Initial release";
    semver:module-version "1.0.0";
  }


  container adt {
    description
      "ADT configuration commands";
    container enable {
      presence "Indicates a enable node is configured.";
      description
        "Enable ADT";
    }
    container input {
      description
        "configure adt data source";
      container mdt {
        presence "Indicates a mdt node is configured.";
        description
          "Sensor group configuration";
        container sensor-groups {
          description
            "Sensor group configuration";
          list sensor-group {
            key "sensor-group-name";
            description
              "Sensor Group Id";
            leaf sensor-group-name {
              type xr:Cisco-ios-xr-string {
                length "1..800" {
                  description
                    "Sensor Group Id";
                }
              }
              description
                "Sensor Group Id";
            }
          }
        }
      }
    }
  }
}
