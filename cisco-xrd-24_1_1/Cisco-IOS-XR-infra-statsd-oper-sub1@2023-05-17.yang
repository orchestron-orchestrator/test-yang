submodule Cisco-IOS-XR-infra-statsd-oper-sub1 {

  belongs-to Cisco-IOS-XR-infra-statsd-oper {
    prefix Cisco-IOS-XR-infra-statsd-oper;
  }

  /*** LINKAGE (IMPORTS / INCLUDES) ***/

  import cisco-semver { prefix "semver"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR infra-statsd package operational data.

     Copyright (c) 2013-2023 by Cisco Systems, Inc.
     All rights reserved.";

  revision "2023-05-17" {
    description
      "Adding last-update-time field in Interface Rates container
       2022-10-31
         Container names changed for Interface counter rates
       2022-09-30
         Interface counter rates support added";
    semver:module-version "1.3.0";
  }

  revision "2020-12-17" {
    description
      "Unit of bandwidth in datarate container changed from 32-bit to 64-bit.";
    semver:module-version "1.2.0";
  }

  revision "2020-10-08" {
    description
      "Unit of last-data-time in milliseconds reverted to seconds for generic stats
      2020-05-05
           Added Hardware timestamp support for protocol stats.
      2020-04-14
           Unit of last-data-time changed from seconds to milliseconds for generic stats
      2020-04-14
           Data type of last-data-time changed from uint32 to uint64 for generic and proto stats
      2020-04-14
           Adding Hardware timestamp feature in generic structure.";
    semver:module-version "1.1.0";
  }

  revision "2019-04-05" {
    description
      "Establish semantic version baseline.";
    semver:module-version "1.0.1";
  }

  revision "2015-11-09" {
    description
      "IOS XR 6.0 revision.";
  }

  grouping IFCS-RATE-BAG {
    description "Interface client rate";
    leaf time-interval-ms {
      type uint64;
      description
        "Time period in ms over which the rates was
        calculated";
    }
    leaf input-datarate-kbps {
      type uint64;
      units "bit/s";
      description "Input data rate in 1000's of bps";
    }
    leaf input-packetratepps {
      type uint64;
      description "Input packets in pps";
    }
    leaf output-datarate-kbps {
      type uint64;
      units "bit/s";
      description "Output data rate in 1000's of bps";
    }
    leaf output-packetratepps {
      type uint64;
      description "Output packets in pps";
    }
    leaf overhead-bytes {
      type uint64;
      units "byte";
      description "Overhead bytes per packet";
    }
    leaf bandwidth-kbps {
      type uint64;
      units "bit/s";
      description "Bandwidth in 1000's of bps";
    }
    leaf input-bandwidth-percent {
      type uint8;
      units "percentage";
      description "Percent Input bandwidth utilization";
    }
    leaf output-bandwidth-percent {
      type uint8;
      units "percentage";
      description "Percent Output bandwidth utilization";
    }
    leaf last-update-time {
      type uint64;
      description
        "Time(in ms) when the counters were last updated
        bythe stats collector from hardware";
    }
  }

  grouping STATSDBAG-DATARATE {
    description "Datarate information";
    leaf input-data-rate {
      type uint64;
      units "bit/s";
      description "Input data rate in 1000's of bps";
    }
    leaf input-packet-rate {
      type uint64;
      units "packet/s";
      description "Input packets per second";
    }
    leaf output-data-rate {
      type uint64;
      units "bit/s";
      description "Output data rate in 1000's of bps";
    }
    leaf output-packet-rate {
      type uint64;
      units "packet/s";
      description "Output packets per second";
    }
    leaf peak-input-data-rate {
      type uint64;
      description
        "Peak input data rate, highest spike since last
        clear counters";
    }
    leaf peak-input-packet-rate {
      type uint64;
      description
        "Peak input packet rate, highest spike since last
        clear counters";
    }
    leaf peak-output-data-rate {
      type uint64;
      description
        "Peak output data rate, highest spike since last
        clear counters";
    }
    leaf peak-output-packet-rate {
      type uint64;
      description
        "Peak output packet rate, highest spike since
        last clear counters";
    }
    leaf bandwidth {
      type uint64;
      units "kbit/s";
      description "Bandwidth (in kbps)";
    }
    leaf load-interval {
      type uint32;
      description "Number of 30-sec intervals less one";
    }
    leaf output-load {
      type uint8;
      description "Output load as fraction of 255";
    }
    leaf input-load {
      type uint8;
      description "Input load as fraction of 255";
    }
    leaf reliability {
      type uint8;
      description "Reliability coefficient";
    }
  }

  grouping IFSTATSBAG-GENERIC {
    description "Generic set of interface counters";
    leaf packets-received {
      type uint64;
      description "Total Packets received";
    }
    leaf bytes-received {
      type uint64;
      units "byte";
      description "Total Bytes received";
    }
    leaf packets-sent {
      type uint64;
      description "Total Packets sent";
    }
    leaf bytes-sent {
      type uint64;
      units "byte";
      description "Total Bytes sent";
    }
    leaf multicast-packets-received {
      type uint64;
      description "Total no. of multicast packets received";
    }
    leaf broadcast-packets-received {
      type uint64;
      description "Total no. of broadcast packets received";
    }
    leaf multicast-packets-sent {
      type uint64;
      description "Total no. of multicast packets sent";
    }
    leaf broadcast-packets-sent {
      type uint64;
      description "Total no. of broadcast packets sent";
    }
    leaf output-drops {
      type uint32;
      description "No. of packet dropped before being transmitted";
    }
    leaf output-queue-drops {
      type uint32;
      description
        "Number of packets dropped due to configured
        output policy";
    }
    leaf input-drops {
      type uint32;
      description "Total input drops";
    }
    leaf input-queue-drops {
      type uint32;
      description
        "Placeholder for packets dropped due to configure
        input policy";
    }
    leaf runt-packets-received {
      type uint32;
      description
        "Received packets which are too small to be
        handled";
    }
    leaf giant-packets-received {
      type uint32;
      description
        "Received packets which are too large to be
        handled";
    }
    leaf throttled-packets-received {
      type uint32;
      description
        "No. of times the receiver on the port is was
        disabled";
    }
    leaf parity-packets-received {
      type uint32;
      description "No. of parity errors on the interface";
    }
    leaf unknown-protocol-packets-received {
      type uint32;
      description
        "No. of packets dropped because they were
        destined for higher levelprotocols not configure
        or running on the interface";
    }
    leaf input-errors {
      type uint32;
      description "Total input errors";
    }
    leaf crc-errors {
      type uint32;
      description "Input CRC errors";
    }
    leaf input-overruns {
      type uint32;
      description
        "No. of input packets received with FIFO or DMA
        overrun errors";
    }
    leaf framing-errors-received {
      type uint32;
      description "No. of packets received with framing error";
    }
    leaf input-ignored-packets {
      type uint32;
      description
        "Packets dropped due to internal driver error or
        hardware errors ";
    }
    leaf input-aborts {
      type uint32;
      description "No. of packets whose reciept was aborted";
    }
    leaf output-errors {
      type uint32;
      description
        "Total packets that could not be transmitted due
        to internal driver error";
    }
    leaf output-underruns {
      type uint32;
      description
        "Transmitted packets with FIFO or DMA underrun
        errors";
    }
    leaf output-buffer-failures {
      type uint32;
      description "No. of no resource error received on output";
    }
    leaf output-buffers-swapped-out {
      type uint32;
      description "No. of packets swapped to DRAM or main memory";
    }
    leaf applique {
      type uint32;
      description
        "No. of unrecoverable error which have occured on
        the applique";
    }
    leaf resets {
      type uint32;
      description "Number of hardware resets";
    }
    leaf carrier-transitions {
      type uint32;
      description
        "No. of times the carrier detect signal of
        interface has changed state";
    }
    leaf availability-flag {
      type uint32;
      description "Availability bit mask";
    }
    leaf last-data-time {
      type uint64;
      units "second";
      description
        "Time when counters were last written (in
        seconds)";
    }
    leaf hardware-timestamp {
      type uint64;
      units "millisecond";
      description
        "Time when counters were last read by Primary
        collector from hardware (in msecs)";
    }
    leaf seconds-since-last-clear-counters {
      type uint32;
      units "second";
      description
        "Time elapsed since last clear command executed
        (in Seconds)";
    }
    leaf last-discontinuity-time {
      type uint32;
      units "second";
      description
        "SysUpTime when counters were last reset (in
        seconds)";
    }
    leaf seconds-since-packet-received {
      type uint32;
      units "second";
      description "Time elapsed since packet received (in Seconds)";
    }
    leaf seconds-since-packet-sent {
      type uint32;
      units "second";
      description "Time elapsed since packet sent (in Seconds)";
    }
  }

  grouping IFSTATSBAG-PROTO {
    description "Interface counters per protocol";
    leaf bytes-received {
      type uint64;
      units "byte";
      description "Total no. of Bytes received";
    }
    leaf packets-received {
      type uint64;
      description "Total no. of Packets received";
    }
    leaf bytes-sent {
      type uint64;
      units "byte";
      description "Total no. of Bytes sent";
    }
    leaf packets-sent {
      type uint64;
      description "Total no. of Packets sent";
    }
    leaf protocol {
      type uint32;
      description "Protocol number";
    }
    leaf last-data-time {
      type uint64;
      units "second";
      description
        "Time when counters were last written (in
        seconds)";
    }
    leaf input-data-rate {
      type uint64;
      units "bit/s";
      description "Input data rate in 1000's of bps";
    }
    leaf input-packet-rate {
      type uint64;
      units "packet/s";
      description "Input packets per second";
    }
    leaf output-data-rate {
      type uint64;
      units "bit/s";
      description "Output data rate in 1000's of bps";
    }
    leaf output-packet-rate {
      type uint64;
      units "packet/s";
      description "Output packets per second";
    }
    leaf hardware-timestamp {
      type uint64;
      units "millisecond";
      description
        "Time when counters were last read by Primary
        collector from hardware (in msecs)";
    }
  }
}
