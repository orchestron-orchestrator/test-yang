module Cisco-IOS-XR-infra-correlator-cfg {

  /*** NAMESPACE / PREFIX DEFINITION ***/

  namespace "http://cisco.com/ns/yang"+
    "/Cisco-IOS-XR-infra-correlator-cfg";


  prefix "infra-correlator-cfg";

  /*** LINKAGE (IMPORTS / INCLUDES) ***/

  import Cisco-IOS-XR-types { prefix "xr"; }

  import cisco-semver { prefix "semver"; }

  import Cisco-IOS-XR-infra-syslog-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR infra-correlator package configuration.

     This YANG module augments the
       Cisco-IOS-XR-infra-syslog-cfg
     module with configuration data.

     Copyright (c) 2013-2019 by Cisco Systems, Inc.
     All rights reserved.";

  revision "2019-04-05" {
    description
      "Establish semantic version baseline.";
    semver:module-version "1.0.1";
  }

  revision "2017-05-01" {
    description
      "Fixing backward compatibility error in module.";
  }

  revision "2015-11-09" {
    description
      "IOS XR 6.0 revision.";
  }

  grouping CONTEXT-CORRELATION {
    description "Common node of non-stateful, stateful";
    leaf context-correlation {
      type empty;
      description "Enable correlation on alarm context";
    }
  }

  grouping NON-ROOT-CAUSE-TABLE {
    description "Common node of non-stateful, stateful";

    container non-root-causes {
      description "Table of configured non-rootcause";

      list non-root-cause {
        key "category group message-code";
        description "A non-rootcause";
        leaf category {
          type string;
          description "Correlated message category";
        }
        leaf group {
          type string;
          description "Correlated message group";
        }
        leaf message-code {
          type string;
          description "Correlated message code";
        }
      }
    }
  }

  grouping TIMEOUT-ROOT-CAUSE {
    description "Common node of non-stateful, stateful";
    leaf timeout-root-cause {
      type uint32 {
        range "1..7200000";
      }
      units "millisecond";
      description
        "Rootcause Timeout (time to wait for rootcause)
        in milliseconds";
    }
  }

  grouping APPLIED-TO {
    description "Common node of rule, rule-set";

    container applied-to {
      description "Applied to the Rule or Ruleset";

      container contexts {
        description "Table of configured contexts to apply";

        list context {
          key "context";
          description "A context";
          leaf context {
            type string {
              length "1..32";
            }
            description "Context";
          }
        }
      }

      container locations {
        description "Table of configured locations to apply";

        list location {
          key "location";
          description "A location";
          leaf location {
            type xr:Node-id;
            description "Location";
          }
        }
      }
      leaf all {
        type empty;
        description "Apply to all of the router";
      }
    }
  }

  grouping TIMEOUT {
    description "Common node of non-stateful, stateful";
    leaf timeout {
      type uint32 {
        range "1..7200000";
      }
      units "millisecond";
      description
        "Timeout (time to wait for active correlation) in
        milliseconds";
    }
  }

  grouping ROOT-CAUSE {
    description "Common node of non-stateful, stateful";

    container root-cause {
      description "The root cause";
      leaf category {
        type string;
        description "Root message category";
      }
      leaf group {
        type string;
        description "Root message group";
      }
      leaf message-code {
        type string;
        description "Root message code";
      }
    }
  }

  augment "/a1:syslog" {

    container correlator {
      description "Configure properties of the event correlator";

      container rules {
        description "Table of configured rules";

        list rule {
          key "name";
          description "Rule name";

          container definition {
            description "Configure a specified correlation rule";
            leaf timeout {
              type uint32 {
                range "1..7200000";
              }
              description
                "Timeout (time the rule is to be active) in
                milliseconds";
            }
            leaf category-name-entry1 {
              type string;
              description "Root message category name";
            }
            leaf group-name-entry1 {
              type string;
              description "Root message group name";
            }
            leaf message-code-entry1 {
              type string;
              description "Root message code";
            }
            leaf category-name-entry2 {
              type string;
              description "Correlated message category name";
            }
            leaf group-name-entry2 {
              type string;
              description "Correlated message group name";
            }
            leaf message-code-entry2 {
              type string;
              description "Correlated message code";
            }
            leaf category-name-entry3 {
              type string;
              description "Correlated message category name";
            }
            leaf group-name-entry3 {
              type string;
              description "Correlated message group name";
            }
            leaf message-code-entry3 {
              type string;
              description "Correlated message code";
            }
            leaf category-name-entry4 {
              type string;
              description "Correlated message category name";
            }
            leaf group-name-entry4 {
              type string;
              description "Correlated message group name";
            }
            leaf message-code-entry4 {
              type string;
              description "Correlated message code";
            }
            leaf category-name-entry5 {
              type string;
              description "Correlated message category name";
            }
            leaf group-name-entry5 {
              type string;
              description "Correlated message group name";
            }
            leaf message-code-entry5 {
              type string;
              description "Correlated message code";
            }
            leaf category-name-entry6 {
              type string;
              description "Correlated message category name";
            }
            leaf group-name-entry6 {
              type string;
              description "Correlated message group name";
            }
            leaf message-code-entry6 {
              type string;
              description "Correlated message code";
            }
            leaf category-name-entry7 {
              type string;
              description "Correlated message category name";
            }
            leaf group-name-entry7 {
              type string;
              description "Correlated message group name";
            }
            leaf message-code-entry7 {
              type string;
              description "Correlated message code";
            }
            leaf category-name-entry8 {
              type string;
              description "Correlated message category name";
            }
            leaf group-name-entry8 {
              type string;
              description "Correlated message group name";
            }
            leaf message-code-entry8 {
              type string;
              description "Correlated message code";
            }
            leaf category-name-entry9 {
              type string;
              description "Correlated message category name";
            }
            leaf group-name-entry9 {
              type string;
              description "Correlated message group name";
            }
            leaf message-code-entry9 {
              type string;
              description "Correlated message code";
            }
            leaf category-name-entry10 {
              type string;
              description "Correlated message category name";
            }
            leaf group-name-entry10 {
              type string;
              description "Correlated message group name";
            }
            leaf message-code-entry10 {
              type string;
              description "Correlated message code";
            }
          }

          container non-stateful {
            description "The Non-Stateful Rule Type";
            uses CONTEXT-CORRELATION;
            uses TIMEOUT-ROOT-CAUSE;
            uses NON-ROOT-CAUSE-TABLE;
            uses ROOT-CAUSE;
            uses TIMEOUT;
          }

          container stateful {
            description "The Stateful Rule Type";
            leaf reparent {
              type empty;
              description
                "Enable reparent of alarm on rootcause alarm
                clear";
            }
            leaf reissue {
              type empty;
              description
                "Enable reissue of non-bistate alarms on
                rootcause alarm clear";
            }
            uses CONTEXT-CORRELATION;
            uses TIMEOUT-ROOT-CAUSE;
            uses NON-ROOT-CAUSE-TABLE;
            uses ROOT-CAUSE;
            uses TIMEOUT;
          }

          container apply-to {
            description "Apply the Rules";

            container contexts {
              description
                "Apply rule to a specified list of contexts,
                e.g. interfaces";
              leaf-list context {
                type string;
                max-elements "32";
                description "One or more context names";
              }
            }

            container locations {
              description
                "Apply rule to a specified list of Locations";
              leaf-list location {
                type xr:Node-id;
                max-elements "32";
                description "One or more Locations";
              }
            }
            leaf all-of-router {
              type empty;
              description "Apply the rule to all of the router";
            }
          }
          leaf name {
            type string {
              length "1..32";
            }
            description "Rule name";
          }
          uses APPLIED-TO;
        }
      }

      container rule-sets {
        description "Table of configured rulesets";

        list rule-set {
          key "name";
          description "Ruleset name";

          container rulenames {
            description "Table of configured rulenames";

            list rulename {
              key "rulename";
              description "A rulename";
              leaf rulename {
                type string {
                  length "1..32";
                }
                description "Rule name";
              }
            }
          }
          leaf name {
            type string {
              length "1..32";
            }
            description "Ruleset name";
          }
          uses APPLIED-TO;
        }
      }
      leaf buffer-size {
        type uint32 {
          range "1024..52428800";
        }
        description "Configure size of the correlator buffer";
      }
    }
    description
      "This augment extends the configuration data of
      'Cisco-IOS-XR-infra-syslog-cfg'";
  }

  augment "/a1:syslog" {

    container suppression {
      description
        "Configure properties of the syslog/alarm
        suppression";

      container rules {
        description "Table of configured rules";

        list rule {
          key "name";
          description "Rule name";

          container applied-to {
            description "Applied to the Rule";

            container sources {
              description "Table of configured sources to apply";

              list source {
                key "source";
                description "An alarm source";
                leaf source {
                  type xr:Node-id;
                  description "Source";
                }
              }
            }
            leaf all {
              type empty;
              description "Apply to all of the router";
            }
          }

          container alarm-causes {
            description "Causes of alarms to be suppressed";

            list alarm-cause {
              key "category group code";
              description
                "Category, Group and Code of alarm/syslog to
                be suppressed";
              leaf category {
                type string {
                  length "1..32";
                }
                description "Category";
              }
              leaf group {
                type string {
                  length "1..32";
                }
                description "Group";
              }
              leaf code {
                type string {
                  length "1..32";
                }
                description "Code";
              }
            }
          }
          leaf all-alarms {
            type empty;
            description "Suppress all alarms";
          }
          leaf name {
            type string {
              length "1..32";
            }
            description "Rule name";
          }
        }
      }
    }
    description
      "This augment extends the configuration data of
      'Cisco-IOS-XR-infra-syslog-cfg'";
  }
}
