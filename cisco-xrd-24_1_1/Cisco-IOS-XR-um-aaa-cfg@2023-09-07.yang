module Cisco-IOS-XR-um-aaa-cfg {

  /*** NAMESPACE / PREFIX DEFINITION ***/

  namespace "http://cisco.com/ns/yang/Cisco-IOS-XR-um-aaa-cfg";
  prefix um-aaa-cfg;

  /*** LINKAGE (IMPORTS / INCLUDES) ***/
  import cisco-semver { prefix "semver"; }

  /*** META INFORMATION ***/

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR aaa package configuration.

     This YANG module augments the
     modules with configuration data.

     Copyright (c) 2021-2023 by Cisco Systems, Inc.
     All rights reserved.";

  revision 2023-09-07 {
    description
      "Added local in must statement for commands authorization-list
       2022-10-28
         Removed range check for banner/login node
       2022-07-18
         Modified must statements for authorization-list nodes";
    semver:module-version "2.1.0";
  }

  revision "2021-10-10" {
    description
      "Modified must statements for group-2 nodes
      2021-07-07
          Removed conatiner api from container authorization and accounting";
    semver:module-version "2.0.0";
  }

  revision "2021-02-08" {
    description
      "Initial release";
    semver:module-version "1.0.0";
  }

  container aaa {
    description
      "Authentication, Authorization and Accounting";
    container authentication {
      description
        "AAA Authentication data";
      container ppp {
        description
          "Set authentication lists for PPP";
        list authentication-list {
          key "list-name";
          description
            "List name for AAA authentication";
          leaf list-name {
            type union {
              type string {
                pattern 'default' {
                  description
                    "Default list name for AAA authentication";
                }
              }
              type string {
                length "1..253" {
                  description
                    "List name for AAA authentication.
                     Allowed special chars for tacacs server group are A-Z,a-z,_,.,-,%,=,+,space allowed with backslash,;,:,|,#,$,0-9
                     and for radius server group are _,-,.,;,:,$,#,space allowed with backslash";
                }
              }
            }
            description
              "List name for AAA authentication";
          }
          container local {
            must "not(../groups/group-1/tacacs or
                  ../groups/group-1/radius or
                  ../groups/group-1/server-group-name)";
            presence "Indicates a local node is configured.";
            description
              "Local command accounting using syslog";
          }
          container groups {
            description
              "Use Server-group";
            container group-1 {
              description
                "First server-group";
              container tacacs {
                must 'not(../../../local) and not(../radius or ../server-group-name)';
                presence "Indicates a tacacs node is configured.";
                description
                  "Use list of all TACACS+ hosts";
              }
              container radius {
                must 'not(../../../local) and not(../tacacs or ../server-group-name)';
                presence "Indicates a radius node is configured.";
                description
                  "Use list of all RADIUS hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must 'not(../../../local) and not(../tacacs or ../radius)';
                description
                  "server-group name";
              }
            }
            container group-2 {
              description
                "Second server-group";
              container local {
                must "(../../group-1/tacacs or ../../group-1/radius or
                      ../../group-1/server-group-name) and
                      not(../tacacs or ../radius or ../server-group-name or
                      ../../../local)";
                presence "Indicates a local node is configured.";
                description
                  "Local command accounting using syslog";
              }
              container tacacs {
                must "(../../group-1/radius or ../../group-1/server-group-name or ../../../local)
                      and not(../local or ../radius or ../server-group-name or
                      ../../group-1/tacacs)";
                presence "Indicates a tacacs node is configured.";
                description
                  "Use list of all TACACS+ hosts";
              }
              container radius {
                must "(../../group-1/tacacs or ../../group-1/server-group-name or ../../../local)
                      and not(../local or ../tacacs or ../server-group-name or
                      ../../group-1/radius)";
                presence "Indicates a radius node is configured.";
                description
                  "Use list of all RADIUS hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must "(../../group-1/tacacs or ../../group-1/radius or
                      ../../group-1/server-group-name or ../../../local) and
                      not(../local or ../tacacs or ../radius)";
                description
                  "server-group name";
              }
            }
            container group-3 {
              description
                "Second server-group";
              container local {
                must "(../../group-2/tacacs or ../../group-2/radius or
                      ../../group-2/server-group-name) and
                      not(../tacacs or ../radius or ../server-group-name or
                      ../../group-2/local)";
                presence "Indicates a local node is configured.";
                description
                  "Local command accounting using syslog";
              }
              container tacacs {
                must "(../../group-2/local or ../../group-2/radius or
                      ../../group-2/server-group-name)
                      and not(../local or ../radius or ../server-group-name or
                      ../../group-1/tacacs or ../../group-2/tacacs)";
                presence "Indicates a tacacs node is configured.";
                description
                  "Use list of all TACACS+ hosts";
              }
              container radius {
                must "(../../group-2/local or ../../group-2/tacacs or
                      ../../group-2/server-group-name)
                      and not(../local or ../tacacs or ../server-group-name or
                      ../../group-1/radius or ../../group-2/radius)";
                presence "Indicates a radius node is configured.";
                description
                  "Use list of all RADIUS hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must "(../../group-2/local or ../../group-2/tacacs or
                      ../../group-2/radius or ../../group-2/server-group-name)
                      and not(../local or ../tacacs or ../radius)";
                description
                  "server-group name";
              }
            }
            container group-4 {
              description
                "Second server-group";
              container local {
                must "(../../group-3/tacacs or ../../group-3/radius or
                      ../../group-3/server-group-name) and
                      not(../tacacs or ../radius or ../server-group-name or
                      ../../group-3/local)";
                presence "Indicates a local node is configured.";
                description
                  "Local command accounting using syslog";
              }
              container tacacs {
                must "(../../group-3/local or ../../group-3/radius or
                      ../../group-3/server-group-name) and
                      not(../local or ../radius or ../server-group-name or
                      ../../group-1/tacacs or ../../group-2/tacacs or
                      ../../group-3/tacacs)";
                presence "Indicates a tacacs node is configured.";
                description
                  "Use list of all TACACS+ hosts";
              }
              container radius {
                must "(../../group-3/local or ../../group-3/tacacs or
                      ../../group-3/server-group-name) and
                      not(../local or ../tacacs or ../server-group-name or
                      ../../group-1/radius or ../../group-2/radius or
                      ../../group-3/radius)";
                presence "Indicates a radius node is configured.";
                description
                  "Use list of all RADIUS hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must "(../../group-3/local or ../../group-3/tacacs or
                      ../../group-3/radius or ../../group-3/server-group-name)
                      and not(../local or ../tacacs or ../radius)";
                description
                  "server-group name";
              }
            }
          }
        }
      }
      container onepk {
        description
          "Set authentication lists for OnePk";
        list authentication-list {
          key "list-name";
          description
            "List name for AAA authentication";
          leaf list-name {
            type union {
              type string {
                pattern 'default' {
                  description
                    "Default list name for AAA authentication";
                }
              }
              type string {
                length "1..253" {
                  description
                    "List name for AAA authentication.
                     Allowed special chars for tacacs server group are A-Z,a-z,_,.,-,%,=,+,space allowed with backslash,;,:,|,#,$,0-9
                     and for radius server group are _,-,.,;,:,$,#,space allowed with backslash";
                }
              }
            }
            description
              "List name for AAA authentication";
          }
          container local {
            must "not(../groups/group-1/tacacs or
                  ../groups/group-1/radius or
                  ../groups/group-1/server-group-name)";
            presence "Indicates a local node is configured.";
            description
              "Local command accounting using syslog";
          }
          container groups {
            description
              "Use Server-group";
            container group-1 {
              description
                "First server-group";
              container tacacs {
                must 'not(../../../local) and not(../radius or ../server-group-name)';
                presence "Indicates a tacacs node is configured.";
                description
                  "Use list of all TACACS+ hosts";
              }
              container radius {
                must 'not(../../../local) and not(../tacacs or ../server-group-name)';
                presence "Indicates a radius node is configured.";
                description
                  "Use list of all RADIUS hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must 'not(../../../local) and not(../tacacs or ../radius)';
                description
                  "server-group name";
              }
            }
            container group-2 {
              description
                "Second server-group";
              container local {
                must "(../../group-1/tacacs or ../../group-1/radius or
                      ../../group-1/server-group-name) and
                      not(../tacacs or ../radius or ../server-group-name or
                      ../../../local)";
                presence "Indicates a local node is configured.";
                description
                  "Local command accounting using syslog";
              }
              container tacacs {
                must "(../../group-1/radius or ../../group-1/server-group-name or ../../../local)
                      and not(../local or ../radius or ../server-group-name or
                      ../../group-1/tacacs)";
                presence "Indicates a tacacs node is configured.";
                description
                  "Use list of all TACACS+ hosts";
              }
              container radius {
                must "(../../group-1/tacacs or ../../group-1/server-group-name or ../../../local)
                      and not(../local or ../tacacs or ../server-group-name or
                      ../../group-1/radius)";
                presence "Indicates a radius node is configured.";
                description
                  "Use list of all RADIUS hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must "(../../group-1/tacacs or ../../group-1/radius or
                      ../../group-1/server-group-name or ../../../local) and
                      not(../local or ../tacacs or ../radius)";
                description
                  "server-group name";
              }
            }
            container group-3 {
              description
                "Second server-group";
              container local {
                must "(../../group-2/tacacs or ../../group-2/radius or
                      ../../group-2/server-group-name) and
                      not(../tacacs or ../radius or ../server-group-name or
                      ../../group-2/local)";
                presence "Indicates a local node is configured.";
                description
                  "Local command accounting using syslog";
              }
              container tacacs {
                must "(../../group-2/local or ../../group-2/radius or
                      ../../group-2/server-group-name)
                      and not(../local or ../radius or ../server-group-name or
                      ../../group-1/tacacs or ../../group-2/tacacs)";
                presence "Indicates a tacacs node is configured.";
                description
                  "Use list of all TACACS+ hosts";
              }
              container radius {
                must "(../../group-2/local or ../../group-2/tacacs or
                      ../../group-2/server-group-name)
                      and not(../local or ../tacacs or ../server-group-name or
                      ../../group-1/radius or ../../group-2/radius)";
                presence "Indicates a radius node is configured.";
                description
                  "Use list of all RADIUS hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must "(../../group-2/local or ../../group-2/tacacs or
                      ../../group-2/radius or ../../group-2/server-group-name)
                      and not(../local or ../tacacs or ../radius)";
                description
                  "server-group name";
              }
            }
            container group-4 {
              description
                "Second server-group";
              container local {
                must "(../../group-3/tacacs or ../../group-3/radius or
                      ../../group-3/server-group-name) and
                      not(../tacacs or ../radius or ../server-group-name or
                      ../../group-3/local)";
                presence "Indicates a local node is configured.";
                description
                  "Local command accounting using syslog";
              }
              container tacacs {
                must "(../../group-3/local or ../../group-3/radius or
                      ../../group-3/server-group-name) and
                      not(../local or ../radius or ../server-group-name or
                      ../../group-1/tacacs or ../../group-2/tacacs or
                      ../../group-3/tacacs)";
                presence "Indicates a tacacs node is configured.";
                description
                  "Use list of all TACACS+ hosts";
              }
              container radius {
                must "(../../group-3/local or ../../group-3/tacacs or
                      ../../group-3/server-group-name) and
                      not(../local or ../tacacs or ../server-group-name or
                      ../../group-1/radius or ../../group-2/radius or
                      ../../group-3/radius)";
                presence "Indicates a radius node is configured.";
                description
                  "Use list of all RADIUS hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must "(../../group-3/local or ../../group-3/tacacs or
                      ../../group-3/radius or ../../group-3/server-group-name)
                      and not(../local or ../tacacs or ../radius)";
                description
                  "server-group name";
              }
            }
          }
        }
      }
      container login {
        description
          "Set authentication lists for login";
        list authentication-list {
          key "list-name";
          description
            "List name for AAA authentication";
          leaf list-name {
            type union {
              type string {
                pattern 'default' {
                  description
                    "Default list name for AAA authentication";
                }
              }
              type string {
                length "1..253" {
                  description
                    "List name for AAA authentication.
                     Allowed special chars for tacacs server group are A-Z,a-z,_,.,-,%,=,+,space allowed with backslash,;,:,|,#,$,0-9
                     and for radius server group are _,-,.,;,:,$,#,space allowed with backslash";
                }
              }
            }
            description
              "List name for AAA authentication";
          }
          container local {
            must "not(../line or ../groups/group-1/tacacs or
                  ../groups/group-1/radius or
                  ../groups/group-1/server-group-name)";
            presence "Indicates a local node is configured.";
            description
              "Local command accounting using syslog";
          }
          container line {
            must "not(../local or ../groups/group-1/tacacs or
                  ../groups/group-1/radius or
                  ../groups/group-1/server-group-name)";
            presence "Indicates a line node is configured.";
            description
              "Use line password for authentication";
          }
          container groups {
            description
              "Use Server-group";
            container group-1 {
              description
                "First server-group";
              container tacacs {
                must "not(../../../local or ../../../line) and
                      not(../radius or ../server-group-name)";
                presence "Indicates a tacacs node is configured.";
                description
                  "Use list of all TACACS+ hosts";
              }
              container radius {
                must "not(../../../local or ../../../line) and
                      not(../tacacs or ../server-group-name)";
                presence "Indicates a radius node is configured.";
                description
                  "Use list of all RADIUS hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must "not(../../../local or ../../../line) and
                      not(../tacacs or ../radius)";
                description
                  "server-group name";
              }
            }
            container group-2 {
              description
                "Second server-group";
              container local {
                must "(../../group-1/tacacs or ../../group-1/radius or
                      ../../group-1/server-group-name) and
                      not(../line or ../tacacs or ../radius or ../server-group-name or
                      ../../../local)";
                presence "Indicates a local node is configured.";
                description
                  "Local command accounting using syslog";
              }
              container line {
                must "(../../group-1/tacacs or ../../group-1/radius or
                      ../../group-1/server-group-name) and
                      not(../local or ../tacacs or ../radius or
                      ../server-group-name or
                      ../../../line)";
                presence "Indicates a line node is configured.";
                description
                  "Use line password for authentication";
              }
              container tacacs {
                must "(../../group-1/radius or ../../group-1/server-group-name
                      or ../../../local or ../../../line)
                      and not(../local or ../line or ../radius or
                      ../server-group-name or
                      ../../group-1/tacacs)";
                presence "Indicates a tacacs node is configured.";
                description
                  "Use list of all TACACS+ hosts";
              }
              container radius {
                must "(../../group-1/tacacs or ../../group-1/server-group-name
                      or ../../../local or ../../../line)
                      and not(../local or ../line or ../tacacs or
                      ../server-group-name or
                      ../../group-1/radius)";
                presence "Indicates a radius node is configured.";
                description
                  "Use list of all RADIUS hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must "(../../group-1/tacacs or ../../group-1/radius or
                      ../../group-1/server-group-name or ../../../local or ../../../line)
                      and not(../local or ../line or ../tacacs or ../radius)";
                description
                  "server-group name";
              }
            }
            container group-3 {
              description
                "Second server-group";
              container local {
                must "(../../group-2/line or ../../group-2/tacacs or
                      ../../group-2/radius or
                      ../../group-2/server-group-name) and
                      not(../line or ../tacacs or ../radius or
                      ../server-group-name or
                      ../../group-2/local)";
                presence "Indicates a local node is configured.";
                description
                  "Local command accounting using syslog";
              }
              container line {
                must "(../../group-2/local or ../../group-2/tacacs or
                      ../../group-2/radius or
                      ../../group-2/server-group-name) and
                      not(../local or ../tacacs or ../radius or
                      ../server-group-name or
                      ../../group-2/line)";
                presence "Indicates a line node is configured.";
                description
                  "Use line password for authentication";
              }
              container tacacs {
                must "(../../group-2/local or ../../group-2/line or
                      ../../group-2/radius or
                      ../../group-2/server-group-name)
                      and not(../local or ../line or ../radius or
                      ../server-group-name or
                      ../../group-1/tacacs or ../../group-2/tacacs)";
                presence "Indicates a tacacs node is configured.";
                description
                  "Use list of all TACACS+ hosts";
              }
              container radius {
                must "(../../group-2/local or ../../group-2/line or
                      ../../group-2/tacacs or
                      ../../group-2/server-group-name)
                      and not(../local or ../line or ../tacacs or
                      ../server-group-name or
                      ../../group-1/radius or ../../group-2/radius)";
                presence "Indicates a radius node is configured.";
                description
                  "Use list of all RADIUS hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must "(../../group-2/local or ../../group-2/line or
                      ../../group-2/tacacs or
                      ../../group-2/radius or ../../group-2/server-group-name)
                      and not(../local or ../line or ../tacacs or ../radius)";
                description
                  "server-group name";
              }
            }
            container group-4 {
              description
                "Second server-group";
              container local {
                must "(../../group-3/line or ../../group-3/tacacs or
                      ../../group-3/radius or
                      ../../group-3/server-group-name) and
                      not(../line or ../tacacs or ../radius or
                      ../server-group-name or
                      ../../group-3/local)";
                presence "Indicates a local node is configured.";
                description
                  "Local command accounting using syslog";
              }
              container line {
                must "(../../group-3/local or ../../group-3/tacacs or
                      ../../group-3/radius or
                      ../../group-3/server-group-name) and
                      not(../local or ../tacacs or ../radius or
                      ../server-group-name or
                      ../../group-3/line)";
                presence "Indicates a line node is configured.";
                description
                  "Use line password for authentication";
              }
              container tacacs {
                must "(../../group-3/local or ../../group-3/line or
                      ../../group-3/radius or
                      ../../group-3/server-group-name) and
                      not(../local or ../line or ../radius or
                      ../server-group-name or
                      ../../group-1/tacacs or ../../group-2/tacacs or
                      ../../group-3/tacacs)";
                presence "Indicates a tacacs node is configured.";
                description
                  "Use list of all TACACS+ hosts";
              }
              container radius {
                must "(../../group-3/local or ../../group-3/line or
                      ../../group-3/tacacs or
                      ../../group-3/server-group-name) and
                      not(../local or ../line or ../tacacs or
                      ../server-group-name or
                      ../../group-1/radius or ../../group-2/radius or
                      ../../group-3/radius)";
                presence "Indicates a radius node is configured.";
                description
                  "Use list of all RADIUS hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must "(../../group-3/local or ../../group-3/line or
                      ../../group-3/tacacs or ../../group-3/radius or
                      ../../group-3/server-group-name)
                      and not(../local or ../line or ../tacacs or ../radius)";
                description
                  "server-group name";
              }
            }
          }
        }
      }
    }
    container authorization {
      description
        "AAA Authorization data";
      container exec {
        description
          "Set authorization lists for EXEC";
        list authorization-list {
          must "local or none or groups/group-1/tacacs or
                groups/group-1/radius or
                groups/group-1/server-group-name";
          key "list-name";
          description
            "List name for AAA authorization";
          leaf list-name {
            type union {
              type string {
                pattern 'default' {
                  description
                    "Default list name for AAA authorization";
                }
              }
              type string {
                length "1..253" {
                  description
                    "List name for AAA authorization.
                     Allowed special chars for tacacs server group are A-Z,a-z,_,.,-,%,=,+,space allowed with backslash,;,:,|,#,$,0-9
                     and for radius server group are _,-,.,;,:,$,#,space allowed with backslash";
                }
              }
            }
            description
              "List name for AAA authorization";
          }
          container local {
            must "not(../none or ../groups/group-1/tacacs or
                  ../groups/group-1/radius or
                  ../groups/group-1/server-group-name)";
            presence "Indicates a local node is configured.";
            description
              "Local command accounting using syslog";
          }
          container none {
            must "not(../local or ../groups/group-1/tacacs or
                  ../groups/group-1/radius or
                  ../groups/group-1/server-group-name)";
            presence "Indicates a none node is configured.";
            description
              "no authorization";
          }
          container groups {
            description
              "Use Server-group";
            container group-1 {
              description
                "First server-group";
              container tacacs {
                must "not(../../../local or ../../../none) and
                      not(../radius or ../server-group-name)";
                presence "Indicates a tacacs node is configured.";
                description
                  "Use list of all TACACS+ hosts";
              }
              container radius {
                must "not(../../../local or ../../../none) and
                      not(../tacacs or ../server-group-name)";
                presence "Indicates a radius node is configured.";
                description
                  "Use list of all RADIUS hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must "not(../../../local or ../../../none) and
                      not(../tacacs or ../radius)";
                description
                  "server-group name";
              }
            }
            container group-2 {
              description
                "Second server-group";
              container local {
                must "(../../../none or ../../group-1/tacacs or
                      ../../group-1/radius or
                      ../../group-1/server-group-name) and
                      not(../tacacs or ../radius or ../server-group-name or
                      ../../../local or ../none)";
                presence "Indicates a local node is configured.";
                description
                  "Local command accounting using syslog";
              }
              container none {
                must "(../../../local or ../../group-1/tacacs or
                      ../../group-1/radius or
                      ../../group-1/server-group-name) and
                      not(../local or ../tacacs or ../radius or
                      ../server-group-name or
                      ../../../none)";
                presence "Indicates a none node is configured.";
                description
                  "no authorization";
              }
              container tacacs {
                must "(../../../local or ../../group-1/radius or
                      ../../group-1/server-group-name)
                      and not(../local or ../none or ../radius or
                      ../server-group-name or
                      ../../group-1/tacacs)";
                presence "Indicates a tacacs node is configured.";
                description
                  "Use list of all TACACS+ hosts";
              }
              container radius {
                must "(../../../local or ../../group-1/tacacs or
                      ../../group-1/server-group-name)
                      and not(../local or ../none or ../tacacs or
                      ../server-group-name or
                      ../../group-1/radius)";
                presence "Indicates a radius node is configured.";
                description
                  "Use list of all RADIUS hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must "(../../../local or ../../group-1/tacacs or
                      ../../group-1/radius or
                      ../../group-1/server-group-name) and
                      not(../local or ../none or ../tacacs or ../radius)";
                description
                  "server-group name";
              }
            }
            container group-3 {
              description
                "Third server-group";
              container local {
                must "(../../group-2/tacacs or ../../group-2/radius or
                      ../../group-2/server-group-name) and
                      not(../none or ../tacacs or ../radius or
                      ../server-group-name or
                      ../../group-2/local)";
                presence "Indicates a local node is configured.";
                description
                  "Local command accounting using syslog";
              }
              container none {
                must "(../../group-2/tacacs or ../../group-2/radius or
                      ../../group-2/server-group-name or
                      ../../group-2/local) and
                      not(../local or ../tacacs or ../radius or
                      ../server-group-name or
                      ../../group-2/none)";
                presence "Indicates a none node is configured.";
                description
                  "no authorization";
              }
              container tacacs {
                must "(../../group-2/local or
                      ../../group-2/radius or
                      ../../group-2/server-group-name)
                      and not(../local or ../none or ../radius or
                      ../server-group-name or
                      ../../group-1/tacacs or ../../group-2/tacacs)";
                presence "Indicates a tacacs node is configured.";
                description
                  "Use list of all TACACS+ hosts";
              }
              container radius {
                must "(../../group-2/local or
                      ../../group-2/tacacs or
                      ../../group-2/server-group-name)
                      and not(../local or ../none or ../tacacs or
                      ../server-group-name or
                      ../../group-1/radius or ../../group-2/radius)";
                presence "Indicates a radius node is configured.";
                description
                  "Use list of all RADIUS hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must "(../../group-2/local or
                      ../../group-2/tacacs or
                      ../../group-2/radius or ../../group-2/server-group-name)
                      and not(../local or ../none or ../tacacs or ../radius)";
                description
                  "server-group name";
              }
            }
            container group-4 {
              description
                "Second server-group";
              container local {
                must "(../../group-3/none or ../../group-3/tacacs or
                      ../../group-3/radius or
                      ../../group-3/server-group-name) and
                      not(../none or ../tacacs or ../radius or
                      ../server-group-name or
                      ../../group-3/local)";
                presence "Indicates a local node is configured.";
                description
                  "Local command accounting using syslog";
              }
              container none {
                must "(../../group-3/local or ../../group-3/tacacs or
                      ../../group-3/radius or
                      ../../group-3/server-group-name) and
                      not(../local or ../tacacs or ../radius or
                      ../server-group-name or
                      ../../group-3/none)";
                presence "Indicates a none node is configured.";
                description
                  "no authorization";
              }
              container tacacs {
                must "(../../group-3/local or
                      ../../group-3/radius or
                      ../../group-3/server-group-name) and
                      not(../local or ../none or ../radius or
                      ../server-group-name or
                      ../../group-1/tacacs or ../../group-2/tacacs or
                      ../../group-3/tacacs)";
                presence "Indicates a tacacs node is configured.";
                description
                  "Use list of all TACACS+ hosts";
              }
              container radius {
                must "(../../group-3/local or
                      ../../group-3/tacacs or
                      ../../group-3/server-group-name) and
                      not(../local or ../none or ../tacacs or
                      ../server-group-name or
                      ../../group-1/radius or ../../group-2/radius or
                      ../../group-3/radius)";
                presence "Indicates a radius node is configured.";
                description
                  "Use list of all RADIUS hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must "(../../group-3/local or
                      ../../group-3/tacacs or
                      ../../group-3/radius or ../../group-3/server-group-name)
                      and not(../local or ../none or ../tacacs or ../radius)";
                description
                  "server-group name";
              }
            }
          }
        }
      }
      container eventmanager {
        description
          "Set Event Manager authorization method";
        list authorization-list {
          must "local or groups/group-1/tacacs or
                groups/group-1/server-group-name";
          key "list-name";
          description
            "List name for AAA authorization";
          leaf list-name {
            type union {
              type string {
                pattern 'default' {
                  description
                    "Default list name for AAA authorization";
                }
              }
              type string {
                length "1..253" {
                  description
                    "List name for AAA authorization.
                     Allowed special chars for tacacs server group are A-Z,a-z,_,.,-,%,=,+,space allowed with backslash,;,:,|,#,$,0-9
                     and for radius server group are _,-,.,;,:,$,#,space allowed with backslash";
                }
              }
            }
            description
              "List name for AAA authorization";
          }
          container local {
            must "not(../groups/group-1/tacacs or
                  ../groups/group-1/server-group-name)";
            presence "Indicates a local node is configured.";
            description
              "Local command accounting using syslog";
          }
          container groups {
            description
              "Use Server-group";
            container group-1 {
              description
                "First server-group";
              container tacacs {
                must 'not(../../../local) and not(../server-group-name)';
                presence "Indicates a tacacs node is configured.";
                description
                  "Use list of all TACACS+ hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must 'not(../../../local) and not(../tacacs)';
                description
                  "server-group name";
              }
            }
            container group-2 {
              description
                "Second server-group";
              container local {
                must "(../../../local or ../../group-1/tacacs or
                      ../../group-1/server-group-name) and
                      not(../tacacs or ../server-group-name or
                      ../../../local)";
                presence "Indicates a local node is configured.";
                description
                  "Local command accounting using syslog";
              }
              container tacacs {
                must "(../../../local or
                      ../../group-1/server-group-name)
                      and not(../local or ../server-group-name or
                      ../../group-1/tacacs)";
                presence "Indicates a tacacs node is configured.";
                description
                  "Use list of all TACACS+ hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must "(../../../local or ../../group-1/tacacs or
                      ../../group-1/server-group-name) and
                      not(../local or ../tacacs)";
                description
                  "server-group name";
              }
            }
          }
        }
      }
      container commands {
        description
          "For EXEC (shell) commands";
        list authorization-list {
          must "local or none or groups/group-1/tacacs or
                groups/group-1/radius or
                groups/group-1/server-group-name";
          key "list-name";
          description
            "List name for AAA authorization";
          leaf list-name {
            type union {
              type string {
                pattern 'default' {
                  description
                    "Default list name for AAA authorization";
                }
              }
              type string {
                length "1..253" {
                  description
                    "List name for AAA authorization.
                     Allowed special chars for tacacs server group are A-Z,a-z,_,.,-,%,=,+,space allowed with backslash,;,:,|,#,$,0-9
                     and for radius server group are _,-,.,;,:,$,#,space allowed with backslash";
                }
              }
            }
            description
              "List name for AAA authorization";
          }
          container local {
            must 'not(../none)';
            presence "Indicates a local node is configured.";
            description
              "Authorize if authenticated locally";
          }
          container none {
            must "not(../groups/group-1/tacacs or
                  ../groups/group-1/radius or
                  ../groups/group-1/server-group-name)";
            presence "Indicates a none node is configured.";
            description
              "no authorization";
          }
          container groups {
            description
              "Use Server-group";
            container group-1 {
              description
                "First server-group";
              container tacacs {
                must 'not(../../../none) and not(../radius or ../server-group-name)';
                presence "Indicates a tacacs node is configured.";
                description
                  "Use list of all TACACS+ hosts";
              }
              container radius {
                must 'not(../../../none) and not(../tacacs or ../server-group-name)';
                presence "Indicates a radius node is configured.";
                description
                  "Use list of all RADIUS hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must 'not(../../../none) and not(../tacacs or ../radius)';
                description
                  "server-group name";
              }
            }
            container group-2 {
              description
                "Second server-group";
              container none {
                must "(../../group-1/tacacs or ../../group-1/radius or
                      ../../group-1/server-group-name) and
                      not(../tacacs or ../radius or ../server-group-name or
                      ../../../none)";
                presence "Indicates a none node is configured.";
                description
                  "no authorization";
              }
              container tacacs {
                must "(../../group-1/radius or ../../group-1/server-group-name
                      or ../../../local or ../../../none)
                      and not(../none or ../radius or ../server-group-name or
                      ../../group-1/tacacs)";
                presence "Indicates a tacacs node is configured.";
                description
                  "Use list of all TACACS+ hosts";
              }
              container radius {
                must "(../../group-1/tacacs or ../../group-1/server-group-name
                      or ../../../local or ../../../none)
                      and not(../none or ../tacacs or ../server-group-name or
                      ../../group-1/radius)";
                presence "Indicates a radius node is configured.";
                description
                  "Use list of all RADIUS hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must "(../../group-1/tacacs or ../../group-1/radius or
                      ../../group-1/server-group-name or ../../../local or ../../../none)
                      and not(../none or ../tacacs or ../radius)";
                description
                  "server-group name";
              }
            }
            container group-3 {
              description
                "Third server-group";
              container none {
                must "(../../group-2/tacacs or ../../group-2/radius or
                      ../../group-2/server-group-name) and
                      not(../tacacs or ../radius or ../server-group-name or
                      ../../group-2/none)";
                presence "Indicates a none node is configured.";
                description
                  "no authorization";
              }
              container tacacs {
                must "(../../group-2/radius or
                      ../../group-2/server-group-name)
                      and not(../none or ../radius or ../server-group-name or
                      ../../group-1/tacacs or ../../group-2/tacacs)";
                presence "Indicates a tacacs node is configured.";
                description
                  "Use list of all TACACS+ hosts";
              }
              container radius {
                must "(../../group-2/tacacs or
                      ../../group-2/server-group-name)
                      and not(../none or ../tacacs or ../server-group-name or
                      ../../group-1/radius or ../../group-2/radius)";
                presence "Indicates a radius node is configured.";
                description
                  "Use list of all RADIUS hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must "(../../group-2/tacacs or
                      ../../group-2/radius or ../../group-2/server-group-name)
                      and not(../none or ../tacacs or ../radius)";
                description
                  "server-group name";
              }
            }
            container group-4 {
              description
                "Fourth server-group";
              container none {
                must "(../../group-3/tacacs or ../../group-3/radius or
                      ../../group-3/server-group-name) and
                      not(../tacacs or ../radius or ../server-group-name or
                      ../../group-3/none)";
                presence "Indicates a none node is configured.";
                description
                  "no authorization";
              }
              container tacacs {
                must "(../../group-3/radius or
                      ../../group-3/server-group-name) and
                      not(../none or ../radius or ../server-group-name or
                      ../../group-1/tacacs or ../../group-2/tacacs or
                      ../../group-3/tacacs)";
                presence "Indicates a tacacs node is configured.";
                description
                  "Use list of all TACACS+ hosts";
              }
              container radius {
                must "(../../group-3/tacacs or
                      ../../group-3/server-group-name) and
                      not(../none or ../tacacs or ../server-group-name or
                      ../../group-1/radius or ../../group-2/radius or
                      ../../group-3/radius)";
                presence "Indicates a radius node is configured.";
                description
                  "Use list of all RADIUS hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must "(../../group-3/tacacs or
                      ../../group-3/radius or ../../group-3/server-group-name)
                      and not(../none or ../tacacs or ../radius)";
                description
                  "server-group name";
              }
            }
          }
        }
      }
      container onepk {
        description
          "Set authorization lists for ONE-PK";
        list authorization-list {
          must "local or none or groups/group-1/tacacs or
                groups/group-1/radius or
                groups/group-1/server-group-name";
          key "list-name";
          description
            "List name for AAA authorization";
          leaf list-name {
            type union {
              type string {
                pattern 'default' {
                  description
                    "Default list name for AAA authorization";
                }
              }
              type string {
                length "1..253" {
                  description
                    "List name for AAA authorization.
                     Allowed special chars for tacacs server group are A-Z,a-z,_,.,-,%,=,+,space allowed with backslash,;,:,|,#,$,0-9
                     and for radius server group are _,-,.,;,:,$,#,space allowed with backslash";
                }
              }
            }
            description
              "List name for AAA authorization";
          }
          container local {
            must "not(../none or ../groups/group-1/tacacs or
                  ../groups/group-1/radius or
                  ../groups/group-1/server-group-name)";
            presence "Indicates a local node is configured.";
            description
              "Local command accounting using syslog";
          }
          container none {
            must "not(../local or ../groups/group-1/tacacs or
                  ../groups/group-1/radius or
                  ../groups/group-1/server-group-name)";
            presence "Indicates a none node is configured.";
            description
              "no authorization";
          }
          container groups {
            description
              "Use Server-group";
            container group-1 {
              description
                "First server-group";
              container tacacs {
                must "not(../../../local or ../../../none) and
                      not(../radius or ../server-group-name)";
                presence "Indicates a tacacs node is configured.";
                description
                  "Use list of all TACACS+ hosts";
              }
              container radius {
                must "not(../../../local or ../../../none) and
                      not(../tacacs or ../server-group-name)";
                presence "Indicates a radius node is configured.";
                description
                  "Use list of all RADIUS hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must "not(../../../local or ../../../none) and
                      not(../tacacs or ../radius)";
                description
                  "server-group name";
              }
            }
            container group-2 {
              description
                "Second server-group";
              container local {
                must "(../../../none or ../../group-1/tacacs or
                      ../../group-1/radius or
                      ../../group-1/server-group-name) and
                      not(../tacacs or ../radius or ../server-group-name or
                      ../../../local or ../none)";
                presence "Indicates a local node is configured.";
                description
                  "Local command accounting using syslog";
              }
              container none {
                must "(../../../local or ../../group-1/tacacs or
                      ../../group-1/radius or
                      ../../group-1/server-group-name) and
                      not(../local or ../tacacs or ../radius or
                      ../server-group-name or
                      ../../../none)";
                presence "Indicates a none node is configured.";
                description
                  "no authorization";
              }
              container tacacs {
                must "(../../../local or ../../group-1/radius or
                      ../../group-1/server-group-name)
                      and not(../local or ../none or ../radius or
                      ../server-group-name or
                      ../../group-1/tacacs)";
                presence "Indicates a tacacs node is configured.";
                description
                  "Use list of all TACACS+ hosts";
              }
              container radius {
                must "(../../../local or ../../group-1/tacacs or
                      ../../group-1/server-group-name)
                      and not(../local or ../none or ../tacacs or
                      ../server-group-name or
                      ../../group-1/radius)";
                presence "Indicates a radius node is configured.";
                description
                  "Use list of all RADIUS hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must "(../../../local or ../../group-1/tacacs or
                      ../../group-1/radius or
                      ../../group-1/server-group-name) and
                      not(../local or ../none or ../tacacs or ../radius)";
                description
                  "server-group name";
              }
            }
            container group-3 {
              description
                "Third server-group";
              container local {
                must "(../../group-2/tacacs or ../../group-2/radius or
                      ../../group-2/server-group-name) and
                      not(../none or ../tacacs or ../radius or
                      ../server-group-name or
                      ../../group-2/local)";
                presence "Indicates a local node is configured.";
                description
                  "Local command accounting using syslog";
              }
              container none {
                must "(../../group-2/tacacs or ../../group-2/radius or
                      ../../group-2/server-group-name or
                      ../../group-2/local) and
                      not(../local or ../tacacs or ../radius or
                      ../server-group-name or
                      ../../group-2/none)";
                presence "Indicates a none node is configured.";
                description
                  "no authorization";
              }
              container tacacs {
                must "(../../group-2/local or
                      ../../group-2/radius or
                      ../../group-2/server-group-name)
                      and not(../local or ../none or ../radius or
                      ../server-group-name or
                      ../../group-1/tacacs or ../../group-2/tacacs)";
                presence "Indicates a tacacs node is configured.";
                description
                  "Use list of all TACACS+ hosts";
              }
              container radius {
                must "(../../group-2/local or
                      ../../group-2/tacacs or
                      ../../group-2/server-group-name)
                      and not(../local or ../none or ../tacacs or
                      ../server-group-name or
                      ../../group-1/radius or ../../group-2/radius)";
                presence "Indicates a radius node is configured.";
                description
                  "Use list of all RADIUS hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must "(../../group-2/local or
                      ../../group-2/tacacs or
                      ../../group-2/radius or ../../group-2/server-group-name)
                      and not(../local or ../none or ../tacacs or ../radius)";
                description
                  "server-group name";
              }
            }
            container group-4 {
              description
                "Second server-group";
              container local {
                must "(../../group-3/none or ../../group-3/tacacs or
                      ../../group-3/radius or
                      ../../group-3/server-group-name) and
                      not(../none or ../tacacs or ../radius or
                      ../server-group-name or
                      ../../group-3/local)";
                presence "Indicates a local node is configured.";
                description
                  "Local command accounting using syslog";
              }
              container none {
                must "(../../group-3/local or ../../group-3/tacacs or
                      ../../group-3/radius or
                      ../../group-3/server-group-name) and
                      not(../local or ../tacacs or ../radius or
                      ../server-group-name or
                      ../../group-3/none)";
                presence "Indicates a none node is configured.";
                description
                  "no authorization";
              }
              container tacacs {
                must "(../../group-3/local or
                      ../../group-3/radius or
                      ../../group-3/server-group-name) and
                      not(../local or ../none or ../radius or
                      ../server-group-name or
                      ../../group-1/tacacs or ../../group-2/tacacs or
                      ../../group-3/tacacs)";
                presence "Indicates a tacacs node is configured.";
                description
                  "Use list of all TACACS+ hosts";
              }
              container radius {
                must "(../../group-3/local or
                      ../../group-3/tacacs or
                      ../../group-3/server-group-name) and
                      not(../local or ../none or ../tacacs or
                      ../server-group-name or
                      ../../group-1/radius or ../../group-2/radius or
                      ../../group-3/radius)";
                presence "Indicates a radius node is configured.";
                description
                  "Use list of all RADIUS hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must "(../../group-3/local or
                      ../../group-3/tacacs or
                      ../../group-3/radius or ../../group-3/server-group-name)
                      and not(../local or ../none or ../tacacs or ../radius)";
                description
                  "server-group name";
              }
            }
          }
        }
      }
      container nacm {
        description
          "Set authorization lists for NACM";
        list authorization-list {
          must "local or none or groups/group-1/tacacs or
                groups/group-1/server-group-name or
                only-external/local or only-external/none or
                only-external/groups/group-1/tacacs or
                only-external/groups/group-1/server-group-name or
                prefer-external/local or prefer-external/none or
                prefer-external/groups/group-1/tacacs or
                prefer-external/groups/group-1/server-group-name";
          key "list-name";
          description
            "List name for AAA authorization";
          leaf list-name {
            type union {
              type string {
                pattern 'default' {
                  description
                    "Default list name for AAA authorization";
                }
              }
              type string {
                length "1..253" {
                  description
                    "List name for AAA authorization.
                     Allowed special chars for tacacs server group are A-Z,a-z,_,.,-,%,=,+,space allowed with backslash,;,:,|,#,$,0-9
                     and for radius server group are _,-,.,;,:,$,#,space allowed with backslash";
                }
              }
            }
            description
              "List name for AAA authorization";
          }
          container local {
            must "not(../none or ../groups/group-1/tacacs or
                  ../groups/group-1/server-group-name)";
            presence "Indicates a local node is configured.";
            description
              "Local command accounting using syslog";
          }
          container none {
            must "not(../local or ../groups/group-1/tacacs or
                  ../groups/group-1/server-group-name)";
            presence "Indicates a none node is configured.";
            description
              "no authorization";
          }
          container groups {
            description
              "Use Server-group";
            container group-1 {
              description
                "First server-group";
              container tacacs {
                must "not(../../../local or ../../../none) and
                      not(../server-group-name)";
                presence "Indicates a tacacs node is configured.";
                description
                  "Use list of all TACACS+ hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must "not(../../../local or ../../../none) and
                      not(../tacacs)";
                description
                  "server-group name";
              }
            }
            container group-2 {
              description
                "Second server-group";
              container local {
                must "(../../../none or ../../group-1/tacacs or
                      ../../group-1/server-group-name) and
                      not(../tacacs or ../server-group-name or
                      ../../../local or ../none)";
                presence "Indicates a local node is configured.";
                description
                  "Local command accounting using syslog";
              }
              container none {
                must "(../../../local or ../../group-1/tacacs or
                      ../../group-1/server-group-name) and
                      not(../local or ../tacacs or
                      ../server-group-name or
                      ../../../none)";
                presence "Indicates a none node is configured.";
                description
                  "no authorization";
              }
              container tacacs {
                must "(../../../local or
                      ../../group-1/server-group-name)
                      and not(../local or ../none or
                      ../server-group-name or
                      ../../group-1/tacacs)";
                presence "Indicates a tacacs node is configured.";
                description
                  "Use list of all TACACS+ hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must "(../../../local or ../../group-1/tacacs or
                      ../../group-1/server-group-name) and
                      not(../local or ../none or ../tacacs)";
                description
                  "server-group name";
              }
            }
            container group-3 {
              description
                "Third server-group";
              container local {
                must "(../../group-2/tacacs or
                      ../../group-2/server-group-name or
                      ../../group-2/local) and
                      not(../none or ../tacacs or
                      ../server-group-name or
                      ../../group-2/local)";
                presence "Indicates a local node is configured.";
                description
                  "Local command accounting using syslog";
              }
              container none {
                must "(../../group-2/tacacs or
                      ../../group-2/server-group-name) and
                      not(../local or ../tacacs or
                      ../server-group-name or
                      ../../group-2/none)";
                presence "Indicates a none node is configured.";
                description
                  "no authorization";
              }
              container tacacs {
                must "(../../group-2/local or
                      ../../group-2/server-group-name)
                      and not(../local or ../none or
                      ../server-group-name or
                      ../../group-1/tacacs or ../../group-2/tacacs)";
                presence "Indicates a tacacs node is configured.";
                description
                  "Use list of all TACACS+ hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must "(../../group-2/local or
                      ../../group-2/tacacs or
                      ../../group-2/server-group-name)
                      and not(../local or ../none or ../tacacs)";
                description
                  "server-group name";
              }
            }
            container group-4 {
              description
                "Second server-group";
              container local {
                must "(../../group-3/none or ../../group-3/tacacs or
                      ../../group-3/server-group-name) and
                      not(../none or ../tacacs or
                      ../server-group-name or
                      ../../group-3/local)";
                presence "Indicates a local node is configured.";
                description
                  "Local command accounting using syslog";
              }
              container none {
                must "(../../group-3/local or ../../group-3/tacacs or
                      ../../group-3/server-group-name) and
                      not(../local or ../tacacs or
                      ../server-group-name or
                      ../../group-3/none)";
                presence "Indicates a none node is configured.";
                description
                  "no authorization";
              }
              container tacacs {
                must "(../../group-3/local or
                      ../../group-3/server-group-name) and
                      not(../local or ../none or
                      ../server-group-name or
                      ../../group-1/tacacs or ../../group-2/tacacs or
                      ../../group-3/tacacs)";
                presence "Indicates a tacacs node is configured.";
                description
                  "Use list of all TACACS+ hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must "(../../group-3/local or
                      ../../group-3/tacacs or
                      ../../group-3/server-group-name)
                      and not(../local or ../none or ../tacacs)";
                description
                  "server-group name";
              }
            }
          }
          container only-external {
            description
              "only external groups";
            container local {
              must "not(../none or ../groups/group-1/tacacs or
                    ../groups/group-1/server-group-name)";
              presence "Indicates a local node is configured.";
              description
                "Local command accounting using syslog";
            }
            container none {
              must "not(../local or ../groups/group-1/tacacs or
                    ../groups/group-1/server-group-name)";
              presence "Indicates a none node is configured.";
              description
                "no authorization";
            }
            container groups {
              description
                "Use Server-group";
              container group-1 {
                description
                  "First server-group";
                container tacacs {
                  must "not(../../../local or ../../../none) and
                        not(../server-group-name)";
                  presence "Indicates a tacacs node is configured.";
                  description
                    "Use list of all TACACS+ hosts";
                }
                leaf server-group-name {
                  type string {
                    length "1..253" {
                      description
                        "server-group name.
                         Allowed special chars for tacacs server group are A-Z,a-z,_,.,-,%,=,+,space allowed with backslash,;,:,|,#,$,0-9
                         and for radius server group are _,-,.,;,:,$,#,space allowed with backslash";
                    }
                  }
                  must "not(../../../local or ../../../none) and
                        not(../tacacs)";
                  description
                    "server-group name";
                }
              }
              container group-2 {
                description
                  "Second server-group";
                container local {
                  must "(../../../none or ../../group-1/tacacs or
                        ../../group-1/server-group-name) and
                        not(../tacacs or ../server-group-name or
                        ../../../local or ../none)";
                  presence "Indicates a local node is configured.";
                  description
                    "Local command accounting using syslog";
                }
                container none {
                  must "(../../../local or ../../group-1/tacacs or
                        ../../group-1/server-group-name) and
                        not(../local or ../tacacs or
                        ../server-group-name or
                        ../../../none)";
                  presence "Indicates a none node is configured.";
                  description
                    "no authorization";
                }
                container tacacs {
                  must "(../../../local or
                        ../../group-1/server-group-name)
                        and not(../local or ../none or
                        ../server-group-name or
                        ../../group-1/tacacs)";
                  presence "Indicates a tacacs node is configured.";
                  description
                    "Use list of all TACACS+ hosts";
                }
                leaf server-group-name {
                  type string {
                    length "1..253" {
                      description
                        "server-group name.
                         Allowed special chars for tacacs server group are A-Z,a-z,_,.,-,%,=,+,space allowed with backslash,;,:,|,#,$,0-9
                         and for radius server group are _,-,.,;,:,$,#,space allowed with backslash";
                    }
                  }
                  must "(../../../local or ../../group-1/tacacs or
                        ../../group-1/server-group-name) and
                        not(../local or ../none or ../tacacs)";
                  description
                    "server-group name";
                }
              }
              container group-3 {
                description
                  "Third server-group";
                container local {
                  must "(../../group-2/tacacs or
                        ../../group-2/server-group-name) and
                        not(../none or ../tacacs or
                        ../server-group-name or
                        ../../group-2/local)";
                  presence "Indicates a local node is configured.";
                  description
                    "Local command accounting using syslog";
                }
                container none {
                  must "(../../group-2/tacacs or
                        ../../group-2/server-group-name or
                        ../../group-2/local) and
                        not(../local or ../tacacs or
                        ../server-group-name or
                        ../../group-2/none)";
                  presence "Indicates a none node is configured.";
                  description
                    "no authorization";
                }
                container tacacs {
                  must "(../../group-2/local or
                        ../../group-2/server-group-name)
                        and not(../local or ../none or
                        ../server-group-name or
                        ../../group-1/tacacs or ../../group-2/tacacs)";
                  presence "Indicates a tacacs node is configured.";
                  description
                    "Use list of all TACACS+ hosts";
                }
                leaf server-group-name {
                  type string {
                    length "1..253" {
                      description
                        "server-group name.
                         Allowed special chars for tacacs server group are A-Z,a-z,_,.,-,%,=,+,space allowed with backslash,;,:,|,#,$,0-9
                         and for radius server group are _,-,.,;,:,$,#,space allowed with backslash";
                    }
                  }
                  must "(../../group-2/local or
                        ../../group-2/tacacs or
                        ../../group-2/server-group-name)
                        and not(../local or ../none or ../tacacs)";
                  description
                    "server-group name";
                }
              }
              container group-4 {
                description
                  "Second server-group";
                container local {
                  must "(../../group-3/none or ../../group-3/tacacs or
                        ../../group-3/server-group-name) and
                        not(../none or ../tacacs or
                        ../server-group-name or
                        ../../group-3/local)";
                  presence "Indicates a local node is configured.";
                  description
                    "Local command accounting using syslog";
                }
                container none {
                  must "(../../group-3/local or ../../group-3/tacacs or
                        ../../group-3/server-group-name) and
                        not(../local or ../tacacs or
                        ../server-group-name or
                        ../../group-3/none)";
                  presence "Indicates a none node is configured.";
                  description
                    "no authorization";
                }
                container tacacs {
                  must "(../../group-3/local or
                        ../../group-3/server-group-name) and
                        not(../local or ../none or
                        ../server-group-name or
                        ../../group-1/tacacs or ../../group-2/tacacs or
                        ../../group-3/tacacs)";
                  presence "Indicates a tacacs node is configured.";
                  description
                    "Use list of all TACACS+ hosts";
                }
                leaf server-group-name {
                  type string {
                    length "1..253" {
                      description
                        "server-group name.
                         Allowed special chars for tacacs server group are A-Z,a-z,_,.,-,%,=,+,space allowed with backslash,;,:,|,#,$,0-9
                         and for radius server group are _,-,.,;,:,$,#,space allowed with backslash";
                    }
                  }
                  must "(../../group-3/local or
                        ../../group-3/tacacs or
                        ../../group-3/server-group-name)
                        and not(../local or ../none or ../tacacs)";
                  description
                    "server-group name";
                }
              }
            }
          }
          container prefer-external {
            description
              "Prefer external groups with local groups";
            container local {
              must "not(../none or ../groups/group-1/tacacs or
                    ../groups/group-1/server-group-name)";
              presence "Indicates a local node is configured.";
              description
                "Local command accounting using syslog";
            }
            container none {
              must "not(../local or ../groups/group-1/tacacs or
                    ../groups/group-1/server-group-name)";
              presence "Indicates a none node is configured.";
              description
                "no authorization";
            }
            container groups {
              description
                "Use Server-group";
              container group-1 {
                description
                  "First server-group";
                container tacacs {
                  must "not(../../../local or ../../../none) and
                        not(../server-group-name)";
                  presence "Indicates a tacacs node is configured.";
                  description
                    "Use list of all TACACS+ hosts";
                }
                leaf server-group-name {
                  type string {
                    length "1..253" {
                      description
                        "server-group name.
                         Allowed special chars for tacacs server group are A-Z,a-z,_,.,-,%,=,+,space allowed with backslash,;,:,|,#,$,0-9
                         and for radius server group are _,-,.,;,:,$,#,space allowed with backslash";
                    }
                  }
                  must "not(../../../local or ../../../none) and
                        not(../tacacs)";
                  description
                    "server-group name";
                }
              }
              container group-2 {
                description
                  "Second server-group";
                container local {
                  must "(../../../none or ../../group-1/tacacs or
                        ../../group-1/server-group-name) and
                        not(../tacacs or ../server-group-name or
                        ../../../local or ../none)";
                  presence "Indicates a local node is configured.";
                  description
                    "Local command accounting using syslog";
                }
                container none {
                  must "(../../../local or ../../group-1/tacacs or
                        ../../group-1/server-group-name) and
                        not(../local or ../tacacs or
                        ../server-group-name or
                        ../../../none)";
                  presence "Indicates a none node is configured.";
                  description
                    "no authorization";
                }
                container tacacs {
                  must "(../../../local or
                        ../../group-1/server-group-name)
                        and not(../local or ../none or
                        ../server-group-name or
                        ../../group-1/tacacs)";
                  presence "Indicates a tacacs node is configured.";
                  description
                    "Use list of all TACACS+ hosts";
                }
                leaf server-group-name {
                  type string {
                    length "1..253" {
                      description
                        "server-group name.
                         Allowed special chars for tacacs server group are A-Z,a-z,_,.,-,%,=,+,space allowed with backslash,;,:,|,#,$,0-9
                         and for radius server group are _,-,.,;,:,$,#,space allowed with backslash";
                    }
                  }
                  must "(../../../local or ../../group-1/tacacs or
                        ../../group-1/server-group-name) and
                        not(../local or ../none or ../tacacs)";
                  description
                    "server-group name";
                }
              }
              container group-3 {
                description
                  "Third server-group";
                container local {
                  must "(../../group-2/tacacs or
                        ../../group-2/server-group-name) and
                        not(../none or ../tacacs or
                        ../server-group-name or
                        ../../group-2/local)";
                  presence "Indicates a local node is configured.";
                  description
                    "Local command accounting using syslog";
                }
                container none {
                  must "(../../group-2/tacacs or
                        ../../group-2/server-group-name or
                        ../../group-2/local) and
                        not(../local or ../tacacs or
                        ../server-group-name or
                        ../../group-2/none)";
                  presence "Indicates a none node is configured.";
                  description
                    "no authorization";
                }
                container tacacs {
                  must "(../../group-2/local or
                        ../../group-2/server-group-name)
                        and not(../local or ../none or
                        ../server-group-name or
                        ../../group-1/tacacs or ../../group-2/tacacs)";
                  presence "Indicates a tacacs node is configured.";
                  description
                    "Use list of all TACACS+ hosts";
                }
                leaf server-group-name {
                  type string {
                    length "1..253" {
                      description
                        "server-group name.
                         Allowed special chars for tacacs server group are A-Z,a-z,_,.,-,%,=,+,space allowed with backslash,;,:,|,#,$,0-9
                         and for radius server group are _,-,.,;,:,$,#,space allowed with backslash";
                    }
                  }
                  must "(../../group-2/local or
                        ../../group-2/tacacs or
                        ../../group-2/server-group-name)
                        and not(../local or ../none or ../tacacs)";
                  description
                    "server-group name";
                }
              }
              container group-4 {
                description
                  "Second server-group";
                container local {
                  must "(../../group-3/none or ../../group-3/tacacs or
                        ../../group-3/server-group-name) and
                        not(../none or ../tacacs or
                        ../server-group-name or
                        ../../group-3/local)";
                  presence "Indicates a local node is configured.";
                  description
                    "Local command accounting using syslog";
                }
                container none {
                  must "(../../group-3/local or ../../group-3/tacacs or
                        ../../group-3/server-group-name) and
                        not(../local or ../tacacs or
                        ../server-group-name or
                        ../../group-3/none)";
                  presence "Indicates a none node is configured.";
                  description
                    "no authorization";
                }
                container tacacs {
                  must "(../../group-3/local or
                        ../../group-3/server-group-name) and
                        not(../local or ../none or
                        ../server-group-name or
                        ../../group-1/tacacs or ../../group-2/tacacs or
                        ../../group-3/tacacs)";
                  presence "Indicates a tacacs node is configured.";
                  description
                    "Use list of all TACACS+ hosts";
                }
                leaf server-group-name {
                  type string {
                    length "1..253" {
                      description
                        "server-group name.
                         Allowed special chars for tacacs server group are A-Z,a-z,_,.,-,%,=,+,space allowed with backslash,;,:,|,#,$,0-9
                         and for radius server group are _,-,.,;,:,$,#,space allowed with backslash";
                    }
                  }
                  must "(../../group-3/local or
                        ../../group-3/tacacs or
                        ../../group-3/server-group-name)
                        and not(../local or ../none or ../tacacs)";
                  description
                    "server-group name";
                }
              }
            }
          }
        }
      }
      container network {
        description
          "For network services (such as IKE)";
        list authorization-list {
          must "local or none or groups/group-1/tacacs or
                groups/group-1/radius or
                groups/group-1/server-group-name";
          key "list-name";
          description
            "List name for AAA authorization";
          leaf list-name {
            type union {
              type string {
                pattern 'default' {
                  description
                    "Default list name for AAA authorization";
                }
              }
              type string {
                length "1..253" {
                  description
                    "List name for AAA authorization.
                     Allowed special chars for tacacs server group are A-Z,a-z,_,.,-,%,=,+,space allowed with backslash,;,:,|,#,$,0-9
                     and for radius server group are _,-,.,;,:,$,#,space allowed with backslash";
                }
              }
            }
            description
              "List name for AAA authorization";
          }
          container local {
            must "not(../none or ../groups/group-1/tacacs or
                  ../groups/group-1/radius or
                  ../groups/group-1/server-group-name)";
            presence "Indicates a local node is configured.";
            description
              "Local command accounting using syslog";
          }
          container none {
            must "not(../local or ../groups/group-1/tacacs or
                  ../groups/group-1/radius or
                  ../groups/group-1/server-group-name)";
            presence "Indicates a none node is configured.";
            description
              "no authorization";
          }
          container groups {
            description
              "Use Server-group";
            container group-1 {
              description
                "First server-group";
              container tacacs {
                must "not(../../../local or ../../../none) and
                      not(../radius or ../server-group-name)";
                presence "Indicates a tacacs node is configured.";
                description
                  "Use list of all TACACS+ hosts";
              }
              container radius {
                must "not(../../../local or ../../../none) and
                      not(../tacacs or ../server-group-name)";
                presence "Indicates a radius node is configured.";
                description
                  "Use list of all RADIUS hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must "not(../../../local or ../../../none) and
                      not(../tacacs or ../radius)";
                description
                  "server-group name";
              }
            }
            container group-2 {
              description
                "Second server-group";
              container local {
                must "(../../../none or ../../group-1/tacacs or
                      ../../group-1/radius or
                      ../../group-1/server-group-name) and
                      not(../tacacs or ../radius or ../server-group-name or
                      ../../../local or ../none)";
                presence "Indicates a local node is configured.";
                description
                  "Local command accounting using syslog";
              }
              container none {
                must "(../../../local or ../../group-1/tacacs or
                      ../../group-1/radius or
                      ../../group-1/server-group-name) and
                      not(../local or ../tacacs or ../radius or
                      ../server-group-name or
                      ../../../none)";
                presence "Indicates a none node is configured.";
                description
                  "no authorization";
              }
              container tacacs {
                must "(../../../local or ../../group-1/radius or
                      ../../group-1/server-group-name)
                      and not(../local or ../none or ../radius or
                      ../server-group-name or
                      ../../group-1/tacacs)";
                presence "Indicates a tacacs node is configured.";
                description
                  "Use list of all TACACS+ hosts";
              }
              container radius {
                must "(../../../local or ../../group-1/tacacs or
                      ../../group-1/server-group-name)
                      and not(../local or ../none or ../tacacs or
                      ../server-group-name or
                      ../../group-1/radius)";
                presence "Indicates a radius node is configured.";
                description
                  "Use list of all RADIUS hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must "(../../../local or ../../group-1/tacacs or
                      ../../group-1/radius or
                      ../../group-1/server-group-name) and
                      not(../local or ../none or ../tacacs or ../radius)";
                description
                  "server-group name";
              }
            }
            container group-3 {
              description
                "Third server-group";
              container local {
                must "(../../group-2/tacacs or ../../group-2/radius or
                      ../../group-2/server-group-name) and
                      not(../none or ../tacacs or ../radius or
                      ../server-group-name or
                      ../../group-2/local)";
                presence "Indicates a local node is configured.";
                description
                  "Local command accounting using syslog";
              }
              container none {
                must "(../../group-2/tacacs or ../../group-2/radius or
                      ../../group-2/server-group-name or
                      ../../group-2/local) and
                      not(../local or ../tacacs or ../radius or
                      ../server-group-name or
                      ../../group-2/none)";
                presence "Indicates a none node is configured.";
                description
                  "no authorization";
              }
              container tacacs {
                must "(../../group-2/local or
                      ../../group-2/radius or
                      ../../group-2/server-group-name)
                      and not(../local or ../none or ../radius or
                      ../server-group-name or
                      ../../group-1/tacacs or ../../group-2/tacacs)";
                presence "Indicates a tacacs node is configured.";
                description
                  "Use list of all TACACS+ hosts";
              }
              container radius {
                must "(../../group-2/local or
                      ../../group-2/tacacs or
                      ../../group-2/server-group-name)
                      and not(../local or ../none or ../tacacs or
                      ../server-group-name or
                      ../../group-1/radius or ../../group-2/radius)";
                presence "Indicates a radius node is configured.";
                description
                  "Use list of all RADIUS hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must "(../../group-2/local or
                      ../../group-2/tacacs or
                      ../../group-2/radius or ../../group-2/server-group-name)
                      and not(../local or ../none or ../tacacs or ../radius)";
                description
                  "server-group name";
              }
            }
            container group-4 {
              description
                "Second server-group";
              container local {
                must "(../../group-3/none or ../../group-3/tacacs or
                      ../../group-3/radius or
                      ../../group-3/server-group-name) and
                      not(../none or ../tacacs or ../radius or
                      ../server-group-name or
                      ../../group-3/local)";
                presence "Indicates a local node is configured.";
                description
                  "Local command accounting using syslog";
              }
              container none {
                must "(../../group-3/local or ../../group-3/tacacs or
                      ../../group-3/radius or
                      ../../group-3/server-group-name) and
                      not(../local or ../tacacs or ../radius or
                      ../server-group-name or
                      ../../group-3/none)";
                presence "Indicates a none node is configured.";
                description
                  "no authorization";
              }
              container tacacs {
                must "(../../group-3/local or
                      ../../group-3/radius or
                      ../../group-3/server-group-name) and
                      not(../local or ../none or ../radius or
                      ../server-group-name or
                      ../../group-1/tacacs or ../../group-2/tacacs or
                      ../../group-3/tacacs)";
                presence "Indicates a tacacs node is configured.";
                description
                  "Use list of all TACACS+ hosts";
              }
              container radius {
                must "(../../group-3/local or
                      ../../group-3/tacacs or
                      ../../group-3/server-group-name) and
                      not(../local or ../none or ../tacacs or
                      ../server-group-name or
                      ../../group-1/radius or ../../group-2/radius or
                      ../../group-3/radius)";
                presence "Indicates a radius node is configured.";
                description
                  "Use list of all RADIUS hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must "(../../group-3/local or
                      ../../group-3/tacacs or
                      ../../group-3/radius or ../../group-3/server-group-name)
                      and not(../local or ../none or ../tacacs or ../radius)";
                description
                  "server-group name";
              }
            }
          }
        }
      }
    }
    container accounting {
      description
        "AAA Accounting data";
      container update {
        description
          "For starting Network UPDATE accounting";
        container newinfo {
          must 'not(../periodic)';
          presence "Indicates a newinfo node is configured.";
          description
            "Update records for new accountable information only";
        }
        leaf periodic {
          type uint32 {
            range "1..35791394" {
              description
                "Periodic update interval in minutes";
            }
          }
          must 'not(../newinfo)';
          description
            "Update records at periodic intervals";
        }
      }
      container exec {
        description
          "For starting an EXEC (shell)";
        list accounting-list {
          must "(start-stop or stop-only) and (none or
                groups/group-1/tacacs or
                groups/group-1/radius or
                groups/group-1/server-group-name)";
          key "list-name";
          description
            "List name for AAA accounting";
          leaf list-name {
            type union {
              type string {
                pattern 'default' {
                  description
                    "Default list name for AAA accounting";
                }
              }
              type string {
                length "1..253" {
                  description
                    "List name for AAA accounting.
                     Allowed special chars for tacacs server group are A-Z,a-z,_,.,-,%,=,+,space allowed with backslash,;,:,|,#,$,0-9
                     and for radius server group are _,-,.,;,:,$,#,space allowed with backslash";
                }
              }
            }
            description
              "List name for AAA accounting";
          }
          container start-stop {
            must 'not(../stop-only)';
            presence "Indicates a start-stop node is configured.";
            description
              "start and stop records";
          }
          container stop-only {
            must 'not(../start-stop)';
            presence "Indicates a stop-only node is configured.";
            description
              "stop records only";
          }
          container none {
            must "not(../groups/group-1/tacacs or
                  ../groups/group-1/radius or
                  ../groups/group-1/server-group-name)";
            presence "Indicates a none node is configured.";
            description
              "No accounting";
          }
          container groups {
            description
              "Use Server-group";
            container group-1 {
              description
                "First server-group";
              container tacacs {
                must 'not(../../../none) and not(../radius or ../server-group-name)';
                presence "Indicates a tacacs node is configured.";
                description
                  "Use list of all TACACS+ hosts";
              }
              container radius {
                must 'not(../../../none) and not(../tacacs or ../server-group-name)';
                presence "Indicates a radius node is configured.";
                description
                  "Use list of all RADIUS hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must 'not(../../../none) and not(../tacacs or ../radius)';
                description
                  "server-group name";
              }
            }
            container group-2 {
              description
                "Second server-group";
              container none {
                must "(../../group-1/tacacs or ../../group-1/radius or
                      ../../group-1/server-group-name) and
                      not(../tacacs or ../radius or ../server-group-name)";
                presence "Indicates a none node is configured.";
                description
                  "No accounting";
              }
              container tacacs {
                must "(../../group-1/radius or ../../group-1/server-group-name or ../../../none)
                      and not(../none or ../radius or ../server-group-name or
                      ../../group-1/tacacs)";
                presence "Indicates a tacacs node is configured.";
                description
                  "Use list of all TACACS+ hosts";
              }
              container radius {
                must "(../../group-1/tacacs or ../../group-1/server-group-name or ../../../none)
                      and not(../none or ../tacacs or ../server-group-name or
                      ../../group-1/radius)";
                presence "Indicates a radius node is configured.";
                description
                  "Use list of all RADIUS hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must "(../../group-1/tacacs or ../../group-1/radius or
                      ../../group-1/server-group-name or ../../../none) and
                      not(../none or ../tacacs or ../radius)";
                description
                  "server-group name";
              }
            }
            container group-3 {
              description
                "Third server-group";
              container none {
                must "(../../group-2/tacacs or ../../group-2/radius or
                      ../../group-2/server-group-name) and
                      not(../tacacs or ../radius or ../server-group-name or
                      ../../group-2/none)";
                presence "Indicates a none node is configured.";
                description
                  "No accounting";
              }
              container tacacs {
                must "(../../group-2/none or ../../group-2/radius or
                      ../../group-2/server-group-name)
                      and not(../none or ../radius or ../server-group-name or
                      ../../group-1/tacacs or ../../group-2/tacacs)";
                presence "Indicates a tacacs node is configured.";
                description
                  "Use list of all TACACS+ hosts";
              }
              container radius {
                must "(../../group-2/none or ../../group-2/tacacs or
                      ../../group-2/server-group-name)
                      and not(../none or ../tacacs or ../server-group-name or
                      ../../group-1/radius or ../../group-2/radius)";
                presence "Indicates a radius node is configured.";
                description
                  "Use list of all RADIUS hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must "(../../group-2/none or ../../group-2/tacacs or
                      ../../group-2/radius or ../../group-2/server-group-name)
                      and not(../none or ../tacacs or ../radius)";
                description
                  "server-group name";
              }
            }
            container group-4 {
              description
                "Fourth server-group";
              container none {
                must "(../../group-3/tacacs or ../../group-3/radius or
                      ../../group-3/server-group-name) and
                      not(../tacacs or ../radius or ../server-group-name or
                      ../../group-3/none)";
                presence "Indicates a none node is configured.";
                description
                  "No accounting";
              }
              container tacacs {
                must "(../../group-3/none or ../../group-3/radius or
                      ../../group-3/server-group-name) and
                      not(../none or ../radius or ../server-group-name or
                      ../../group-1/tacacs or ../../group-2/tacacs or
                      ../../group-3/tacacs)";
                presence "Indicates a tacacs node is configured.";
                description
                  "Use list of all TACACS+ hosts";
              }
              container radius {
                must "(../../group-3/none or ../../group-3/tacacs or
                      ../../group-3/server-group-name) and
                      not(../none or ../tacacs or ../server-group-name or
                      ../../group-1/radius or ../../group-2/radius or
                      ../../group-3/radius)";
                presence "Indicates a radius node is configured.";
                description
                  "Use list of all RADIUS hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must "(../../group-3/none or ../../group-3/tacacs or
                      ../../group-3/radius or ../../group-3/server-group-name)
                      and not(../none or ../tacacs or ../radius)";
                description
                  "server-group name";
              }
            }
          }
        }
      }
      container commands {
        description
          "For EXEC (shell) commands";
        list accounting-list {
          must "(start-stop or stop-only) and (none or local or
                groups/group-1/tacacs or
                groups/group-1/radius or
                groups/group-1/server-group-name)";
          key "list-name";
          description
            "List name for AAA accounting";
          leaf list-name {
            type union {
              type string {
                pattern 'default' {
                  description
                    "Default list name for AAA accounting";
                }
              }
              type string {
                length "1..253" {
                  description
                    "List name for AAA accounting.
                     Allowed special chars for tacacs server group are A-Z,a-z,_,.,-,%,=,+,space allowed with backslash,;,:,|,#,$,0-9
                     and for radius server group are _,-,.,;,:,$,#,space allowed with backslash";
                }
              }
            }
            description
              "List name for AAA accounting";
          }
          container start-stop {
            must 'not(../stop-only)';
            presence "Indicates a start-stop node is configured.";
            description
              "start and stop records";
          }
          container stop-only {
            must 'not(../start-stop)';
            presence "Indicates a stop-only node is configured.";
            description
              "stop records only";
          }
          container none {
            must "not(../local or ../groups/group-1/tacacs or
                  ../groups/group-1/radius or
                  ../groups/group-1/server-group-name)";
            presence "Indicates a none node is configured.";
            description
              "No accounting";
          }
          container local {
            must "not(../none or ../groups/group-1/tacacs or
                  ../groups/group-1/radius or
                  ../groups/group-1/server-group-name)";
            presence "Indicates a local node is configured.";
            description
              "Local command accounting using syslog";
          }
          container groups {
            description
              "Use Server-group";
            container group-1 {
              description
                "First server-group";
              container tacacs {
                must "not(../../../none or ../../../local) and
                      not(../radius or ../server-group-name)";
                presence "Indicates a tacacs node is configured.";
                description
                  "Use list of all TACACS+ hosts";
              }
              container radius {
                must "not(../../../none or ../../../local) and
                      not(../tacacs or ../server-group-name)";
                presence "Indicates a radius node is configured.";
                description
                  "Use list of all RADIUS hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must "not(../../../none or ../../../local) and
                      not(../tacacs or ../radius)";
                description
                  "server-group name";
              }
            }
            container group-2 {
              description
                "Second server-group";
              container local {
                must "(../../group-1/tacacs or ../../group-1/radius or
                      ../../group-1/server-group-name) and
                      not(../none or ../tacacs or ../radius or
                      ../server-group-name or
                      ../../../local)";
                presence "Indicates a local node is configured.";
                description
                  "Local command accounting using syslog";
              }
              container none {
                must "(../../group-1/tacacs or ../../group-1/radius or
                      ../../group-1/server-group-name) and
                      not(../local or ../tacacs or ../radius or
                      ../server-group-name or
                      ../../../none)";
                presence "Indicates a none node is configured.";
                description
                  "No accounting";
              }
              container tacacs {
                must "(../../group-1/radius or ../../group-1/server-group-name
                      or ../../../local or ../../../none)
                      and not(../local or ../none or ../radius or
                      ../server-group-name or
                      ../../group-1/tacacs)";
                presence "Indicates a tacacs node is configured.";
                description
                  "Use list of all TACACS+ hosts";
              }
              container radius {
                must "(../../group-1/tacacs or ../../group-1/server-group-name
                      or ../../../local or ../../../none)
                      and not(../local or ../none or ../tacacs or
                      ../server-group-name or
                      ../../group-1/radius)";
                presence "Indicates a radius node is configured.";
                description
                  "Use list of all RADIUS hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must "(../../group-1/tacacs or ../../group-1/radius or
                      ../../group-1/server-group-name or ../../../local or ../../../none)
                      and not(../local or ../none or ../tacacs or ../radius)";
                description
                  "server-group name";
              }
            }
            container group-3 {
              description
                "Third server-group";
              container local {
                must "(../../group-2/none or ../../group-2/tacacs or
                      ../../group-2/radius or
                      ../../group-2/server-group-name) and
                      not(../none or ../tacacs or ../radius or
                      ../server-group-name or ../../group-2/local)";
                presence "Indicates a local node is configured.";
                description
                  "Local command accounting using syslog";
              }
              container none {
                must "(../../group-2/local or ../../group-2/tacacs or
                      ../../group-2/radius or
                      ../../group-2/server-group-name) and
                      not(../local or ../tacacs or ../radius or
                      ../server-group-name or ../../group-2/none)";
                presence "Indicates a none node is configured.";
                description
                  "No accounting";
              }
              container tacacs {
                must "(../../group-2/local or ../../group-2/none or
                      ../../group-2/radius or
                      ../../group-2/server-group-name)
                      and not(../local or ../none or ../radius or
                      ../server-group-name or
                      ../../group-1/tacacs or ../../group-2/tacacs)";
                presence "Indicates a tacacs node is configured.";
                description
                  "Use list of all TACACS+ hosts";
              }
              container radius {
                must "(../../group-2/local or ../../group-2/none or
                      ../../group-2/tacacs or
                      ../../group-2/server-group-name)
                      and not(../local or ../none or ../tacacs or
                      ../server-group-name or
                      ../../group-1/radius or ../../group-2/radius)";
                presence "Indicates a radius node is configured.";
                description
                  "Use list of all RADIUS hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must "(../../group-2/local or ../../group-2/none or
                      ../../group-2/tacacs or
                      ../../group-2/radius or ../../group-2/server-group-name)
                      and not(../local or ../none or ../tacacs or ../radius)";
                description
                  "server-group name";
              }
            }
            container group-4 {
              description
                "Second server-group";
              container local {
                must "(../../group-3/none or ../../group-3/tacacs or
                      ../../group-3/radius or
                      ../../group-3/server-group-name) and
                      not(../none or ../tacacs or ../radius or
                      ../server-group-name or
                      ../../group-3/local)";
                presence "Indicates a local node is configured.";
                description
                  "Local command accounting using syslog";
              }
              container none {
                must "(../../group-3/local or ../../group-3/tacacs or
                      ../../group-3/radius or
                      ../../group-3/server-group-name) and
                      not(../local or ../tacacs or ../radius or
                      ../server-group-name or
                      ../../group-3/none)";
                presence "Indicates a none node is configured.";
                description
                  "No accounting";
              }
              container tacacs {
                must "(../../group-3/local or ../../group-3/none or
                      ../../group-3/radius or
                      ../../group-3/server-group-name) and
                      not(../local or ../none or ../radius or
                      ../server-group-name or
                      ../../group-1/tacacs or ../../group-2/tacacs or
                      ../../group-3/tacacs)";
                presence "Indicates a tacacs node is configured.";
                description
                  "Use list of all TACACS+ hosts";
              }
              container radius {
                must "(../../group-3/local or ../../group-3/none or
                      ../../group-3/tacacs or
                      ../../group-3/server-group-name) and
                      not(../local or ../none or ../tacacs or
                      ../server-group-name or
                      ../../group-1/radius or ../../group-2/radius or
                      ../../group-3/radius)";
                presence "Indicates a radius node is configured.";
                description
                  "Use list of all RADIUS hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must "(../../group-3/local or ../../group-3/none or
                      ../../group-3/tacacs or
                      ../../group-3/radius or ../../group-3/server-group-name)
                      and not(../local or ../none or ../tacacs or ../radius)";
                description
                  "server-group name";
              }
            }
          }
        }
      }
      container system {
        description
          "For System events";
        container rp-failover {
          description
            "flag for rp-failover";
          list accounting-list {
            must "(start-stop or stop-only) and (none or groups/group-1/tacacs or
                  groups/group-1/radius or
                  groups/group-1/server-group-name)";
            key "list-name";
            description
              "List name for AAA accounting";
            leaf list-name {
              type union {
                type string {
                  pattern 'default' {
                    description
                      "Default list name for AAA accounting";
                  }
                }
                type string {
                  length "1..253" {
                    description
                      "List name for AAA accounting.
                       Allowed special chars for tacacs server group are A-Z,a-z,_,.,-,%,=,+,space allowed with backslash,;,:,|,#,$,0-9
                       and for radius server group are _,-,.,;,:,$,#,space allowed with backslash";
                  }
                }
              }
              description
                "List name for AAA accounting";
            }
            container start-stop {
              must 'not(../stop-only)';
              presence "Indicates a start-stop node is configured.";
              description
                "start and stop records";
            }
            container stop-only {
              must 'not(../start-stop)';
              presence "Indicates a stop-only node is configured.";
              description
                "stop records only";
            }
            container none {
              must "not(../groups/group-1/tacacs or
                    ../groups/group-1/radius or
                    ../groups/group-1/server-group-name)";
              presence "Indicates a none node is configured.";
              description
                "No accounting";
            }
            container groups {
              description
                "Use Server-group";
              container group-1 {
                description
                  "First server-group";
                container tacacs {
                  must 'not(../../../none) and not(../radius or ../server-group-name)';
                  presence "Indicates a tacacs node is configured.";
                  description
                    "Use list of all TACACS+ hosts";
                }
                container radius {
                  must 'not(../../../none) and not(../tacacs or ../server-group-name)';
                  presence "Indicates a radius node is configured.";
                  description
                    "Use list of all RADIUS hosts";
                }
                leaf server-group-name {
                  type string {
                    length "1..253" {
                      description
                        "server-group name.
                         Allowed special chars for tacacs server group are A-Z,a-z,_,.,-,%,=,+,space allowed with backslash,;,:,|,#,$,0-9
                         and for radius server group are _,-,.,;,:,$,#,space allowed with backslash";
                    }
                  }
                  must 'not(../../../none) and not(../tacacs or ../radius)';
                  description
                    "server-group name";
                }
              }
              container group-2 {
                description
                  "Second server-group";
                container none {
                  must "(../../group-1/tacacs or ../../group-1/radius or
                        ../../group-1/server-group-name) and
                        not(../tacacs or ../radius or ../server-group-name)";
                  presence "Indicates a none node is configured.";
                  description
                    "No accounting";
                }
                container tacacs {
                  must "(../../group-1/radius or ../../group-1/server-group-name
                        or ../../../none)
                        and not(../none or ../radius or ../server-group-name or
                        ../../group-1/tacacs)";
                  presence "Indicates a tacacs node is configured.";
                  description
                    "Use list of all TACACS+ hosts";
                }
                container radius {
                  must "(../../group-1/tacacs or ../../group-1/server-group-name
                        or ../../../none)
                        and not(../none or ../tacacs or ../server-group-name or
                        ../../group-1/radius)";
                  presence "Indicates a radius node is configured.";
                  description
                    "Use list of all RADIUS hosts";
                }
                leaf server-group-name {
                  type string {
                    length "1..253" {
                      description
                        "server-group name.
                         Allowed special chars for tacacs server group are A-Z,a-z,_,.,-,%,=,+,space allowed with backslash,;,:,|,#,$,0-9
                         and for radius server group are _,-,.,;,:,$,#,space allowed with backslash";
                    }
                  }
                  must "(../../group-1/tacacs or ../../group-1/radius or
                        ../../group-1/server-group-name or ../../../none) and
                        not(../none or ../tacacs or ../radius)";
                  description
                    "server-group name";
                }
              }
              container group-3 {
                description
                  "Third server-group";
                container none {
                  must "(../../group-2/tacacs or ../../group-2/radius or
                        ../../group-2/server-group-name) and
                        not(../tacacs or ../radius or ../server-group-name or
                        ../../group-2/none)";
                  presence "Indicates a none node is configured.";
                  description
                    "No accounting";
                }
                container tacacs {
                  must "(../../group-2/none or ../../group-2/radius or
                        ../../group-2/server-group-name)
                        and not(../none or ../radius or ../server-group-name or
                        ../../group-1/tacacs or ../../group-2/tacacs)";
                  presence "Indicates a tacacs node is configured.";
                  description
                    "Use list of all TACACS+ hosts";
                }
                container radius {
                  must "(../../group-2/none or ../../group-2/tacacs or
                        ../../group-2/server-group-name)
                        and not(../none or ../tacacs or ../server-group-name or
                        ../../group-1/radius or ../../group-2/radius)";
                  presence "Indicates a radius node is configured.";
                  description
                    "Use list of all RADIUS hosts";
                }
                leaf server-group-name {
                  type string {
                    length "1..253" {
                      description
                        "server-group name.
                         Allowed special chars for tacacs server group are A-Z,a-z,_,.,-,%,=,+,space allowed with backslash,;,:,|,#,$,0-9
                         and for radius server group are _,-,.,;,:,$,#,space allowed with backslash";
                    }
                  }
                  must "(../../group-2/none or ../../group-2/tacacs or
                        ../../group-2/radius or ../../group-2/server-group-name)
                        and not(../none or ../tacacs or ../radius)";
                  description
                    "server-group name";
                }
              }
              container group-4 {
                description
                  "Fourth server-group";
                container none {
                  must "(../../group-3/none or ../../group-3/tacacs or
                        ../../group-3/radius or
                        ../../group-3/server-group-name) and
                        not(../tacacs or ../radius or ../server-group-name)";
                  presence "Indicates a none node is configured.";
                  description
                    "No accounting";
                }
                container tacacs {
                  must "(../../group-3/none or ../../group-3/radius or
                        ../../group-3/server-group-name) and
                        not(../none or ../radius or ../server-group-name or
                        ../../group-1/tacacs or ../../group-2/tacacs or
                        ../../group-3/tacacs)";
                  presence "Indicates a tacacs node is configured.";
                  description
                    "Use list of all TACACS+ hosts";
                }
                container radius {
                  must "(../../group-3/none or ../../group-3/tacacs or
                        ../../group-3/server-group-name) and
                        not(../none or ../tacacs or ../server-group-name or
                        ../../group-1/radius or ../../group-2/radius or
                        ../../group-3/radius)";
                  presence "Indicates a radius node is configured.";
                  description
                    "Use list of all RADIUS hosts";
                }
                leaf server-group-name {
                  type string {
                    length "1..253" {
                      description
                        "server-group name.
                         Allowed special chars for tacacs server group are A-Z,a-z,_,.,-,%,=,+,space allowed with backslash,;,:,|,#,$,0-9
                         and for radius server group are _,-,.,;,:,$,#,space allowed with backslash";
                    }
                  }
                  must "(../../group-3/none or ../../group-3/tacacs or
                        ../../group-3/radius or ../../group-3/server-group-name)
                        and not(../none or ../tacacs or ../radius)";
                  description
                    "server-group name";
                }
              }
            }
          }
        }
        list accounting-list {
          must "start-stop and (none or
                groups/group-1/tacacs or
                groups/group-1/radius or
                groups/group-1/server-group-name)";
          key "list-name";
          description
            "List name for AAA accounting";
          leaf list-name {
            type union {
              type string {
                pattern 'default' {
                  description
                    "Default list name for AAA accounting";
                }
              }
              type string {
                length "1..253" {
                  description
                    "List name for AAA accounting.
                     Allowed special chars for tacacs server group are A-Z,a-z,_,.,-,%,=,+,space allowed with backslash,;,:,|,#,$,0-9
                     and for radius server group are _,-,.,;,:,$,#,space allowed with backslash";
                }
              }
            }
            description
              "List name for AAA accounting";
          }
          container start-stop {
            presence "Indicates a start-stop node is configured.";
            description
              "start and stop records";
          }
          container broadcast {
            presence "Indicates a broadcast node is configured.";
            description
              "Set broadcast accounting";
          }
          container none {
            must "not(../groups/group-1/tacacs or
                  ../groups/group-1/radius or
                  ../groups/group-1/server-group-name)";
            presence "Indicates a none node is configured.";
            description
              "No accounting";
          }
          container groups {
            description
              "Use Server-group";
            container group-1 {
              description
                "First server-group";
              container tacacs {
                must 'not(../../../none) and not(../radius or ../server-group-name)';
                presence "Indicates a tacacs node is configured.";
                description
                  "Use list of all TACACS+ hosts";
              }
              container radius {
                must 'not(../../../none) and not(../tacacs or ../server-group-name)';
                presence "Indicates a radius node is configured.";
                description
                  "Use list of all RADIUS hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must 'not(../../../none) and not(../tacacs or ../radius)';
                description
                  "server-group name";
              }
            }
            container group-2 {
              description
                "Second server-group";
              container none {
                must "(../../group-1/tacacs or ../../group-1/radius or
                      ../../group-1/server-group-name) and
                      not(../tacacs or ../radius or ../server-group-name)";
                presence "Indicates a none node is configured.";
                description
                  "No accounting";
              }
              container tacacs {
                must "(../../group-1/radius or ../../group-1/server-group-name
                      or ../../../none)
                      and not(../none or ../radius or ../server-group-name or
                      ../../group-1/tacacs)";
                presence "Indicates a tacacs node is configured.";
                description
                  "Use list of all TACACS+ hosts";
              }
              container radius {
                must "(../../group-1/tacacs or ../../group-1/server-group-name
                      or ../../../none)
                      and not(../none or ../tacacs or ../server-group-name or
                      ../../group-1/radius)";
                presence "Indicates a radius node is configured.";
                description
                  "Use list of all RADIUS hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must "(../../group-1/tacacs or ../../group-1/radius or
                      ../../group-1/server-group-name or ../../../none) and
                      not(../none or ../tacacs or ../radius)";
                description
                  "server-group name";
              }
            }
            container group-3 {
              description
                "Third server-group";
              container none {
                must "(../../group-2/tacacs or ../../group-2/radius or
                      ../../group-2/server-group-name) and
                      not(../tacacs or ../radius or ../server-group-name or
                      ../../group-2/none)";
                presence "Indicates a none node is configured.";
                description
                  "No accounting";
              }
              container tacacs {
                must "(../../group-2/none or ../../group-2/radius or
                      ../../group-2/server-group-name)
                      and not(../none or ../radius or ../server-group-name or
                      ../../group-1/tacacs or ../../group-2/tacacs)";
                presence "Indicates a tacacs node is configured.";
                description
                  "Use list of all TACACS+ hosts";
              }
              container radius {
                must "(../../group-2/none or ../../group-2/tacacs or
                      ../../group-2/server-group-name)
                      and not(../none or ../tacacs or ../server-group-name or
                      ../../group-1/radius or ../../group-2/radius)";
                presence "Indicates a radius node is configured.";
                description
                  "Use list of all RADIUS hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must "(../../group-2/none or ../../group-2/tacacs or
                      ../../group-2/radius or ../../group-2/server-group-name)
                      and not(../none or ../tacacs or ../radius)";
                description
                  "server-group name";
              }
            }
            container group-4 {
              description
                "Fourth server-group";
              container none {
                must "(../../group-3/tacacs or ../../group-3/radius or
                      ../../group-3/server-group-name) and
                      not(../tacacs or ../radius or ../server-group-name or
                      ../../group-3/none)";
                presence "Indicates a none node is configured.";
                description
                  "No accounting";
              }
              container tacacs {
                must "(../../group-3/none or ../../group-3/radius or
                      ../../group-3/server-group-name) and
                      not(../none or ../radius or ../server-group-name or
                      ../../group-1/tacacs or ../../group-2/tacacs or
                      ../../group-3/tacacs)";
                presence "Indicates a tacacs node is configured.";
                description
                  "Use list of all TACACS+ hosts";
              }
              container radius {
                must "(../../group-3/none or ../../group-3/tacacs or
                      ../../group-3/server-group-name) and
                      not(../none or ../tacacs or ../server-group-name or
                      ../../group-1/radius or ../../group-2/radius or
                      ../../group-3/radius)";
                presence "Indicates a radius node is configured.";
                description
                  "Use list of all RADIUS hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must "(../../group-3/none or ../../group-3/tacacs or
                      ../../group-3/radius or ../../group-3/server-group-name)
                      and not(../none or ../tacacs or ../radius)";
                description
                  "server-group name";
              }
            }
          }
        }
      }
      container network {
        description
          "For network services (such as IKE, PPP)";
        list accounting-list {
          must "(start-stop or stop-only) and (none or
                groups/group-1/tacacs or
                groups/group-1/radius or
                groups/group-1/server-group-name)";
          key "list-name";
          description
            "List name for AAA accounting";
          leaf list-name {
            type union {
              type string {
                pattern 'default' {
                  description
                    "Default list name for AAA accounting";
                }
              }
              type string {
                length "1..253" {
                  description
                    "List name for AAA accounting.
                     Allowed special chars for tacacs server group are A-Z,a-z,_,.,-,%,=,+,space allowed with backslash,;,:,|,#,$,0-9
                     and for radius server group are _,-,.,;,:,$,#,space allowed with backslash";
                }
              }
            }
            description
              "List name for AAA accounting";
          }
          container start-stop {
            must 'not(../stop-only)';
            presence "Indicates a start-stop node is configured.";
            description
              "start and stop records";
          }
          container stop-only {
            must 'not(../start-stop)';
            presence "Indicates a stop-only node is configured.";
            description
              "stop records only";
          }
          container none {
            must "not(../groups/group-1/tacacs or
                  ../groups/group-1/radius or
                  ../groups/group-1/server-group-name)";
            presence "Indicates a none node is configured.";
            description
              "No accounting";
          }
          container groups {
            description
              "Use Server-group";
            container group-1 {
              description
                "First server-group";
              container tacacs {
                must 'not(../../../none) and not(../radius or ../server-group-name)';
                presence "Indicates a tacacs node is configured.";
                description
                  "Use list of all TACACS+ hosts";
              }
              container radius {
                must 'not(../../../none) and not(../tacacs or ../server-group-name)';
                presence "Indicates a radius node is configured.";
                description
                  "Use list of all RADIUS hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must 'not(../../../none) and not(../tacacs or ../radius)';
                description
                  "server-group name";
              }
            }
            container group-2 {
              description
                "Second server-group";
              container none {
                must "(../../group-1/tacacs or ../../group-1/radius or
                      ../../group-1/server-group-name) and
                      not(../tacacs or ../radius or ../server-group-name)";
                presence "Indicates a none node is configured.";
                description
                  "No accounting";
              }
              container tacacs {
                must "(../../group-1/radius or ../../group-1/server-group-name
                      or ../../../none)
                      and not(../none or ../radius or ../server-group-name or
                      ../../group-1/tacacs)";
                presence "Indicates a tacacs node is configured.";
                description
                  "Use list of all TACACS+ hosts";
              }
              container radius {
                must "(../../group-1/tacacs or ../../group-1/server-group-name
                      or ../../../none)
                      and not(../none or ../tacacs or ../server-group-name or
                      ../../group-1/radius)";
                presence "Indicates a radius node is configured.";
                description
                  "Use list of all RADIUS hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must "(../../group-1/tacacs or ../../group-1/radius or
                      ../../group-1/server-group-name or ../../../none) and
                      not(../none or ../tacacs or ../radius)";
                description
                  "server-group name";
              }
            }
            container group-3 {
              description
                "Third server-group";
              container none {
                must "(../../group-2/tacacs or ../../group-2/radius or
                      ../../group-2/server-group-name) and
                      not(../tacacs or ../radius or ../server-group-name or
                      ../../group-2/none)";
                presence "Indicates a none node is configured.";
                description
                  "No accounting";
              }
              container tacacs {
                must "(../../group-2/none or ../../group-2/radius or
                      ../../group-2/server-group-name)
                      and not(../none or ../radius or ../server-group-name or
                      ../../group-1/tacacs or ../../group-2/tacacs)";
                presence "Indicates a tacacs node is configured.";
                description
                  "Use list of all TACACS+ hosts";
              }
              container radius {
                must "(../../group-2/none or ../../group-2/tacacs or
                      ../../group-2/server-group-name)
                      and not(../none or ../tacacs or ../server-group-name or
                      ../../group-1/radius or ../../group-2/radius)";
                presence "Indicates a radius node is configured.";
                description
                  "Use list of all RADIUS hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must "(../../group-2/none or ../../group-2/tacacs or
                      ../../group-2/radius or ../../group-2/server-group-name)
                      and not(../none or ../tacacs or ../radius)";
                description
                  "server-group name";
              }
            }
            container group-4 {
              description
                "Fourth server-group";
              container none {
                must "(../../group-3/tacacs or ../../group-3/radius or
                      ../../group-3/server-group-name) and
                      not(../tacacs or ../radius or ../server-group-name or
                      ../../group-3/none)";
                presence "Indicates a none node is configured.";
                description
                  "No accounting";
              }
              container tacacs {
                must "(../../group-3/none or ../../group-3/radius or
                      ../../group-3/server-group-name) and
                      not(../none or ../radius or ../server-group-name or
                      ../../group-1/tacacs or ../../group-2/tacacs or
                      ../../group-3/tacacs)";
                presence "Indicates a tacacs node is configured.";
                description
                  "Use list of all TACACS+ hosts";
              }
              container radius {
                must "(../../group-3/none or ../../group-3/tacacs or
                      ../../group-3/server-group-name) and
                      not(../none or ../tacacs or ../server-group-name or
                      ../../group-1/radius or ../../group-2/radius or
                      ../../group-3/radius)";
                presence "Indicates a radius node is configured.";
                description
                  "Use list of all RADIUS hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must "(../../group-3/none or ../../group-3/tacacs or
                      ../../group-3/radius or ../../group-3/server-group-name)
                      and not(../none or ../tacacs or ../radius)";
                description
                  "server-group name";
              }
            }
          }
        }
      }
      container onepk {
        description
          "For ONE-PK services";
        list accounting-list {
          must "(start-stop or stop-only) and (none or
                groups/group-1/tacacs or
                groups/group-1/radius or
                groups/group-1/server-group-name)";
          key "list-name";
          description
            "List name for AAA accounting";
          leaf list-name {
            type union {
              type string {
                pattern 'default' {
                  description
                    "Default list name for AAA accounting";
                }
              }
              type string {
                length "1..253" {
                  description
                    "List name for AAA accounting.
                     Allowed special chars for tacacs server group are A-Z,a-z,_,.,-,%,=,+,space allowed with backslash,;,:,|,#,$,0-9
                     and for radius server group are _,-,.,;,:,$,#,space allowed with backslash";
                }
              }
            }
            description
              "List name for AAA accounting";
          }
          container start-stop {
            must 'not(../stop-only)';
            presence "Indicates a start-stop node is configured.";
            description
              "start and stop records";
          }
          container stop-only {
            must 'not(../start-stop)';
            presence "Indicates a stop-only node is configured.";
            description
              "stop records only";
          }
          container none {
            must "not(../groups/group-1/tacacs or
                  ../groups/group-1/radius or
                  ../groups/group-1/server-group-name)";
            presence "Indicates a none node is configured.";
            description
              "No accounting";
          }
          container groups {
            description
              "Use Server-group";
            container group-1 {
              description
                "First server-group";
              container tacacs {
                must 'not(../../../none) and not(../radius or ../server-group-name)';
                presence "Indicates a tacacs node is configured.";
                description
                  "Use list of all TACACS+ hosts";
              }
              container radius {
                must 'not(../../../none) and not(../tacacs or ../server-group-name)';
                presence "Indicates a radius node is configured.";
                description
                  "Use list of all RADIUS hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must 'not(../../../none) and not(../tacacs or ../radius)';
                description
                  "server-group name";
              }
            }
            container group-2 {
              description
                "Second server-group";
              container none {
                must "(../../group-1/tacacs or ../../group-1/radius or
                      ../../group-1/server-group-name) and
                      not(../tacacs or ../radius or ../server-group-name)";
                presence "Indicates a none node is configured.";
                description
                  "No accounting";
              }
              container tacacs {
                must "(../../group-1/radius or ../../group-1/server-group-name
                      or ../../../none)
                      and not(../none or ../radius or ../server-group-name or
                      ../../group-1/tacacs)";
                presence "Indicates a tacacs node is configured.";
                description
                  "Use list of all TACACS+ hosts";
              }
              container radius {
                must "(../../group-1/tacacs or ../../group-1/server-group-name
                      or ../../../none)
                      and not(../none or ../tacacs or ../server-group-name or
                      ../../group-1/radius)";
                presence "Indicates a radius node is configured.";
                description
                  "Use list of all RADIUS hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must "(../../group-1/tacacs or ../../group-1/radius or
                      ../../group-1/server-group-name or ../../../none) and
                      not(../none or ../tacacs or ../radius)";
                description
                  "server-group name";
              }
            }
            container group-3 {
              description
                "Third server-group";
              container none {
                must "(../../group-2/tacacs or ../../group-2/radius or
                      ../../group-2/server-group-name) and
                      not(../tacacs or ../radius or ../server-group-name or
                      ../../group-2/none)";
                presence "Indicates a none node is configured.";
                description
                  "No accounting";
              }
              container tacacs {
                must "(../../group-2/none or ../../group-2/radius or
                      ../../group-2/server-group-name)
                      and not(../none or ../radius or ../server-group-name or
                      ../../group-1/tacacs or ../../group-2/tacacs)";
                presence "Indicates a tacacs node is configured.";
                description
                  "Use list of all TACACS+ hosts";
              }
              container radius {
                must "(../../group-2/none or ../../group-2/tacacs or
                      ../../group-2/server-group-name)
                      and not(../none or ../tacacs or ../server-group-name or
                      ../../group-1/radius or ../../group-2/radius)";
                presence "Indicates a radius node is configured.";
                description
                  "Use list of all RADIUS hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must "(../../group-2/none or ../../group-2/tacacs or
                      ../../group-2/radius or ../../group-2/server-group-name)
                      and not(../none or ../tacacs or ../radius)";
                description
                  "server-group name";
              }
            }
            container group-4 {
              description
                "Fourth server-group";
              container none {
                must "(../../group-3/tacacs or ../../group-3/radius or
                      ../../group-3/server-group-name) and
                      not(../tacacs or ../radius or ../server-group-name or
                      ../../group-3/none)";
                presence "Indicates a none node is configured.";
                description
                  "No accounting";
              }
              container tacacs {
                must "(../../group-3/none or ../../group-3/radius or
                      ../../group-3/server-group-name) and
                      not(../none or ../radius or ../server-group-name or
                      ../../group-1/tacacs or ../../group-2/tacacs or
                      ../../group-3/tacacs)";
                presence "Indicates a tacacs node is configured.";
                description
                  "Use list of all TACACS+ hosts";
              }
              container radius {
                must "(../../group-3/none or ../../group-3/tacacs or
                      ../../group-3/server-group-name) and
                      not(../none or ../tacacs or ../server-group-name or
                      ../../group-1/radius or ../../group-2/radius or
                      ../../group-3/radius)";
                presence "Indicates a radius node is configured.";
                description
                  "Use list of all RADIUS hosts";
              }
              leaf server-group-name {
                type string {
                  length "1..253" {
                    description
                      "server-group name.
                       Allowed special chars for tacacs server group are A-Z,a-z,_,.,-,%,=,+,space allowed with backslash,;,:,|,#,$,0-9
                       and for radius server group are _,-,.,;,:,$,#,space allowed with backslash";
                  }
                }
                must "(../../group-3/none or ../../group-3/tacacs or
                      ../../group-3/radius or ../../group-3/server-group-name)
                      and not(../none or ../tacacs or ../radius)";
                description
                  "server-group name";
              }
            }
          }
        }
      }
    }
    container banner {
      description
        "AAA banner";
      leaf login {
        type string;
        description
          "c banner-text c, where 'c' is a delimiting character";
      }
    }
  }
}
