module Cisco-IOS-XR-um-ftp-tftp-cfg {

  /*** NAMESPACE / PREFIX DEFINITION ***/

  namespace "http://cisco.com/ns/yang/Cisco-IOS-XR-um-ftp-tftp-cfg";
  prefix um-ftp-tftp-cfg;

  /*** LINKAGE (IMPORTS / INCLUDES) ***/

  import Cisco-IOS-XR-types {
    prefix xr;
  }

  import cisco-semver { prefix "semver"; }

  /*** META INFORMATION ***/

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ftp-tftp package configuration.

     This YANG module augments the
     modules with configuration data.

     Copyright (c) 2020-2022 by Cisco Systems, Inc.
     All rights reserved.";

  revision 2021-05-12 {
    description
      "Add the must statement to the vrf list";
    semver:module-version "1.0.0";
  }

  revision "2020-12-14" {
    description
      "Initial release";
  }

  container ftp {
    description
      "Global FTP configuration commands";
    container client {
      description
        "FTP client configuration commands";
      container vrfs {
        description
          "VRF name for FTP service";
        list vrf {
          must 'passive or source-interface or anonymous-password or username or password/encrypted';
          key "vrf-name";
          description
            "VRF name for FTP service";
          leaf vrf-name {
            type xr:Cisco-ios-xr-string {
              length "1..32" {
                description
                  "Name of VRF";
              }
            }
            description
              "VRF name for FTP service";
          }
          container passive {
            presence "Indicates a passive node is configured.";
            description
              "Connect using passive mode";
          }
          leaf source-interface {
            type xr:Interface-name;
            description
              "Specify interface for source address in FTP connections";
          }
          leaf anonymous-password {
            type xr:Proprietary-password;
            description
              "Specify a password for anonymous users";
          }
          leaf username {
            type xr:Cisco-ios-xr-string {
              length "1..800" {
                description
                  "FTP username";
              }
            }
            description
              "Specify username for FTP connections";
          }
          container password {
            description
              "Specify password for ftp connection";
            leaf encrypted {
              type xr:Proprietary-password;
              description
                "Specify an encrypted password";
            }
          }
        }
      }
    }
  }
  container tftp {
    description
      "Global TFTP configuration commands";
    container vrfs {
      description
        "VRF name for TFTP service";
      list vrf {
        must 'ipv4/server/access-list or ipv4/server/max-servers or ipv4/server/dscp or ipv4/server/homedir or
ipv6/server/access-list or ipv6/server/max-servers or ipv6/server/dscp or ipv6/server/homedir';
        key "vrf-name";
        description
          "VRF name for TFTP service";
        leaf vrf-name {
          type xr:Cisco-ios-xr-string {
            length "1..32" {
              description
                "Name of VRF";
            }
          }
          description
            "VRF name for TFTP service";
        }
        container ipv4 {
          description
            "Ipv4";
          container server {
            description
              "server";
            leaf access-list {
              type xr:Cisco-ios-xr-string {
                length "1..64" {
                  description
                    "Access list - Maximum 64 characters";
                }
              }
              must '../homedir';
              description
                "Access list";
            }
            leaf max-servers {
              type union {
                type enumeration {
                  enum no-limit {
                    value 0;
                    description
                      "No limit to number of allowable UDP max servers";
                  }
                }
                type uint32 {
                  range "1..2147483647";
                }
              }
              must '../homedir';
              description
                "Set number of allowable UDP max servers";
            }
            leaf homedir {
              type string {
                length "1..64" {
                  description
                    "Access list - Maximum 64 characters";
                }
              }
              description
                "home directory";
            }
            leaf dscp {
              type union {
                type uint32 {
                  range "0..63" {
                    description
                      "Differentiated services codepoint value";
                  }
                }
                type enumeration {
                  enum default {
                    value 0;
                    description
                      "Match packets with default dscp (000000)";
                  }
                  enum cs1 {
                    value 8;
                    description
                      "Match packets with CS1(precedence 1) dscp (001000)";
                  }
                  enum af11 {
                    value 10;
                    description
                      "Match packets with AF11 dscp (001010)";
                  }
                  enum af12 {
                    value 12;
                    description
                      "Match packets with AF12 dscp (001100)";
                  }
                  enum af13 {
                    value 14;
                    description
                      "Match packets with AF13 dscp (001110)";
                  }
                  enum cs2 {
                    value 16;
                    description
                      "Match packets with CS2(precedence 2) dscp (010000)";
                  }
                  enum af21 {
                    value 18;
                    description
                      "Match packets with AF21 dscp (010010)";
                  }
                  enum af22 {
                    value 20;
                    description
                      "Match packets with AF22 dscp (010100)";
                  }
                  enum af23 {
                    value 22;
                    description
                      "Match packets with AF23 dscp (010110)";
                  }
                  enum cs3 {
                    value 24;
                    description
                      "Match packets with CS3(precedence 3) dscp (011000)";
                  }
                  enum af31 {
                    value 26;
                    description
                      "Match packets with AF31 dscp (011010)";
                  }
                  enum af32 {
                    value 28;
                    description
                      "Match packets with AF32 dscp (011100)";
                  }
                  enum af33 {
                    value 30;
                    description
                      "Match packets with AF33 dscp (011110)";
                  }
                  enum cs4 {
                    value 32;
                    description
                      "Match packets with CS4(precedence 4) dscp (100000)";
                  }
                  enum af41 {
                    value 34;
                    description
                      "Match packets with AF41 dscp (100010)";
                  }
                  enum af42 {
                    value 36;
                    description
                      "Match packets with AF42 dscp (100100)";
                  }
                  enum af43 {
                    value 38;
                    description
                      "Match packets with AF43 dscp (100110)";
                  }
                  enum cs5 {
                    value 40;
                    description
                      "Match packets with CS5(precedence 5) dscp (101000)";
                  }
                  enum ef {
                    value 46;
                    description
                      "Match packets with EF dscp (101110)";
                  }
                  enum cs6 {
                    value 48;
                    description
                      "Match packets with CS6(precedence 6) dscp (110000)";
                  }
                  enum cs7 {
                    value 56;
                    description
                      "Match packets with CS7(precedence 7) dscp (111000)";
                  }
                }
              }
              must '../homedir';
              description
                "Set IP DSCP (DiffServ CodePoint) for TFTP Server Packets af11 ...";
            }
          }
        }
        container ipv6 {
          description
            "Ipv6";
          container server {
            description
              "server";
            leaf access-list {
              type xr:Cisco-ios-xr-string {
                length "1..64" {
                  description
                    "Access list - Maximum 64 characters";
                }
              }
              must '../homedir';
              description
                "Access list";
            }
            leaf max-servers {
              type union {
                type enumeration {
                  enum no-limit {
                    value 0;
                    description
                      "No limit to number of allowable UDP max servers";
                  }
                }
                type uint32 {
                  range "1..2147483647";
                }
              }
              must '../homedir';
              description
                "Set number of allowable UDP max servers";
            }
            leaf homedir {
              type string {
                length "1..64" {
                  description
                    "Access list - Maximum 64 characters";
                }
              }
              description
                "home directory";
            }
            leaf dscp {
              type union {
                type uint32 {
                  range "0..63" {
                    description
                      "Differentiated services codepoint value";
                  }
                }
                type enumeration {
                  enum default {
                    value 0;
                    description
                      "Match packets with default dscp (000000)";
                  }
                  enum cs1 {
                    value 8;
                    description
                      "Match packets with CS1(precedence 1) dscp (001000)";
                  }
                  enum af11 {
                    value 10;
                    description
                      "Match packets with AF11 dscp (001010)";
                  }
                  enum af12 {
                    value 12;
                    description
                      "Match packets with AF12 dscp (001100)";
                  }
                  enum af13 {
                    value 14;
                    description
                      "Match packets with AF13 dscp (001110)";
                  }
                  enum cs2 {
                    value 16;
                    description
                      "Match packets with CS2(precedence 2) dscp (010000)";
                  }
                  enum af21 {
                    value 18;
                    description
                      "Match packets with AF21 dscp (010010)";
                  }
                  enum af22 {
                    value 20;
                    description
                      "Match packets with AF22 dscp (010100)";
                  }
                  enum af23 {
                    value 22;
                    description
                      "Match packets with AF23 dscp (010110)";
                  }
                  enum cs3 {
                    value 24;
                    description
                      "Match packets with CS3(precedence 3) dscp (011000)";
                  }
                  enum af31 {
                    value 26;
                    description
                      "Match packets with AF31 dscp (011010)";
                  }
                  enum af32 {
                    value 28;
                    description
                      "Match packets with AF32 dscp (011100)";
                  }
                  enum af33 {
                    value 30;
                    description
                      "Match packets with AF33 dscp (011110)";
                  }
                  enum cs4 {
                    value 32;
                    description
                      "Match packets with CS4(precedence 4) dscp (100000)";
                  }
                  enum af41 {
                    value 34;
                    description
                      "Match packets with AF41 dscp (100010)";
                  }
                  enum af42 {
                    value 36;
                    description
                      "Match packets with AF42 dscp (100100)";
                  }
                  enum af43 {
                    value 38;
                    description
                      "Match packets with AF43 dscp (100110)";
                  }
                  enum cs5 {
                    value 40;
                    description
                      "Match packets with CS5(precedence 5) dscp (101000)";
                  }
                  enum ef {
                    value 46;
                    description
                      "Match packets with EF dscp (101110)";
                  }
                  enum cs6 {
                    value 48;
                    description
                      "Match packets with CS6(precedence 6) dscp (110000)";
                  }
                  enum cs7 {
                    value 56;
                    description
                      "Match packets with CS7(precedence 7) dscp (111000)";
                  }
                }
              }
              must '../homedir';
              description
                "Set IP DSCP (DiffServ CodePoint) for TFTP Server Packets af11 ...";
            }
          }
        }
      }
    }
  }
  container tftp-fs {
    description
      "Global TFTP configuration commands";
    container client {
      description
        "TFTP client configuration commands";
      container vrfs {
        description
          "VRF name for TFTP service";
        list vrf {
          must 'source-interface or retries or timeout or dscp';
          key "vrf-name";
          description
            "VRF name for TFTP service";
          leaf vrf-name {
            type xr:Cisco-ios-xr-string {
              length "1..32" {
                description
                  "Name of VRF";
              }
            }
            description
              "VRF name for TFTP service";
          }
          leaf source-interface {
            type xr:Interface-name;
            description
              "Specify interface for source address in TFTP connections";
          }
          leaf retries {
            type uint32 {
              range "0..256" {
                description
                  " TFTP initial maximum retry times";
              }
            }
            description
              "Specify the number of retries when client requests TFTP connections";
          }
          leaf timeout {
            type uint32 {
              range "0..256" {
                description
                  " TFTP initial maximum timeout ";
              }
            }
            description
              "Specify the timeout for every TFTP connection in seconds";
          }
          leaf dscp {
            type union {
              type uint32 {
                range "0..63" {
                  description
                    "Differentiated services codepoint value";
                }
              }
              type enumeration {
                enum default {
                  value 0;
                  description
                    "Match packets with default dscp (000000)";
                }
                enum cs1 {
                  value 8;
                  description
                    "Match packets with CS1(precedence 1) dscp (001000)";
                }
                enum af11 {
                  value 10;
                  description
                    "Match packets with AF11 dscp (001010)";
                }
                enum af12 {
                  value 12;
                  description
                    "Match packets with AF12 dscp (001100)";
                }
                enum af13 {
                  value 14;
                  description
                    "Match packets with AF13 dscp (001110)";
                }
                enum cs2 {
                  value 16;
                  description
                    "Match packets with CS2(precedence 2) dscp (010000)";
                }
                enum af21 {
                  value 18;
                  description
                    "Match packets with AF21 dscp (010010)";
                }
                enum af22 {
                  value 20;
                  description
                    "Match packets with AF22 dscp (010100)";
                }
                enum af23 {
                  value 22;
                  description
                    "Match packets with AF23 dscp (010110)";
                }
                enum cs3 {
                  value 24;
                  description
                    "Match packets with CS3(precedence 3) dscp (011000)";
                }
                enum af31 {
                  value 26;
                  description
                    "Match packets with AF31 dscp (011010)";
                }
                enum af32 {
                  value 28;
                  description
                    "Match packets with AF32 dscp (011100)";
                }
                enum af33 {
                  value 30;
                  description
                    "Match packets with AF33 dscp (011110)";
                }
                enum cs4 {
                  value 32;
                  description
                    "Match packets with CS4(precedence 4) dscp (100000)";
                }
                enum af41 {
                  value 34;
                  description
                    "Match packets with AF41 dscp (100010)";
                }
                enum af42 {
                  value 36;
                  description
                    "Match packets with AF42 dscp (100100)";
                }
                enum af43 {
                  value 38;
                  description
                    "Match packets with AF43 dscp (100110)";
                }
                enum cs5 {
                  value 40;
                  description
                    "Match packets with CS5(precedence 5) dscp (101000)";
                }
                enum ef {
                  value 46;
                  description
                    "Match packets with EF dscp (101110)";
                }
                enum cs6 {
                  value 48;
                  description
                    "Match packets with CS6(precedence 6) dscp (110000)";
                }
                enum cs7 {
                  value 56;
                  description
                    "Match packets with CS7(precedence 7) dscp (111000)";
                }
              }
            }
            description
              "Set IP DSCP (DiffServ CodePoint) for TFTP Client Packets";
          }
        }
      }
    }
  }
}
