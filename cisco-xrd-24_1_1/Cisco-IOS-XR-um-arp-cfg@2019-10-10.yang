module Cisco-IOS-XR-um-arp-cfg {

  /*** NAMESPACE / PREFIX DEFINITION ***/

  namespace "http://cisco.com/ns/yang/Cisco-IOS-XR-um-arp-cfg";
  prefix um-arp-cfg;

  /*** LINKAGE (IMPORTS / INCLUDES) ***/

  import cisco-semver {
    prefix semver;
  }
  import Cisco-IOS-XR-types {
    prefix xr;
  }
  import ietf-inet-types {
    prefix inet;
  }
  import ietf-yang-types {
    prefix yang;
  }

  /*** META INFORMATION ***/

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR arp package configuration.

     This YANG module augments the
     modules with configuration data.

     Copyright (c) 2019, 2021-2022 by Cisco Systems, Inc.
     All rights reserved.";

  revision 2019-10-10 {
    description
      "Moved trap augments into Cisco-IOS-XR-um-traps-mpls-ldp-cfg.";
    semver:module-version "3.0.0";
  }

  revision "2019-06-10" {
    description
      "Establish semantic version baseline.";
    semver:module-version "1.0.0";
  }

  revision "2019-04-04" {
    description
      "Initial version";
  }

  container arp {
    description
      "Global ARP configuration";
    container entries {
      description
        "ARP entries";
      list entry {
        key "ip-address";
        description
          "configure ARP entry";
        leaf ip-address {
          type inet:ipv4-address-no-zone;
          description
            "IP Address";
        }
        leaf mac-address {
          type yang:mac-address;
          mandatory true;
          description
            "MAC Address";
        }
        leaf encapsulation-type {
          type enumeration {
            enum ARPA {
              value 1;
              description
                "Encapsulation type ARPA";
            }
            enum SRP {
              value 4;
              description
                "Encapsulation type SRP";
            }
            enum SRPA {
              value 5;
              description
                "Encapsulation type SRPA";
            }
            enum SRPB {
              value 6;
              description
                "Encapsulation type SRPB";
            }
          }
          mandatory true;
          description
            "configure this node";
        }
        container alias {
          presence "Indicates a alias node is configured.";
          description
            "Configure an Alias ARP entry";
        }
        leaf interface {
          type xr:Interface-name;
          description
            "Specify a Interface";
        }
      }
    }
    container vrfs {
      description
        "Specify a non-default VRF";
      list vrf {
        must 'entries/entry';
        key "vrf-name";
        description
          "Specify a non-default VRF";
        leaf vrf-name {
          type xr:Cisco-ios-xr-string {
            length "1..1024" {
              description
                "VRF name";
            }
          }
          description
            "Specify a non-default VRF";
        }
        container entries {
          description
            "ARP entries";
          list entry {
            key "ip-address";
            description
              "configure this node";
            leaf ip-address {
              type inet:ipv4-address-no-zone;
              description
                "IP Address";
            }
            leaf mac-address {
              type yang:mac-address;
              mandatory true;
              description
                "MAC Address";
            }
            leaf encapsulation-type {
              type enumeration {
                enum ARPA {
                  value 1;
                  description
                    "Encapsulation type ARPA";
                }
                enum SRP {
                  value 4;
                  description
                    "Encapsulation type SRP";
                }
                enum SRPA {
                  value 5;
                  description
                    "Encapsulation type SRPA";
                }
                enum SRPB {
                  value 6;
                  description
                    "Encapsulation type SRPB";
                }
              }
              mandatory true;
              description
                "configure this node";
            }
            container alias {
              presence "Indicates a alias node is configured.";
              description
                "Configure an Alias ARP entry";
            }
            leaf interface {
              type xr:Interface-name;
              description
                "Specify a Interface";
            }
          }
        }
      }
    }
    leaf inner-cos {
      type uint32 {
        range "0..7" {
          description
            "inner cos value";
        }
      }
      description
        "Configure inner cos values for arp packets";
    }
    leaf outer-cos {
      type uint32 {
        range "0..7" {
          description
            "Outer cos value";
        }
      }
      description
        "Configure outer cos values for arp packets";
    }
    leaf max-entries {
      type uint32 {
        range "1..256000" {
          description
            "entries";
        }
      }
      description
        "Configure maximum number of safe ARP entries per line card";
    }
    container redundancy {
      presence "Indicates a redundancy node is configured.";
      description
        "Configure parameter for ARP Geo redundancy";
      container groups {
        description
          "Redundancy Group configuration";
        list group {
          key "group-id";
          description
            "Redundancy Group configuration";
          leaf group-id {
            type uint32 {
              range "1..32" {
                description
                  "Group ID";
              }
            }
            description
              "Redundancy Group configuration";
          }
          leaf source-interface {
            type xr:Interface-name;
            description
              "Source interface for Redundancy Peer Communication";
          }
          container peers {
            description
              "Peer Address for this Group";
            list peer {
              key "peer-address";
              description
                "Peer Address for this Group";
              leaf peer-address {
                type inet:ipv4-address-no-zone;
                description
                  "Peer Address for this Group";
              }
            }
          }
          container interface-list {
            presence "Indicates a interface-list node is configured.";
            description
              "List of Interfaces for this Group";
            container interfaces {
              description
                "Interface for this Group";
              list interface {
                key "interface-name";
                description
                  "Interface for this Group";
                leaf interface-name {
                  type xr:Interface-name;
                  description
                    "Interface for this Group";
                }
                leaf id {
                  type uint32 {
                    range "1..65535" {
                      description
                        "ID for the interface to be mapped on to peer";
                    }
                  }
                  mandatory true;
                  description
                    "Map Identifier";
                }
              }
            }
          }
        }
      }
    }
  }
}
