module Cisco-IOS-XR-um-control-plane-local-cfg {

  /*** NAMESPACE / PREFIX DEFINITION ***/

  namespace "http://cisco.com/ns/yang/Cisco-IOS-XR-um-control-plane-local-cfg";
  prefix um-control-plane-local-cfg;

  /*** LINKAGE (IMPORTS / INCLUDES) ***/

  import Cisco-IOS-XR-um-control-plane-cfg {
    prefix a1;
  }

  import cisco-semver { prefix "semver"; }

  /*** META INFORMATION ***/

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR control-plane-local package configuration.

     This YANG module augments the
     modules with configuration data.

     Copyright (c) 2020, 2022 by Cisco Systems, Inc.
     All rights reserved.";

  revision 2022-07-11 {
    description
      "Added missing description statement to nodes";
    semver:module-version "1.0.0";
  }

  revision "2020-12-08" {
    description
      "Initial release";
    semver:module-version "1.0.0";
  }

  feature qos_ui_supp_locp_copy_qos_group {
    description
      "qos ui supp locp copy qos group";
  }

  feature qos_ui_supp_locp_set_precedence {
    description
      "qos ui supp locp set precedence";
  }

  augment "/a1:control-plane" {
    description
      "This augment extends control-plane nodes configuration";
    container local {
      description
        "Locally originated packets";
      container control-packets {
        description
          "Control packets generated by OSPF etc";
        container copy {
          description
            "Copy the field from the packet header";
          container precedence {
            description
              "Precedence value in the packet header";
            container qos-group {
              presence "Indicates a qos-group node is configured.";
              description
                "Set the qos-group field in locally originated control packets ";
            }
          }
        }
        container set {
          if-feature "qos_ui_supp_locp_set_precedence";
          description
            "Set the precedence";
          leaf precedence {
            type uint32 {
              range "0..7" {
                description
                  "Precedence value";
              }
            }
            description
              "Precedence value in the packet header";
          }
        }
      }
    }
  }
}
