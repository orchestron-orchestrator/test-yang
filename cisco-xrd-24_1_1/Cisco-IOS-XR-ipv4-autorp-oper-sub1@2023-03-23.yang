submodule Cisco-IOS-XR-ipv4-autorp-oper-sub1 {

  belongs-to Cisco-IOS-XR-ipv4-autorp-oper {
    prefix Cisco-IOS-XR-ipv4-autorp-oper;
  }

  /*** LINKAGE (IMPORTS / INCLUDES) ***/

  import ietf-inet-types { prefix "inet"; }

  import cisco-semver { prefix "semver"; }

  include Cisco-IOS-XR-ipv4-autorp-oper-sub2 {
    revision-date 2023-03-23;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ipv4-autorp package operational data.

     Copyright (c) 2013-2023 by Cisco Systems, Inc.
     All rights reserved.";

  revision "2023-03-23" {
    description
      "change in 'autorp_map_missed_packet_bag'
       2022-08-25
         backward compatible addition in 'autorp_crp_bag'";
    semver:module-version "1.2.0";
  }

  revision "2019-08-27" {
    description
      "Providing AutoRP information";
    semver:module-version "1.1.0";
  }

  revision "2019-04-05" {
    description
      "Establish semantic version baseline.";
    semver:module-version "1.0.1";
  }

  revision "2015-11-09" {
    description
      "IOS XR 6.0 revision.";
  }

  grouping AUTORP-MAP-SUMMARY-BAG {
    description "Auto-RP Mapping Agent summary";
    leaf is-maximum-disabled {
      type boolean;
      description "Is maximum enforcement disabled ?";
    }
    leaf cache-limit {
      type uint32;
      description "Maximum group to RP mapping entries allowed";
    }
    leaf cache-count {
      type uint32;
      description
        "Number of group to RP mapping entries in the
        cache";
    }
  }

  grouping AUTORP-MAP-MISSED-PACKET-BAG {
    description "AUTORP MAP Missed Packet";
    leaf message-type {
      type uint32;
      description "Message Type";
    }
    leaf message-string {
      type string {
        length "0..70";
      }
      description "Message String";
    }
    leaf message-time {
      type string {
        length "0..40";
      }
      description "Message Time";
    }
  }

  grouping AUTORP-MAP-MISSED-PACKETS-LIST-BAG {
    description "AUTORP MAP Missed Packets list information";

    list missed-packets {
      description "List of Missed Packets";
      uses AUTORP-MAP-MISSED-PACKET-BAG;
    }
  }

  grouping AUTORP-MAP-BAG-EVENT-HISTORY {
    description "AUTORP MAP BAG EVENT HISTORY";
    leaf event-str {
      type string {
        length "0..70";
      }
      description "event str";
    }
    leaf event-time {
      type string {
        length "0..40";
      }
      description "event time";
    }
  }

  grouping AUTORP-MAP-RANGE-BAG {
    description "MRIB multicast-routing entry-interface";
    leaf prefix {
      type inet:ipv4-address;
      description "Prefix of the range";
    }
    leaf prefix-length {
      type uint8;
      description "Prefix length of the range";
    }
    leaf protocol-mode {
      type Autorp-protocol-mode;
      description "Protocol Mode";
    }
    leaf is-advertised {
      type boolean;
      description "Is this entry advertised ?";
    }
    leaf create-type {
      type uint8;
      description "Source of the entry";
    }
    leaf check-point-object-id {
      type uint32;
      description "Checkpoint object id";
    }
    leaf uptime {
      type uint64;
      units "second";
      description "Uptime in seconds";
    }
  }

  grouping AUTORP-MAP-RP-BAG {
    description "Auto-RP Mapping Agent entry";
    leaf rp-address-xr {
      type inet:ipv4-address;
      description "Candidate-RP address";
    }
    leaf expiry-time {
      type uint64;
      units "second";
      description "Time for expiration in seconds";
    }
    leaf pim-version {
      type uint8;
      description "PIM version of the CRP";
    }

    list range {
      description "Array of ranges";
      uses AUTORP-MAP-RANGE-BAG;
    }

    list map-adv-recv-event {
      max-elements "8";
      description "MAP Agent Adv Recv Event History";
      uses AUTORP-MAP-BAG-EVENT-HISTORY;
    }

    list map-rp-elect-recv-event {
      max-elements "8";
      description "MAP Agent RP Election Event History";
      uses AUTORP-MAP-BAG-EVENT-HISTORY;
    }
  }

  grouping AUTORP-MAP-TRAFFIC-BAG {
    description "Auto-RP Mapping Agent Traffic Counters";
    leaf active-sent-packets {
      type uint32;
      description "Number of packets sent in active role";
    }
    leaf standby-sent-packets {
      type uint32;
      description
        "Number of packets dropped in send path in
        standby role";
    }
    leaf active-received-packets {
      type uint32;
      description "Number of packets received in active role";
    }
    leaf standby-received-packets {
      type uint32;
      description
        "Number of packets dropped in receive path in
        standby role";
    }
  }
}
