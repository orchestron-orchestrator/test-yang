module Cisco-IOS-XR-um-if-dhcp-client-options-cfg {

  /*** NAMESPACE / PREFIX DEFINITION ***/

  namespace "http://cisco.com/ns/yang/Cisco-IOS-XR-um-if-dhcp-client-options-cfg";
  prefix um-if-dhcp-client-options-cfg;

  /*** LINKAGE (IMPORTS / INCLUDES) ***/

  import Cisco-IOS-XR-types {
    prefix xr;
  }
  import Cisco-IOS-XR-um-interface-cfg {
    prefix a1;
  }

  import cisco-semver { prefix "semver"; }

  /*** META INFORMATION ***/

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR if-dhcp-client-options package configuration.

     This YANG module augments the
     modules with configuration data.

     Copyright (c) 2020-2022 by Cisco Systems, Inc.
     All rights reserved.";

  revision 2022-07-11 {
    description
      "Added missing description statement to nodes";
    semver:module-version "1.1.0";
  }

  revision "2020-04-20" {
    description
      "Initial release";
    semver:module-version "1.0.0";
  }

  grouping IF-IPV4-BODY {
    description
      "Grouping for if-ipv4";
    container address {
      description
        "Set the IPv4 address of an interface";
      container dhcp-client-options {
        presence "Indicates a dhcp-client-options node is configured.";
        description
          "dhcp client option";
        container option {
          description
            "Insert option keyword";
          container vendor-id-option-60 {
            must "not(../client-id-option-61 or
                      ../user-class-id-option-77)";
            presence "Indicates a vendor-id-option-60 node is configured.";
            description
              "set vendor id option";
            leaf ascii {
              type xr:Cisco-ios-xr-string {
                length "1..255" {
                  description
                    "Enter ascii pattern";
                }
              }
              mandatory true;
              description
                "Option 60 in ascii";
            }
          }
          container client-id-option-61 {
            must "not(../vendor-id-option-60 or
                      ../user-class-id-option-77) and
                  (ascii or sn-chassis)";
            presence "Indicates a client-id-option-61 node is configured.";
            description
              "set client id option";
            leaf ascii {
              type xr:Cisco-ios-xr-string {
                length "1..255" {
                  description
                    "Enter ascii pattern";
                }
              }
              must 'not(../sn-chassis)';
              description
                "Option 61 in ascii";
            }
            container sn-chassis {
              must 'not(../ascii)';
              presence "Indicates a sn-chassis node is configured.";
              description
                "sn chassis number";
            }
          }
          container user-class-id-option-77 {
            must "not(../vendor-id-option-60 or
                      ../client-id-option-61)";
            presence "Indicates a user-class-id-option-77 node is configured.";
            description
              "set user class id option";
            leaf ascii {
              type xr:Cisco-ios-xr-string {
                length "1..255" {
                  description
                    "Enter ascii pattern";
                }
              }
              mandatory true;
              description
                "Option 77 in ascii";
            }
          }
        }
      }
    }
  }

  augment "/a1:interfaces/a1:interface/a1:ipv4" {
    description
      "This augment extends active nodes configuration";
    uses IF-IPV4-BODY;
  }

  augment "/a1:interfaces/a1:interface-preconfigure/a1:ipv4" {
    description
      "This augment extends preconfigured nodes
       configuration";
    uses IF-IPV4-BODY;
  }
}
