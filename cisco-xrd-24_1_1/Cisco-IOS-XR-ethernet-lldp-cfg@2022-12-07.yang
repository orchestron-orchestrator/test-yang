module Cisco-IOS-XR-ethernet-lldp-cfg {

  /*** NAMESPACE / PREFIX DEFINITION ***/

  namespace "http://cisco.com/ns"+
    "/yang/Cisco-IOS-XR-ethernet-lldp-cfg";


  prefix "ethernet-lldp-cfg";

  /*** LINKAGE (IMPORTS / INCLUDES) ***/

  import Cisco-IOS-XR-types { prefix "xr"; }

  import cisco-semver { prefix "semver"; }

  import Cisco-IOS-XR-ifmgr-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ethernet-lldp package configuration.

     This module contains definitions
     for the following management objects:
       lldp: Enable LLDP, or configure global LLDP subcommands

     This YANG module augments the
       Cisco-IOS-XR-ifmgr-cfg
     module with configuration data.

     Copyright (c) 2013-2022 by Cisco Systems, Inc.
     All rights reserved.";

  revision "2022-12-07" {
    description
      "Updated leaf tx-tagged to tagged and added enable-gl-subif-tagged
       2022-11-25
         Corrected chassis-id-type values and order item numbers
       2022-11-08
         Added tx-tagged field
       2022-04-01
         Local LLDP system parameters configuration addition.";
    semver:module-version "1.1.0";
  }

  revision "2020-09-01" {
    description
      "Fixing backward compatibility error in module.";
    semver:module-version "1.0.1";
  }

  revision "2019-04-05" {
    description
      "Establish semantic version baseline.";
    semver:module-version "1.0.1";
  }

  revision "2017-05-01" {
    description
      "Fixing backward compatibility error in module.";
  }

  revision "2015-11-09" {
    description
      "IOS XR 6.0 revision.";
  }

  typedef Chassis-id-sub {
    type enumeration {
      enum chassis-component {
        value 0;
        description
          "Value of entPhysicalAlias object defined in
          IETF RFC 2737";
      }
      enum interface-alias {
        value 1;
        description
          "Value of ifAlias object defined in IETF RFC
          2863";
      }
      enum port-component {
        value 2;
        description
          "Value of entPhysicalAlias object defined in
          IETF RFC 2737";
      }
      enum mac-address {
        value 3;
        description "Value of a unicast source address";
      }
      enum network-address {
        value 4;
        description
          "Network address associated with a particular
          chassis";
      }
      enum interface-name {
        value 5;
        description
          "Value of ifName object defined in IETF RFC 2863";
      }
      enum local {
        value 6;
        description
          "Chassis identifier based on a locally defined
          value";
      }
    }
    description "Chassis id sub";
  }

  container lldp {
    description "Enable LLDP, or configure global LLDP subcommands";

    container tlv-select {
      presence "Indicates a tlv-select node is configured.";
      description "Selection of LLDP TLVs to disable";

      container system-name {
        description "System Name TLV";
        leaf disable {
          type boolean;
          default "false";
          description "disable System Name TLV";
        }
      }

      container port-description {
        description "Port Description TLV";
        leaf disable {
          type boolean;
          default "false";
          description "disable Port Description TLV";
        }
      }

      container system-description {
        description "System Description TLV";
        leaf disable {
          type boolean;
          default "false";
          description "disable System Description TLV";
        }
      }

      container system-capabilities {
        description "System Capabilities TLV";
        leaf disable {
          type boolean;
          default "false";
          description "disable System Capabilities TLV";
        }
      }

      container management-address {
        description "Management Address TLV";
        leaf disable {
          type boolean;
          default "false";
          description "disable Management Address TLV";
        }
      }
      leaf tlv-select-enter {
        type boolean;
        mandatory true;
        description "enter lldp tlv-select submode";
      }
    }
    leaf chassis-id {
      type string {
        length "1..256";
      }
      description "LLDP local chassis ID";
    }
    leaf holdtime {
      type uint32 {
        range "0..65535";
      }
      description
        "Length  of time  (in sec) that receiver must
        keep this packet";
    }
    leaf enable-priority-addr {
      type boolean;
      default "false";
      description
        "Enable or disable Priority to advertise
        Mgmt-interface Addr First";
    }
    leaf extended-show-width {
      type boolean;
      default "false";
      description
        "Enable or disable LLDP Show LLDP Neighbor
        Extended Width";
    }
    leaf enable-subintf {
      type boolean;
      default "false";
      description
        "Enable or disable LLDP on Sub-interfaces as well
        globally";
    }
    leaf enable-mgmtintf {
      type boolean;
      default "false";
      description
        "Enable or disable LLDP on Mgmt interfaces as
        well globally";
    }
    leaf timer {
      type uint32 {
        range "5..65534";
      }
      default "30";
      description
        "Specify the rate at which LLDP packets are sent
        (in sec)";
    }
    leaf reinit {
      type uint32 {
        range "2..5";
      }
      default "2";
      description
        "Delay (in sec) for LLDP initialization on any
        interface";
    }
    leaf system-description {
      type string {
        length "1..256";
      }
      description "LLDP local system description";
    }
    leaf enable {
      type boolean;
      default "false";
      description "Enable or disable LLDP globally";
    }
    leaf enable-global-subif-tagged {
      type boolean;
      default "false";
      description
        "Enable or disable VLAN tagging for LLDP PDU on
        Sub-interfaces globally";
    }
    leaf system-name {
      type xr:Cisco-ios-xr-string {
        length "1..256";
      }
      description "LLDP local system name";
    }
    leaf chassis-id-type {
      type Chassis-id-sub;
      description "LLDP local chassis ID type";
    }
  }

  augment "/a1:interface-configurations/a1:interface-configuration" {

    container lldp {
      presence "Indicates a lldp node is configured.";
      description "Disable LLDP TX or RX";

      container transmit {
        description "Disable LLDP TX";
        leaf disable {
          type boolean;
          default "false";
          description "disable LLDP TX";
        }
      }

      container receive {
        description "Disable LLDP RX";
        leaf disable {
          type boolean;
          default "false";
          description "disable LLDP RX";
        }
      }
      leaf lldp-intf-enter {
        type boolean;
        mandatory true;
        description "enter LLDP interface submode";
      }
      leaf tagged {
        type boolean;
        default "false";
        description
          "Enable VLAN tagged LLDP PDU support on
          interface";
      }
      leaf enable {
        type boolean;
        default "false";
        description "Enable both LLDP TX and RX";
      }
    }
    description
      "This augment extends the configuration data of
      'Cisco-IOS-XR-ifmgr-cfg'";
  }
}
