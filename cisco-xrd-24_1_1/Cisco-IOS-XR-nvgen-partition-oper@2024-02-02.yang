module Cisco-IOS-XR-nvgen-partition-oper {

  /*** NAMESPACE / PREFIX DEFINITION ***/

  namespace "http://cisco.com/ns/yang"+
    "/Cisco-IOS-XR-nvgen-partition-oper";


  prefix "nvgen-partition-oper";

  /*** LINKAGE (IMPORTS / INCLUDES) ***/

  import cisco-semver { prefix "semver"; }

  include Cisco-IOS-XR-nvgen-partition-oper-sub1 {
    revision-date 2024-02-02;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR nvgen-partition package operational data.

     This module contains definitions
     for the following management objects:
       nvgen-partition: nvgen partition details

     Copyright (c) 2013-2024 by Cisco Systems, Inc.
     All rights reserved.";

  revision "2024-02-02" {
    description
      "Add display partition info";
    semver:module-version "1.0.0";
  }

  revision "2019-04-05" {
    description
      "Establish semantic version baseline.";
  }

  revision "2015-11-09" {
    description
      "IOS XR 6.0 revision.";
  }

  container nvgen-partition {
    config false;
    description "nvgen partition details";

    container nvgen-partition-tables {
      description "All partitions";

      list nvgen-partition-table {
        key "path";
        description "nvgen partition details";
        leaf path {
          type string;
          description "Path";
        }
        uses NVGEN-PARTITION-INFO;
      }
    }

    container display-nvgen-partition-tables {
      description "All display partitions";

      list display-nvgen-partition-table {
        key "path";
        description "nvgen display partition details";
        leaf path {
          type string;
          description "Path";
        }
        uses NVGEN-PARTITION-INFO;
      }
    }
  }
}
