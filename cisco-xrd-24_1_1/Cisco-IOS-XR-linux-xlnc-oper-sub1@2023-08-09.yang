submodule Cisco-IOS-XR-linux-xlnc-oper-sub1 {

  belongs-to Cisco-IOS-XR-linux-xlnc-oper {
    prefix Cisco-IOS-XR-linux-xlnc-oper;
  }

  /*** LINKAGE (IMPORTS / INCLUDES) ***/

  import ietf-inet-types { prefix "inet"; }

  import ietf-yang-types { prefix "yang"; }

  import cisco-semver { prefix "semver"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR linux-xlnc package operational data.

     Copyright (c) 2013-2023 by Cisco Systems, Inc.
     All rights reserved.";

  revision "2023-08-09" {
    description
      "Correct name of the IPv6 address list
       2023-04-05
         Add support for Linux-owned VRF
       2022-09-28
         Added new conflict reason to enumeration
       2022-09-16
         Added VRF-disable, East-West and source hint support
       2021-12-03
         Added secondary IPv4 addresses";
    semver:module-version "2.0.0";
  }

  revision "2020-06-22" {
    description
      "Added address-only interface types and corresponding inconsistencies";
    semver:module-version "1.2.0";
  }

  revision "2019-04-05" {
    description
      "Establish semantic version baseline.";
    semver:module-version "1.1.0";
  }

  revision "2015-11-09" {
    description
      "IOS XR 6.0 revision.";
  }

  typedef Xlnc-bag-l4-protocol {
    type enumeration {
      enum tcp {
        description "TCP";
      }
      enum udp {
        description "UDP";
      }
    }
    description "L4 Protocol";
  }
  typedef Xlnc-bag-ew-intf-unused-reason {
    type enumeration {
      enum unknown {
        description "Unknown reason";
      }
      enum interface-does-not-exist {
        description "Configured East-West interface does not exist";
      }
      enum no-ip-address {
        description
          "Configured East-West interface does not have a
          suitable IP address";
      }
    }
    description "Reason configured East-West interface not used";
  }
  typedef Xlnc-bag-src-hint-unused-reason {
    type enumeration {
      enum unknown {
        description "Unknown reason";
      }
      enum interface-does-not-exist {
        description
          "Configured source hint interface does not exist";
      }
      enum no-ip-address {
        description
          "Configured source hint interface does not have
          a suitable IP address";
      }
      enum interface-not-exported-to-linux {
        description
          "Configured source hint interface is not
          exported to Linux";
      }
    }
    description "Reason configured source hint not used";
  }
  typedef Xlnc-bag-conf-err-per-vrf-category {
    type enumeration {
      enum source-hint-interface-unused {
        description "Configured source hint interface unused";
      }
      enum east-west-interface-unused {
        description "Configure East-West interface unused";
      }
      enum active-tp-excptn {
        description
          "Traffic Protection Services/Rules clash with a
          Exception";
      }
    }
    description "per-VRF config error category";
  }
  typedef Xlnc-bag-oper-state {
    type enumeration {
      enum oper-down {
        description "Operationally down";
      }
      enum oper-up {
        description "Operationally up";
      }
      enum oper-unknown {
        description "Unknown oper state";
      }
    }
    description "Operational state values";
  }
  typedef Bag-mac-addr {
    type yang:mac-address;
    description "Bag mac addr";
  }
  typedef Xlnc-bag-admin-state {
    type enumeration {
      enum admin-down {
        description "Administratively down";
      }
      enum admin-up {
        description "Administratively up";
      }
      enum admin-unknown {
        description "Unknown admin state";
      }
    }
    description "Administrative state values";
  }
  typedef Xlnc-bag-attr {
    type enumeration {
      enum admin-state {
        description "Interface administrative state";
      }
      enum mac-address {
        description "MAC address";
      }
      enum l3-mtu {
        description "L3 MTU";
      }
      enum ipv4-address {
        description "IPv4 address";
      }
      enum ipv6-enabled {
        description "IPv6 enabled";
      }
      enum ipv6-address {
        description "IPv6 address";
      }
      enum unknown-attr {
        description "Unknown attribute";
      }
      enum oper-state {
        description "Interface operational state";
      }
    }
    description "Interface attribute type";
  }
  typedef Xlnc-bag-op {
    type enumeration {
      enum set {
        description "Set";
      }
      enum delete {
        description "Delete";
      }
      enum unknown-op {
        description "Unknown";
      }
    }
    description "Operation type (set or delete)";
  }
  typedef Xlnc-bag-error-category {
    type enumeration {
      enum default-error-category {
        description "Default error type";
      }
      enum set-linux-error-category {
        description "Error setting interface attributes in Linux";
      }
      enum set-ios-xr-error-category {
        description "Error setting interface attributes in IOS-XR";
      }
      enum im-resync-error-category {
        description
          "Error setting interface attribute during IM
          resync";
      }
      enum unknown-category {
        description "Unknown error category";
      }
    }
    description "Error category";
  }
  typedef Xlnc-bag-inconsistency-category {
    type enumeration {
      enum attribute-conflicting-sync {
        description
          "An attempt was made to synchronize interface
          attributes in one direction, when they were
          already being synchronized in the opposing
          direction.";
      }
      enum conflicting-im-resync {
        description
          "During an IM resync, an attempt was made to
          synchronize interface attributes in one
          direction when they were already being
          synchronized in the opposing direction.";
      }
      enum more-than-one-ipv6-link-local-address {
        description
          "An attempt was made to configure more than one
          link-local IPv6 address on a single interface.";
      }
      enum more-than-on-ipv4-address {
        description
          "An attempt was made to configure more than one
          primary IPv4 address on a single interface.";
      }
      enum delete-unknown-ipv6-link-local-address {
        description
          "An attempt was made to remove an unknown
          link-local IPv6 address from an interface.";
      }
      enum delete-unknown-ipv4-address {
        description
          "An attempt was made to remove an unknown IPv4
          address from an interface.";
      }
      enum attribute-set-in-linux-failure {
        description
          "An attempt to set an interface attribute value
          in Linux failed.";
      }
      enum attribute-set-in-xr-failure {
        description
          "An attempt to set an interface attribute value
          in IOS-XR failed.";
      }
      enum mtu-too-small-for-ipv6 {
        description
          "The MTU set in Linux is smaller than the
          minimum size required for IPv6. The Linux
          kernel will remove any IPv6 addresses on the
          interface, which must be re-added when the MTU
          is increased.";
      }
      enum mac-address-change-not-supported {
        description
          "MAC address changes are not supported for this
          interface type on this platform. The MAC
          address has not been changed.";
      }
      enum unknown-inconsistency {
        description "Unknown inconsistency type";
      }
      enum delete-loopback-address {
        description
          "An address that was automatically added to a
          Linux loopback device to provide L3
          reachability has been unexpectedly removed. 
          Traffic to/from Linux applications using that
          address will be dropped";
      }
      enum delete-secondary-ipv4-address {
        description
          "An interface with secondary IPv4 address(es)
          was configured to be linux-managed, but the
          secondary IPv4 address configuration cannot be
          removed from IOS-XR";
      }
      enum oper-state-change-to-xr-not-supported {
        description
          "Operational state change syncing to XR are not
          supported. The operational state has not been
          changed.";
      }
    }
    description "XLNC inconsistency types";
  }
  typedef Xlnc-bag-sync-dir {
    type enumeration {
      enum to-xr {
        description "From Linux to IOS-XR";
      }
      enum to-linux {
        description "From IOS-XR to Linux";
      }
      enum unknown-dir {
        description "Unknown direction";
      }
    }
    description "Synchronization direction";
  }
  typedef Xlnc-bag-conf-err-global-category {
    type enumeration {
      enum stats-intvl-mapped {
        description
          "The desired global statistics sync interval
          could not be configured and was mapped to an
          alternative value.";
      }
    }
    description "Global config error category";
  }
  typedef Xlnc-bag-intf-chosen-reason {
    type enumeration {
      enum explicitly-configured {
        description "Explicitly configured";
      }
      enum automatically-selected {
        description "Automatically selected";
      }
    }
    description "Reason why the interface was selected";
  }
  typedef Bag-in6-addr {
    type inet:ipv6-address;
    description "Bag in6 addr";
  }
  typedef Xlnc-bag-addr {
    type enumeration {
      enum ipv4-address {
        description "IPv4 address";
      }
      enum ipv6-address {
        description "IPv6 address";
      }
      enum unknown-address-type {
        description "Unknown address type";
      }
    }
    description "IP address type";
  }

  grouping XLNC-BAG-ACTIVE-TP-TYPE {
    description "Active Traffic Protection Exception";

    container local-addr {
      description "Local IP address.";
      uses XLNC-ADDR-VALUE-TYPE;
    }
    leaf address-family {
      type Xlnc-bag-addr;
      description "Address family";
    }
    leaf protocol {
      type Xlnc-bag-l4-protocol;
      description "L4 Protocol";
    }
    leaf local-port {
      type uint32;
      description "Local port number";
    }
  }

  grouping XLNC-BAG-EW-INTF-UNUSED-TYPE {
    description "East-West interface not being used";
    leaf interface-name {
      type string;
      description "IOS-XR interface name";
    }
    leaf reason {
      type Xlnc-bag-ew-intf-unused-reason;
      description "Reason East-West interface is not being used";
    }
  }

  grouping XLNC-BAG-SRC-HINT-UNUSED-TYPE {
    description "Source hint interface not being used";
    leaf interface-name {
      type string;
      description "IOS-XR interface name";
    }
    leaf address-family {
      type Xlnc-bag-addr;
      description "Address family";
    }
    leaf reason {
      type Xlnc-bag-src-hint-unused-reason;
      description "Reason source hint interface is not being used";
    }
  }

  grouping XLNC-VRF-CONFIG-ERROR-TYPE {
    description "XLNC per-VRF configuration error types";

    container source-hint-interface-unused {
      when "../category = 'source-hint-interface-unused'" {
        description "../Category = 'SourceHintInterfaceUnused'";
      }
      description "Source hint interface not being used";
      uses XLNC-BAG-SRC-HINT-UNUSED-TYPE;
    }

    container east-west-interface-unused {
      when "../category = 'east-west-interface-unused'" {
        description "../Category = 'EastWestInterfaceUnused'";
      }
      description "East-West interface not being used";
      uses XLNC-BAG-EW-INTF-UNUSED-TYPE;
    }

    container active-tp-excptn {
      when "../category = 'active-tp-excptn'" {
        description "../Category = 'ActiveTPExcptn'";
      }
      description "Active Traffic Protection Exception";
      uses XLNC-BAG-ACTIVE-TP-TYPE;
    }
    leaf category {
      type Xlnc-bag-conf-err-per-vrf-category;
      description "Category";
    }
  }

  grouping XLNC-BAG-CONF-ERRS-PER-VRF {
    description "XLNC per_vrf configuration errors";

    list error {
      description "Sequence of configuration errors";
      uses XLNC-VRF-CONFIG-ERROR-TYPE;
    }
  }

  grouping XLNC-BAG-INTERFACE-INCONSISTENCIES {
    description
      "XLNC inconsistencies observed for a given
      interface and associated interface metadata.";
    leaf xr-interface-name {
      type string;
      description "IOS-XR interface name";
    }
    leaf linux-interface-name {
      type string;
      description
        "Linux interface name of the corresponding
        exposed XR interface (EXI)";
    }
    leaf vrf-name {
      type string;
      description "IOS-XR VRF name the interface is assigned to";
    }
    leaf linux-network-namespace-name {
      type string;
      description
        "Linux network namespace name corresponding to
        the IOS-XR VRF the interface is assigned to";
    }
    leaf inconsistencies-truncated {
      type boolean;
      description
        "The oldest entries are no longer saved, because
        the sequence became too long.";
    }

    list inconsistency {
      description "Sequence of inconsistencies";
      uses XLNC-BAG-INCONSISTENCY;
    }
  }

  grouping XLNC-BAG-SET-XR-ERROR-TYPE {
    description "Failed operation to set an attribute in XR.";

    container operation {
      description "Failed synchronization operation";
      uses XLNC-BAG-SYNC-INTF-ATTRS-OP;
    }
    leaf ios-xr-error-decode {
      type string;
      description "Optional decode string for the IOS-XR error.";
    }
    leaf error-string {
      type string;
      description "Optional error string describing the failure.";
    }
  }

  grouping XLNC-BAG-SET-LINUX-ERROR-TYPE {
    description "Failed operation to set an attribute in Linux.";

    container operation {
      description "Failed synchronization operation";
      uses XLNC-BAG-SYNC-INTF-ATTRS-OP;
    }
    leaf attribute-value-valid {
      type boolean;
      description
        "Indicates whether the attribute value in the
        synchronization operation is valid.";
    }
    leaf ios-xr-error-decode {
      type string;
      description "Decode string for the IOS-XR error.";
    }
    leaf libnl-error-decode {
      type string;
      description "Optional decode string for the libnl error.";
    }
  }

  grouping XLNC-BAG-V6-ADDR {
    description "IPv6 address type";
    leaf address {
      type Bag-in6-addr;
      description "Linux representation of the address";
    }
    leaf prefix-length {
      type uint8;
      description "Network prefix length";
    }
  }

  grouping XLNC-BAG-V4-ADDR {
    description "IPv4 address type";
    leaf address {
      type inet:ipv4-address;
      description "Linux representation of the address";
    }
    leaf prefix-length {
      type uint8;
      description "Network prefix length";
    }
  }

  grouping XLNC-ATTR-VALUE-TYPE {
    description "Interface attribute values";

    container ipv4-address {
      when "../attribute-type = 'ipv4-address'" {
        description "../AttributeType = 'IPv4Address'";
      }
      description "IPv4 address";
      uses XLNC-BAG-V4-ADDR;
    }

    container ipv6-address {
      when "../attribute-type = 'ipv6-address'" {
        description "../AttributeType = 'IPv6Address'";
      }
      description "IPv6 address";
      uses XLNC-BAG-V6-ADDR;
    }
    leaf attribute-type {
      type Xlnc-bag-attr;
      description "AttributeType";
    }
    leaf admin-state {
      when "../attribute-type = 'admin-state'" {
        description "../AttributeType = 'AdminState'";
      }
      type Xlnc-bag-admin-state;
      description "Interface administrative state";
    }
    leaf mac-address {
      when "../attribute-type = 'mac-address'" {
        description "../AttributeType = 'MACAddress'";
      }
      type Bag-mac-addr;
      description "MAC address";
    }
    leaf l3-mtu {
      when "../attribute-type = 'l3-mtu'" {
        description "../AttributeType = 'L3_MTU'";
      }
      type uint32;
      description "L3 MTU";
    }
    leaf ipv6-enabled {
      when "../attribute-type = 'ipv6-enabled'" {
        description "../AttributeType = 'IPv6Enabled'";
      }
      type boolean;
      description "IPv6 enabled in IOS-XR";
    }
    leaf oper-state {
      when "../attribute-type = 'oper-state'" {
        description "../AttributeType = 'OperState'";
      }
      type Xlnc-bag-oper-state;
      description "Interface operational state";
    }
  }

  grouping XLNC-BAG-SYNC-INTF-ATTRS-OP {
    description "Interface attributes synchronization operation";

    container attribute-value {
      description "Value of interface attribute";
      uses XLNC-ATTR-VALUE-TYPE;
    }
    leaf synchronization-direction {
      type Xlnc-bag-sync-dir;
      description "Synchronization direction";
    }
    leaf operation-type {
      type Xlnc-bag-op;
      description "Operation type (set or delete)";
    }
  }

  grouping XLNC-ERROR-TYPE {
    description "XLNC error types which may cause an inconsistency";

    container interface-attributes-operation {
      when "../error-category = 'default-error-category'" {
        description "../ErrorCategory = 'DefaultErrorCategory'";
      }
      description "Interface attributes synchronization operation";
      uses XLNC-BAG-SYNC-INTF-ATTRS-OP;
    }

    container set-linux-error {
      when "../error-category = 'set-linux-error-category'" {
        description "../ErrorCategory = 'SetLinuxErrorCategory'";
      }
      description
        "Error type associated with failure to set
        interface attributes in Linux.";
      uses XLNC-BAG-SET-LINUX-ERROR-TYPE;
    }

    container set-ios-xr-error {
      when "../error-category = 'set-ios-xr-error-category'" {
        description "../ErrorCategory = 'SetIOS_XR_ErrorCategory'";
      }
      description
        "Error type associated with failure to set
        interface attributes in IOS-XR.";
      uses XLNC-BAG-SET-XR-ERROR-TYPE;
    }

    container resync-attributes-operation {
      when "../error-category = 'im-resync-error-category'" {
        description "../ErrorCategory = 'ImResyncErrorCategory'";
      }
      description
        "Resync interface attributes synchronization
        operation";
      uses XLNC-BAG-SYNC-INTF-ATTRS-OP;
    }
    leaf error-category {
      type Xlnc-bag-error-category;
      description "ErrorCategory";
    }
  }

  grouping XLNC-BAG-INCONSISTENCY {
    description "XLNC inconsistency record";

    container error {
      description
        "Diagnostic information about the error which
        caused the inconsistency.";
      uses XLNC-ERROR-TYPE;
    }
    leaf milliseconds-since-epoch {
      type uint64;
      units "millisecond";
      description
        "How many milliseconds after the Unix epoch the
        inconsistency occurred";
    }
    leaf inconsistency-category {
      type Xlnc-bag-inconsistency-category;
      description "Type of inconsistency which occurred";
    }
  }

  grouping XLNC-BAG-VRF-INCONSISTENCIES {
    description
      "XLNC inconsistencies observed for a given
      interface and associated interface metadata.";
    leaf vrf-name-xr {
      type string;
      description "IOS-XR VRF name";
    }
    leaf linux-network-namespace-name {
      type string;
      description
        "Linux network namespace name corresponding to
        the IOS-XR VRF";
    }
    leaf inconsistencies-truncated {
      type boolean;
      description
        "The oldest entries are no longer saved, because
        the sequence became too long.";
    }

    list inconsistency {
      description "Sequence of inconsistencies";
      uses XLNC-BAG-INCONSISTENCY;
    }
  }

  grouping XLNC-BAG-STATUS {
    description "XLNC status";
    leaf linux-owned-vrf {
      type string;
      description "Linux owned VRF name";
    }
  }

  grouping XLNC-BAG-INTERFACE-ADDRESS-ONLY {
    description "XLNC Address-only interface";
    leaf interface-name-xr {
      type string;
      description "IOS-XR interface name";
    }
    leaf vrf-name-xr {
      type string;
      description "IOS-XR VRF name the interface is assigned to";
    }
    leaf ipv4-address {
      type inet:ipv4-address;
      description
        "IPv4 address which has been added to a Linux
        loopback device";
    }
    leaf virtual {
      type boolean;
      description
        "Whether this address comes from an IOS-XR
        Virtual IP address";
    }
    leaf-list ipv4-secondary-address {
      type inet:ipv4-address;
      description
        "IPv4 secondary addresses which have been added
        to a Linux loopback device";
    }
    leaf-list ipv6-address {
      type Bag-in6-addr;
      description
        "IPv6 addressess which have been added to a Linux
        loopback device";
    }
  }

  grouping XLNC-BAG-GLOBAL-STATS-SYNC-MAP-TYPE {
    description "Global statistics synchronization mapping";
    leaf synchronization-direction {
      type Xlnc-bag-sync-dir;
      description "Synchronization direction";
    }
    leaf requested-interval {
      type uint32;
      description "Requested interval";
    }
    leaf programmed-interval {
      type uint32;
      description "Programmed interval";
    }
  }

  grouping XLNC-GLOBAL-CONFIG-ERROR-TYPE {
    description "XLNC global configuration error types";

    container global-statistics-sync-mapping {
      when "../category = 'stats-intvl-mapped'" {
        description "../Category = 'StatsIntvlMapped'";
      }
      description "Global statistics synchronization mapping";
      uses XLNC-BAG-GLOBAL-STATS-SYNC-MAP-TYPE;
    }
    leaf category {
      type Xlnc-bag-conf-err-global-category;
      description "Category";
    }
  }

  grouping XLNC-BAG-CONF-ERRS-GLOBAL {
    description "XLNC global configuration errors";

    list error {
      description "Sequence of configuration errors";
      uses XLNC-GLOBAL-CONFIG-ERROR-TYPE;
    }
  }

  grouping XLNC-BAG-ROUTE-MTU-INFO-TYPE {
    description
      "MTU value and (one of) the lowest MTU
      interface(s) it was derived from.";
    leaf mtu {
      type uint16;
      description "MTU hint set on the route";
    }
    leaf interface-name {
      type string;
      description
        "IOS-XR interface name of an interface used to
        calculate the MTU";
    }
  }

  grouping XLNC-ADDR-VALUE-TYPE {
    description "IP address values";
    leaf address-type {
      type Xlnc-bag-addr;
      description "AddressType";
    }
    leaf ipv4-address {
      when "../address-type = 'ipv4-address'" {
        description "../AddressType = 'IPv4Address'";
      }
      type inet:ipv4-address;
      description "IPv4 address";
    }
    leaf ipv6-address {
      when "../address-type = 'ipv6-address'" {
        description "../AddressType = 'IPv6Address'";
      }
      type Bag-in6-addr;
      description "IPv6 address";
    }
  }

  grouping XLNC-BAG-ADDR-INTF-REASON-TYPE {
    description
      "Address, interface, and a reason they were chosen
      for either a source hint or East-West
      communication";

    container ip-address {
      description "IP address";
      uses XLNC-ADDR-VALUE-TYPE;
    }
    leaf interface-name {
      type string;
      description
        "IOS-XR interface name of the interface the
        address came from";
    }
    leaf reason {
      type Xlnc-bag-intf-chosen-reason;
      description "Reason the address and interface were selected";
    }
  }

  grouping XLNC-BAG-VRF-STATUS {
    description "XLNC VRF status";

    container default-route-source-hint-ipv4 {
      description
        "Source hint interface and addresses associated
        with the Linux default IPv4 route";
      uses XLNC-BAG-ADDR-INTF-REASON-TYPE;
    }

    container default-route-mtu-ipv4 {
      description
        "MTU associated with the Linux default IPv4 route
        and an interface used to calculate the MTU.";
      uses XLNC-BAG-ROUTE-MTU-INFO-TYPE;
    }

    container default-route-source-hint-ipv6 {
      description
        "Source hint interface and addresses associated
        with the Linux default IPv6 route";
      uses XLNC-BAG-ADDR-INTF-REASON-TYPE;
    }

    container default-route-mtu-ipv6 {
      description
        "MTU associated with the Linux default IPv6 route
        and an interface used to calculate the MTU.";
      uses XLNC-BAG-ROUTE-MTU-INFO-TYPE;
    }
    leaf vrf-name-xr {
      type string;
      description "IOS-XR VRF name";
    }
    leaf rsi-id {
      type uint64;
      description "VRF RSI ID (if enabled and globally configured)";
    }
    leaf globally-configured {
      type boolean;
      description "VRF exists in IOS-XR global configuration";
    }
    leaf enabled {
      type boolean;
      description "VRF is enabled for synchronization to Linux";
    }
    leaf linux-owned {
      type boolean;
      description
        "VRF is configured as Linux owned and mapped to
        the default Linux namespace";
    }

    list east-west-ipv4 {
      description
        "Interfaces and addresses reserved for East-West
        communication over IPv4";
      uses XLNC-BAG-ADDR-INTF-REASON-TYPE;
    }

    list east-west-ipv6 {
      description
        "Interfaces and addresses reserved for East-West
        communication over IPv6";
      uses XLNC-BAG-ADDR-INTF-REASON-TYPE;
    }
  }
}
