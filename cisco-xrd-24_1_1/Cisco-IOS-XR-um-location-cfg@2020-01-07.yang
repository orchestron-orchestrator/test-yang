module Cisco-IOS-XR-um-location-cfg {

  /*** NAMESPACE / PREFIX DEFINITION ***/

  namespace "http://cisco.com/ns/yang/Cisco-IOS-XR-um-location-cfg";
  prefix um-location-cfg;

  /*** LINKAGE (IMPORTS / INCLUDES) ***/

  import Cisco-IOS-XR-types {
    prefix xr;
  }

  import cisco-semver { prefix "semver"; }

  /*** META INFORMATION ***/

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR location package configuration.

     This YANG module augments the
     modules with configuration data.

     Copyright (c) 2019-2020, 2022 by Cisco Systems, Inc.
     All rights reserved.";

  revision 2020-01-07 {
    description
      "Initial release";
    semver:module-version "1.0.0";
  }


  container locations {
    description
      "Per-node location for active nodes";
    list location {
      key "location-name";
      description
        "The location for an active node";
      leaf location-name {
        type xr:Node-id;
        description
          "The location name for this node";
      }
    }
    list preconfigured-location {
      key "location-name";
      description
        "Per-node location for non-active nodes";
      leaf location-name {
        type xr:Node-id;
        description
          "The location name for this node";
      }
    }
  }
}
