submodule Cisco-IOS-XR-aaa-tacacs-oper-sub1 {

  belongs-to Cisco-IOS-XR-aaa-tacacs-oper {
    prefix Cisco-IOS-XR-aaa-tacacs-oper;
  }

  /*** LINKAGE (IMPORTS / INCLUDES) ***/

  import ietf-inet-types { prefix "inet"; }

  import cisco-semver { prefix "semver"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR aaa-tacacs package operational data.

     Copyright (c) 2013-2022 by Cisco Systems, Inc.
     All rights reserved.";

  revision "2022-11-01" {
    description
      "Added counters for tacacs+ servers
       2022-07-27
         Added support to display tacacs-source-interfaces and complete operational data";
    semver:module-version "1.3.0";
  }

  revision "2021-10-01" {
    description
      "Support to print IPv6 address in operational data.";
    semver:module-version "1.2.0";
  }

  revision "2021-01-06" {
    description
      "Added last-contact-attempt entry in show tacacs.";
    semver:module-version "1.2.0";
  }

  revision "2019-04-05" {
    description
      "Establish semantic version baseline.";
    semver:module-version "1.1.0";
  }

  revision "2015-11-09" {
    description
      "IOS XR 6.0 revision.";
  }

  grouping TACACS-SERVER-GROUPS {
    description "TACACS SERVER GROUPS";

    list server-group {
      description "server group";
      uses TACACS-SERVER-GROUP-BAG;
    }
  }

  grouping TACACS-AAA-COUNTERS {
    description "TACACS AAA COUNTERS";
    leaf ipadd-buf {
      type string;
      description "Ip address buffer of server";
    }
    leaf port {
      type uint32;
      description "server port";
    }
    leaf group-name {
      type string;
      description "name of the server group";
    }
    leaf vrf-name {
      type string;
      description "vrf of the group";
    }
    leaf is-private {
      type boolean;
      description "Flag for private or global server";
    }
    leaf authen-req-counter {
      type uint32;
      description "Authentication counter";
    }
    leaf authen-pass-counter {
      type uint32;
      description "Authentication Success counter";
    }
    leaf authen-fail-counter {
      type uint32;
      description "Authentication Failure counter";
    }
    leaf authen-error-counter {
      type uint32;
      description "Authentication Error counter";
    }
    leaf authen-timeout-counter {
      type uint32;
      description "Authentication Timeout counter";
    }
    leaf exec-author-req-counter {
      type uint32;
      description "Exec Authorization counter";
    }
    leaf exec-author-pass-counter {
      type uint32;
      description "Exec Authorization Success counter";
    }
    leaf exec-author-deny-counter {
      type uint32;
      description "Exec Authorization Deny counter";
    }
    leaf exec-author-error-counter {
      type uint32;
      description "Exec Authorization Error counter";
    }
    leaf exec-author-timeout-counter {
      type uint32;
      description "Exec Authorization Timeout counter";
    }
    leaf cmd-author-req-counter {
      type uint32;
      description "Cmd Authorization counter";
    }
    leaf cmd-author-pass-counter {
      type uint32;
      description "Cmd Authorization Success counter";
    }
    leaf cmd-author-deny-counter {
      type uint32;
      description "Cmd Authorization Deny counter";
    }
    leaf cmd-author-error-counter {
      type uint32;
      description "Cmd Authorization Error counter";
    }
    leaf cmd-author-timeout-counter {
      type uint32;
      description "Cmd Authorization Timeout counter";
    }
    leaf exec-account-req-counter {
      type uint32;
      description "Exec Accounting counter";
    }
    leaf exec-account-pass-counter {
      type uint32;
      description "Exec Accounting Success counter";
    }
    leaf exec-account-fail-counter {
      type uint32;
      description "Exec Accounting Fail counter";
    }
    leaf exec-account-error-counter {
      type uint32;
      description "Exec Accounting Error counter";
    }
    leaf exec-account-timeout-counter {
      type uint32;
      description "Exec Accounting Timeout counter";
    }
    leaf cmd-account-req-counter {
      type uint32;
      description "Cmd Accounting counter";
    }
    leaf cmd-account-pass-counter {
      type uint32;
      description "Cmd Accounting Success counter";
    }
    leaf cmd-account-fail-counter {
      type uint32;
      description "Cmd Accounting Fail counter";
    }
    leaf cmd-account-error-counter {
      type uint32;
      description "Cmd Accounting Error counter";
    }
    leaf cmd-account-timeout-counter {
      type uint32;
      description "Cmd Accounting Timeout counter";
    }
    leaf clear-counter-time {
      type int64;
      description "Last time counters are cleared";
    }
  }

  grouping TACACS-SERVERS {
    description "TACACS SERVERS";

    list server {
      description "server";
      uses TACACS-SERVERBAG;
    }
  }

  grouping TACACS-REQUESTBAG {
    description "TACACS REQUESTBAG";

    list tacacs-requestbag {
      description "address in tacascd proc space of this req";
      leaf time-remaining {
        type uint32;
        description "time remaining for this request";
      }
      leaf bytes-out {
        type uint32;
        units "byte";
        description "bytes written";
      }
      leaf out-pak-size {
        type uint32;
        description "size of the packet to be sent";
      }
      leaf bytes-in {
        type uint32;
        units "byte";
        description "bytes read from socket";
      }
      leaf in-pak-size {
        type uint32;
        description "size of the packet to be received";
      }
      leaf pak-type {
        type string;
        description "the type of packet";
      }
      leaf session-id {
        type int32;
        description "same as in pkt hdr";
      }
      leaf sock {
        type int32;
        description "socket number";
      }
    }
  }

  grouping TACACS-REQUESTS {
    description "TACACS REQUESTS";

    list request {
      description "request";
      uses TACACS-REQUESTBAG;
    }
  }

  grouping TACACS-SERVER-GROUP-BAG {
    description "TACACS SERVER GROUP BAG";
    leaf group-name {
      type string;
      description "name of the server group";
    }
    leaf sg-map-num {
      type uint32;
      description "server group mapped number";
    }
    leaf vrf-name {
      type string {
        length "0..33";
      }
      description "vrf of the group";
    }

    list server {
      description "list of servers in this group";
      uses TACACS-SERVERBAG;
    }
  }

  grouping TACACS-SERVERBAG {
    description "TACACS SERVERBAG";
    leaf addr {
      type inet:ipv4-address;
      description "IPv4 address of T+ server (if applicable)";
    }
    leaf timeout {
      type uint32;
      description "per-server timeout";
    }
    leaf port {
      type uint32;
      description "per server port to use";
    }
    leaf bytes-in {
      type uint32;
      units "byte";
      description "# of bytes read";
    }
    leaf bytes-out {
      type uint32;
      units "byte";
      description "# of bytes out";
    }
    leaf closes {
      type uint32;
      description "socket closes";
    }
    leaf opens {
      type uint32;
      description "socket opens";
    }
    leaf errors {
      type uint32;
      description "error count";
    }
    leaf aborts {
      type uint32;
      description "abort count";
    }
    leaf paks-in {
      type uint32;
      description "# of incoming packets read";
    }
    leaf paks-out {
      type uint32;
      description "# of outgoing packets sent";
    }
    leaf replies-expected {
      type uint32;
      description "# of replies expected to arrive";
    }
    leaf up {
      type boolean;
      description "is the server UP or down ?";
    }
    leaf conn-up {
      type boolean;
      description "is the server connected ?";
    }
    leaf single-connect {
      type boolean;
      description "is this a single connect server ?";
    }
    leaf is-private {
      type boolean;
      description "is this a private server ?";
    }
    leaf vrf-name {
      type string {
        length "0..33";
      }
      description "VRF in which server is reachable";
    }
    leaf addr-buf {
      type string {
        length "0..46";
      }
      description "internet address of T+ server";
    }
    leaf family {
      type string {
        length "0..5";
      }
      description "IP address Family";
    }
    leaf single-connect-idle-timeout {
      type uint32;
      description "Single connection idle timeout";
    }
    leaf connection-attempted {
      type int64;
      description "last attempted contact time";
    }
    leaf connection-timeout {
      type uint32;
      description "Server Connection timeout counter";
    }
    leaf connection-failure {
      type uint32;
      description "Server Connection failed counter";
    }
    leaf connection-disconnect {
      type uint32;
      description "Server connection disconnect counter";
    }
    leaf receive-error {
      type uint32;
      description "receive error counter";
    }
    leaf receive-timeout {
      type uint32;
      description "receive timeout counter";
    }
    leaf send-timeout {
      type uint32;
      description "Send timeout coutner";
    }
  }

  grouping TACACS-DETAILS {
    description "TACACS DETAILS";

    list server {
      description "server";
      uses TACACS-SERVERBAG;
    }

    list server-group {
      description "server group";
      uses TACACS-SERVER-GROUP-BAG;
    }

    list src-intf {
      description "src intf";
      uses TACACS-SRC-INTF;
    }
  }

  grouping TACACS-SRC-INTF {
    description "TACACS SRC INTF";
    leaf interface-name {
      type string;
      description "Name of the source interface";
    }
    leaf ipaddrv4 {
      type string;
      description "IP address buffer";
    }
    leaf ipaddrv6 {
      type string;
      description "IP address buffer";
    }
    leaf vrfid {
      type uint32;
      description "VRF Id";
    }
  }

  grouping TACACS-SOURCE-INTERFACES {
    description "TACACS SOURCE INTERFACES";

    list list-of-source-interface {
      description "List of source interfaces";
      uses TACACS-SRC-INTF;
    }
  }
}
