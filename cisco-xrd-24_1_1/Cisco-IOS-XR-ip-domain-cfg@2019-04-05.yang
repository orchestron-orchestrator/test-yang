module Cisco-IOS-XR-ip-domain-cfg {

  /*** NAMESPACE / PREFIX DEFINITION ***/

  namespace "http://cisco.com/ns/yang/Cisco-IOS-XR-ip-domain-cfg";


  prefix "ip-domain-cfg";

  /*** LINKAGE (IMPORTS / INCLUDES) ***/

  import ietf-inet-types { prefix "inet"; }

  import Cisco-IOS-XR-types { prefix "xr"; }

  import cisco-semver { prefix "semver"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ip-domain package configuration.

     This module contains definitions
     for the following management objects:
       ip-domain: IP domain configuration

     Copyright (c) 2013-2019 by Cisco Systems, Inc.
     All rights reserved.";

  revision "2019-04-05" {
    description
      "Establish semantic version baseline.";
    semver:module-version "1.0.1";
  }

  revision "2019-02-19" {
    description
      "Domains default flows Disable support.";
  }

  revision "2017-09-07" {
    description
      "Fixed type translation error.";
  }

  revision "2015-05-13" {
    description
      "IOS XR 5.3.2 revision.";
  }

  revision "2015-01-07" {
    description
      "IOS XR 5.3.1 revision.";
  }

  container ip-domain {
    description "IP domain configuration";

    container vrfs {
      description "VRF table";

      list vrf {
        key "vrf-name";
        description "VRF specific data";

        container ipv6-hosts {
          description "IPv6 host";

          list ipv6-host {
            key "host-name";
            description "Host name and up to 4 host IPv6 addresses";
            leaf host-name {
              type string;
              description "A hostname";
            }
            leaf-list address {
              type inet:ipv6-address-no-zone;
              min-elements "1";
              max-elements "4";
              description "Host IPv6 addresses";
            }
          }
        }

        container servers {
          description "Name server addresses";

          list server {
            key "order server-address";
            description "Name server address";
            leaf order {
              type uint32;
              description
                "This is used to sort the servers in the
                order of precedence";
            }
            leaf server-address {
              type inet:ip-address-no-zone;
              description "A name server address";
            }
          }
        }

        container lists {
          description
            "Domain names to complete unqualified host
            names";

          list list {
            key "order list-name";
            description
              "Domain name to complete unqualified host
              names";
            leaf order {
              type uint32;
              description
                "This is used to sort the names in the order
                of precedence";
            }
            leaf list-name {
              type xr:Cisco-ios-xr-string;
              description "A domain name";
            }
          }
        }

        container ipv4-hosts {
          description "IPv4 host";

          list ipv4-host {
            key "host-name";
            description "Host name and up to 8 host IPv4 addresses";
            leaf host-name {
              type string;
              description "A hostname";
            }
            leaf-list address {
              type inet:ipv4-address-no-zone;
              min-elements "1";
              max-elements "8";
              description "Host IPv4 addresses";
            }
          }
        }
        leaf lookup {
          type empty;
          description
            "Disable Domain Name System hostname
            translation";
        }
        leaf multicast-domain {
          type string;
          description "Default multicast domain name";
        }
        leaf source-interface {
          type xr:Interface-name;
          description
            "Specify interface for source address in
            connections";
        }
        leaf name {
          type string;
          description "Default domain name";
        }
        leaf vrf-name {
          type xr:Cisco-ios-xr-string;
          description "Name of the VRF instance";
        }
      }
    }
    leaf default-flows-disable {
      type empty;
      description "Disable default flows programming";
    }
  }
}
