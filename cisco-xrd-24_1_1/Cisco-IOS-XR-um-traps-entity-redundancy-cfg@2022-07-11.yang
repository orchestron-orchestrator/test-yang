module Cisco-IOS-XR-um-traps-entity-redundancy-cfg {

  /*** NAMESPACE / PREFIX DEFINITION ***/

  namespace "http://cisco.com/ns/yang/Cisco-IOS-XR-um-traps-entity-redundancy-cfg";
  prefix um-traps-entity-redundancy-cfg;

  /*** LINKAGE (IMPORTS / INCLUDES) ***/

  import Cisco-IOS-XR-um-snmp-server-cfg {
    prefix a1;
  }

  import cisco-semver { prefix "semver"; }

  /*** META INFORMATION ***/

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR traps-entity-redundancy package configuration.

     This YANG module augments the
     modules with configuration data.

     Copyright (c) 2020-2022 by Cisco Systems, Inc.
     All rights reserved.";

  revision 2022-07-11 {
    description
      "Added missing description statement to nodes";
    semver:module-version "1.0.0";
  }

  revision "2020-04-24" {
    description
      "Initial release";
    semver:module-version "1.0.0";
  }

  augment "/a1:snmp-server/a1:traps" {
    description
      "This augment extends snmp-server traps nodes
       configuration";
    container entity-redundancy {
      description
        "Enable SNMP CISCO-ENTITY-REDUNDANCY-MIB traps";
      container all {
        presence "Indicates a all node is configured.";
        description
          "Enable all CISCO-ENTITY-REDUNDANCY-MIB traps";
      }
      container switchover {
        presence "Indicates a switchover node is configured.";
        description
          "Enable switchover traps";
      }
      container status {
        presence "Indicates a status node is configured.";
        description
          "Enable status change traps";
      }
    }
  }
}
