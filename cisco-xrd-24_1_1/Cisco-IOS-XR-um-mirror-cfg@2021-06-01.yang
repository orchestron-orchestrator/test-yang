module Cisco-IOS-XR-um-mirror-cfg {

  /*** NAMESPACE / PREFIX DEFINITION ***/

  namespace "http://cisco.com/ns/yang/Cisco-IOS-XR-um-mirror-cfg";
  prefix um-mirror-cfg;

  /*** LINKAGE (IMPORTS / INCLUDES) ***/
  import cisco-semver { prefix "semver"; }

  /*** META INFORMATION ***/

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR mirror package configuration.

     This YANG module augments the
     modules with configuration data.

     Copyright (c) 2020-2022 by Cisco Systems, Inc.
     All rights reserved.";

  revision 2021-06-01 {
    description
      "Initial release";
    semver:module-version "1.0.0";
  }


  container mirror {
    description
      "Configure settings for mirror directory";
    container enable {
      presence "Indicates a enable node is configured.";
      description
        "Enable mirror directory. This config is no longer required since mirror_server is now always enabled.";
      container checksum {
        presence "Indicates a checksum node is configured.";
        description
          "rsync will use --checksum option for determining if file is in sync";
      }
    }
  }
}
