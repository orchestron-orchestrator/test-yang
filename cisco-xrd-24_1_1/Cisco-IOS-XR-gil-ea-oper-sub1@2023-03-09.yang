submodule Cisco-IOS-XR-gil-ea-oper-sub1 {

  belongs-to Cisco-IOS-XR-gil-ea-oper {
    prefix Cisco-IOS-XR-gil-ea-oper;
  }

  /*** LINKAGE (IMPORTS / INCLUDES) ***/

  import cisco-semver { prefix "semver"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR gil-ea package operational data.

     Copyright (c) 2013-2023 by Cisco Systems, Inc.
     All rights reserved.";

  revision "2023-03-09" {
    description
      "Initial GIL EA Support";
    semver:module-version "1.0.0";
  }

  revision "2019-04-05" {
    description
      "Establish semantic version baseline.";
  }

  revision "2015-11-09" {
    description
      "IOS XR 6.0 revision.";
  }

  typedef Im-state {
    type uint32;
    description "Im state";
  }

  grouping GIL-EA-IDB-CONTENT {
    description "GIL IDB content";
    leaf interface-state {
      type Im-state;
      description "Interface state";
    }
    leaf interface-np-umask {
      type uint32;
      description "Interface NPU mask";
    }
    leaf interface-type {
      type string;
      description "Interface Type";
    }
  }

  grouping GIL-EA-IDB-KEY {
    description "GIL IDB key";
    leaf gil-name {
      type string;
      description "generic-interface-list name";
    }
  }

  grouping GIL-EA-IDB {
    description "Generic Interface List IDB";

    container key {
      description "GIL IDB key";
      uses GIL-EA-IDB-KEY;
    }

    container content {
      description "GIL IDB content";
      uses GIL-EA-IDB-CONTENT;
    }
  }
}
