module Cisco-IOS-XR-ip-rsvp-oper {

  /*** NAMESPACE / PREFIX DEFINITION ***/

  namespace "http://cisco.com/ns/yang/Cisco-IOS-XR-ip-rsvp-oper";


  prefix "ip-rsvp-oper";

  /*** LINKAGE (IMPORTS / INCLUDES) ***/

  import ietf-inet-types { prefix "inet"; }

  import Cisco-IOS-XR-types { prefix "xr"; }

  import cisco-semver { prefix "semver"; }

  include Cisco-IOS-XR-ip-rsvp-oper-sub1 {
    revision-date 2023-10-10;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ip-rsvp package operational data.

     This module contains definitions
     for the following management objects:
       rsvp-standby: RSVP operational data for standby role
       rsvp: RSVP operational data

     Copyright (c) 2013-2023 by Cisco Systems, Inc.
     All rights reserved.";

  revision "2023-10-10" {
    description
      "Added leaf is-global-retransmit-timer-configured
       2023-06-26
         Added a leaf to indicate whether refresh reduction is enabled globally.";
    semver:module-version "2.0.0";
  }

  revision "2019-04-05" {
    description
      "Establish semantic version baseline.";
    semver:module-version "1.0.0";
  }

  revision "2017-09-07" {
    description
      "Fixed type translation error.";
  }

  revision "2017-05-01" {
    description
      "Fixing backward compatibility error in module.";
  }

  revision "2015-11-09" {
    description
      "IOS XR 6.0 revision.";
  }

  typedef Rsvp-mode {
    type enumeration {
      enum send {
        value 0;
        description "Send";
      }
      enum receive {
        value 1;
        description "Receive";
      }
    }
    description "Rsvp mode";
  }
  typedef Rsvp-session {
    type enumeration {
      enum ipv4 {
        value 1;
        description "Show IPv4 sessions only";
      }
      enum p2p-lsp-ipv4 {
        value 7;
        description "Show IPv4 P2P LSP sessions only";
      }
      enum ouni-ipv4 {
        value 9;
        description "Show IPv4 OUNI sessions only";
      }
      enum p2mp-lsp-ipv4 {
        value 13;
        description "Show IPv4 P2MP LSP sessions only";
      }
    }
    description "Rsvp session";
  }

  grouping INTERFACE-NEIGHBOR-DETAIL-TABLE {
    description "Common node of rsvp, rsvp-standby";

    container interface-neighbor-details {
      description "Table of detailed info about I/F neighbors";

      list interface-neighbor-detail {
        key "neighbor-address";
        description "Detailed info for a single interface neighbor";
        leaf neighbor-address {
          type inet:ipv4-address-no-zone;
          description "Address of global neighbor";
        }
        uses RSVP-MGMT-NBR-DETAIL;
      }
    }
  }

  grouping COUNTERS {
    description "Common node of rsvp, rsvp-standby";

    container counters {
      description "Counters";

      container interface-messages {
        description "Table of message counters";

        list interface-message {
          key "interface-name";
          description "Interface message counters";
          leaf interface-name {
            type xr:Interface-name;
            description
              "Interface Name. 'None' is used internally
              where the true interface is unknown (e.g. for
              routed packets)";
          }
          uses RSVP-MGMT-COUNT-MESSAGE;
        }
      }

      container message-summary {
        description
          "Summary information for all RSVP message
          counters";
        uses RSVP-MGMT-COUNT-MESSAGE;
      }

      container prefix-filtering {
        description "Prefix filtering counters";

        container accesses {
          description
            "AccessList specific prefix filtering counters";

          list access {
            key "access-list-name";
            description
              "Prefix filtering counters for a specific
              AccessList";
            leaf access-list-name {
              type xr:Cisco-ios-xr-string {
                length "1..65";
              }
              description "AccessList Name";
            }
            uses RSVP-MGMT-COUNT-PREFIX-ACL-INFO;
          }
        }

        container interfaces {
          description
            "Interface specific prefix filtering counters";

          container summary {
            description
              "Summary of prefix filtering counts for all
              interfaces";
            uses RSVP-MGMT-COUNT-PREFIX-INTERFACE-INFO;
          }

          container interfaces {
            description
              "Table of interface specific prefix filtering
              counters";

            list interface {
              key "interface-name";
              description
                "Prefix filtering counters for a specific
                interface";
              leaf interface-name {
                type xr:Cisco-ios-xr-string;
                description
                  "Interface Name. 'None' is used internally
                  where the true interface is unknown (e.g.
                  for routed packets)";
              }
              uses RSVP-MGMT-COUNT-PREFIX-INTERFACE-INFO;
            }
          }
        }
      }

      container out-of-resource {
        description "Out of resource counters";

        container interfaces {
          description "Interface specific out of resource counters";

          container summary {
            description
              "Summary of out of resource counts for all
              interfaces";
            uses RSVP-MGMT-COUNTERS-OOR;
          }

          container interfaces {
            description
              "Table of interface specific out of resource
              counters";

            list interface {
              key "interface-name";
              description
                "Out of resource counters for a specific
                interface";
              leaf interface-name {
                type xr:Cisco-ios-xr-string;
                description
                  "Interface Name. 'None' is used internally
                  where the true interface is unknown (e.g.
                  for routed packets)";
              }
              uses RSVP-MGMT-COUNTERS-OOR;
            }
          }
        }
      }

      container interface-events {
        description "Event counters";

        list interface-event {
          key "interface-name";
          description "Event counters for an interface";
          leaf interface-name {
            type xr:Interface-name;
            description
              "Interface Name. 'None' is used internally
              where the true interface is unknown (e.g. for
              routed packets)";
          }
          uses RSVP-MGMT-EVENT-COUNT-INFO;
        }
      }

      container nsr {
        description "Summary information for all RSVP NSR counters";
        uses RSVP-SYNC-COUNT-INFO;
      }

      container issu {
        description
          "Summary information for all RSVP ISSU counters";
        uses RSVP-SYNC-COUNT-INFO;
      }

      container database {
        description
          "Summary information for all RSVP database
          counters";
        uses RSVP-MGMT-ALL-DB-COUNTERS;
      }

      container event-syncs {
        description "Table containing event sync counters";

        list event-sync {
          key "interface-name";
          description "Event sync counters";
          leaf interface-name {
            type xr:Interface-name;
            description "Interface Name";
          }
          uses RSVP-MGMT-EVENT-COUNT-INFO;
        }
      }
    }
  }

  grouping HELLO-INTERFACE-INSTANCE-DETAIL-TABLE {
    description "Common node of rsvp, rsvp-standby";

    container hello-interface-instance-details {
      description
        "Table of detailed info about i/f-based hello
        instances";

      list hello-interface-instance-detail {
        key "source-address destination-address";
        description
          "Detailed info for a single interface-based
          hello instance";
        leaf source-address {
          type inet:ipv4-address-no-zone;
          description "Source Address";
        }
        leaf destination-address {
          type inet:ipv4-address-no-zone;
          description "Destination Address";
        }
        uses RSVP-MGMT-HELLO-IF-INSTANCE-DETAIL;
      }
    }
  }

  grouping AUTHENTICATION-BRIEF-TABLE {
    description "Common node of rsvp, rsvp-standby";

    container authentication-briefs {
      description "Table for Authentication related information";

      list authentication-brief {
        key "source-address destination-address mode-id"+
          " interface-name";
        description "Brief Authentication information";
        leaf source-address {
          type inet:ipv4-address-no-zone;
          description "Source Address";
        }
        leaf destination-address {
          type inet:ipv4-address-no-zone;
          description "Destination Address";
        }
        leaf mode-id {
          type Rsvp-mode;
          description "Mode (Tx or Rx)";
        }
        leaf interface-name {
          type xr:Interface-name;
          description "InterfaceName";
        }
        uses RSVP-MGMT-AUTHENTICATION-COMPACT;
      }
    }
  }

  grouping REQUEST-DETAIL-TABLE {
    description "Common node of rsvp, rsvp-standby";

    container request-details {
      description "Table of detail info about requests";

      list request-detail {
        description "Detail info for a request";
        leaf destination-address {
          type inet:ipv4-address-no-zone;
          description "Destination Address";
        }
        leaf destination-port {
          type uint32;
          description "Destination Port";
        }
        leaf protocol {
          type uint32;
          description "Protocol";
        }
        leaf extended-tunnel-id {
          type inet:ipv4-address-no-zone;
          description "Extended Tunnel ID";
        }
        leaf session-type {
          type Rsvp-session;
          description "Session Type";
        }
        leaf p2mp-id {
          type uint32;
          description "P2MP ID";
        }
        leaf source-address {
          type inet:ipv4-address-no-zone;
          description "Source Address";
        }
        leaf source-port {
          type uint32;
          description "Source Port";
        }
        leaf sub-group-origin {
          type inet:ipv4-address-no-zone;
          description "Subgroup Origin";
        }
        leaf sub-group-id {
          type uint32;
          description "Subgroup ID";
        }
        leaf vrf-name {
          type xr:Cisco-ios-xr-string;
          description "VRF Name";
        }
        uses RSVP-MGMT-REQUEST-DETAIL;
      }
    }
  }

  grouping RSB-BRIEF-TABLE {
    description "Common node of rsvp, rsvp-standby";

    container rsb-briefs {
      description
        "Table of brief info about reservation state
        blocks";

      list rsb-brief {
        description
          "Brief info for a single reservation state block";
        leaf destination-address {
          type inet:ipv4-address-no-zone;
          description "Destination Address";
        }
        leaf destination-port {
          type uint32;
          description "Destination Port";
        }
        leaf protocol {
          type uint32;
          description "Protocol";
        }
        leaf extended-tunnel-id {
          type inet:ipv4-address-no-zone;
          description "Extended Tunnel ID";
        }
        leaf session-type {
          type Rsvp-session;
          description "Session Type";
        }
        leaf p2mp-id {
          type uint32;
          description "P2MP ID";
        }
        leaf source-address {
          type inet:ipv4-address-no-zone;
          description "Source Address";
        }
        leaf source-port {
          type uint32;
          description "Source Port ";
        }
        leaf sub-group-origin {
          type inet:ipv4-address-no-zone;
          description "Subgroup Origin";
        }
        leaf sub-group-id {
          type uint32;
          description "Subgroup ID";
        }
        leaf vrf-name {
          type xr:Cisco-ios-xr-string;
          description "VRF Name";
        }
        uses RSVP-MGMT-RESERVATION-COMPACT;
      }
    }
  }

  grouping REQUEST-BRIEF-TABLE {
    description "Common node of rsvp, rsvp-standby";

    container request-briefs {
      description "Table of brief info about requests";

      list request-brief {
        description "Brief info for a request";
        leaf destination-address {
          type inet:ipv4-address-no-zone;
          description "Destination Address";
        }
        leaf destination-port {
          type uint32;
          description "Destination Port";
        }
        leaf protocol {
          type uint32;
          description "Protocol";
        }
        leaf extended-tunnel-id {
          type inet:ipv4-address-no-zone;
          description "Extended Tunnel ID";
        }
        leaf session-type {
          type Rsvp-session;
          description "Session Type";
        }
        leaf p2mp-id {
          type uint32;
          description "P2MP ID";
        }
        leaf source-address {
          type inet:ipv4-address-no-zone;
          description "Source Address";
        }
        leaf source-port {
          type uint32;
          description "Source Port";
        }
        leaf sub-group-origin {
          type inet:ipv4-address-no-zone;
          description "Subgroup Origin";
        }
        leaf sub-group-id {
          type uint32;
          description "Subgroup ID";
        }
        leaf vrf-name {
          type xr:Cisco-ios-xr-string;
          description "VRF Name";
        }
        uses RSVP-MGMT-REQUEST-COMPACT;
      }
    }
  }

  grouping HELLO-INTERFACE-INSTANCE-BRIEF-TABLE {
    description "Common node of rsvp, rsvp-standby";

    container hello-interface-instance-briefs {
      description
        "Table of brief info about i/f-based hello
        instances";

      list hello-interface-instance-brief {
        key "source-address destination-address";
        description
          "Brief info for a single interface-based hello
          instance";
        leaf source-address {
          type inet:ipv4-address-no-zone;
          description "Source Address";
        }
        leaf destination-address {
          type inet:ipv4-address-no-zone;
          description "Destination Address";
        }
        uses RSVP-MGMT-HELLO-IF-INSTANCE-COMPACT;
      }
    }
  }

  grouping INTERFACE-NEIGHBOR-BRIEF-TABLE {
    description "Common node of rsvp, rsvp-standby";

    container interface-neighbor-briefs {
      description "Table of brief info about I/F neighbors";

      list interface-neighbor-brief {
        key "neighbor-address";
        description "Brief info for a single interface neighbor";
        leaf neighbor-address {
          type inet:ipv4-address-no-zone;
          description "Address of global neighbor";
        }
        uses RSVP-MGMT-NBR-COMPACT;
      }
    }
  }

  grouping PSB-BRIEF-TABLE {
    description "Common node of rsvp, rsvp-standby";

    container psb-briefs {
      description "Table of brief info about path state blocks";

      list psb-brief {
        description "Brief info for a single path state block";
        leaf destination-address {
          type inet:ipv4-address-no-zone;
          description "Destination Address";
        }
        leaf destination-port {
          type uint32;
          description "Destination Port";
        }
        leaf protocol {
          type uint32;
          description "Protocol";
        }
        leaf extended-tunnel-id {
          type inet:ipv4-address-no-zone;
          description "Extended Tunnel ID";
        }
        leaf session-type {
          type Rsvp-session;
          description "Session Type";
        }
        leaf p2mp-id {
          type uint32;
          description "P2MP ID";
        }
        leaf source-address {
          type inet:ipv4-address-no-zone;
          description "Source Address";
        }
        leaf source-port {
          type uint32;
          description "Source Port ";
        }
        leaf sub-group-origin {
          type inet:ipv4-address-no-zone;
          description "Subgroup Origin";
        }
        leaf sub-group-id {
          type uint32;
          description "Subgroup ID";
        }
        leaf vrf-name {
          type xr:Cisco-ios-xr-string;
          description "VRF Name";
        }
        uses RSVP-MGMT-PATH-COMPACT;
      }
    }
  }

  grouping GLOBAL-NEIGHBOR-BRIEF-TABLE {
    description "Common node of rsvp, rsvp-standby";

    container global-neighbor-briefs {
      description "Table of brief info about global neighbors";

      list global-neighbor-brief {
        key "neighbor-address";
        description "Brief info for a single global neighbor";
        leaf neighbor-address {
          type inet:ipv4-address-no-zone;
          description "Address of global neighbor";
        }
        uses RSVP-MGMT-GLBL-NBR-COMPACT;
      }
    }
  }

  grouping SESSION-DETAILED-TABLE {
    description "Common node of rsvp, rsvp-standby";

    container session-detaileds {
      description "Table of detailed info about sessions";

      list session-detailed {
        description "Detailed info about session";
        leaf destination-address {
          type inet:ipv4-address-no-zone;
          description "Destination Address";
        }
        leaf destination-port {
          type uint32;
          description "Destination Port";
        }
        leaf protocol {
          type uint32;
          description "Protocol";
        }
        leaf extended-tunnel-id {
          type inet:ipv4-address-no-zone;
          description "Extended Tunnel ID";
        }
        leaf session-type {
          type Rsvp-session;
          description "Session Type";
        }
        leaf p2mp-id {
          type uint32;
          description "P2MP ID";
        }
        leaf vrf-name {
          type xr:Cisco-ios-xr-string;
          description "VRF Name";
        }
        uses RSVP-MGMT-SESSION-DETAIL;
      }
    }
  }

  grouping AUTHENTICATION-DETAIL-TABLE {
    description "Common node of rsvp, rsvp-standby";

    container authentication-details {
      description
        "Table for detailed authentication related
        information";

      list authentication-detail {
        key "source-address destination-address mode-id"+
          " interface-name";
        description "Brief Authentication information";
        leaf source-address {
          type inet:ipv4-address-no-zone;
          description "Source Address";
        }
        leaf destination-address {
          type inet:ipv4-address-no-zone;
          description "Destination Address";
        }
        leaf mode-id {
          type Rsvp-mode;
          description "Mode (Tx or Rx)";
        }
        leaf interface-name {
          type xr:Interface-name;
          description "InterfaceName";
        }
        uses RSVP-MGMT-AUTHENTICATION-DETAIL;
      }
    }
  }

  grouping GLOBAL-NEIGHBOR-DETAIL-TABLE {
    description "Common node of rsvp, rsvp-standby";

    container global-neighbor-details {
      description "Table of detailed info about global neighbors";

      list global-neighbor-detail {
        key "neighbor-address";
        description "Detail info for a single global neighbor";
        leaf neighbor-address {
          type inet:ipv4-address-no-zone;
          description "Address of global neighbor";
        }
        uses RSVP-MGMT-GLBL-NBR-DETAIL;
      }
    }
  }

  grouping INTERFACE-SUMMARY-TABLE {
    description "Common node of rsvp, rsvp-standby";

    container interface-summaries {
      description
        "Table of summary info about RSVP-enabled
        interfaces";

      list interface-summary {
        key "interface-name";
        description "Summary info about an RSVP-enabled interface";
        leaf interface-name {
          type xr:Interface-name;
          description "Interface Name";
        }
        uses RSVP-MGMT-INTERFACE-SUMMARY;
      }
    }
  }

  grouping INTERFACE-BRIEF-TABLE {
    description "Common node of rsvp, rsvp-standby";

    container interface-briefs {
      description
        "Table of brief info about RSVP-enabled
        interfaces";

      list interface-brief {
        key "interface-name";
        description "Brief info about an RSVP-enabled interface";
        leaf interface-name {
          type xr:Interface-name;
          description "Interface Name";
        }
        uses RSVP-MGMT-INTERFACE-COMPACT;
      }
    }
  }

  grouping HELLO-INSTANCE-DETAIL-TABLE {
    description "Common node of rsvp, rsvp-standby";

    container hello-instance-details {
      description "Table of detailed info about hello instances";

      list hello-instance-detail {
        key "source-address destination-address";
        description "Detailed info for a single hello instance";
        leaf source-address {
          type inet:ipv4-address-no-zone;
          description "Source Address";
        }
        leaf destination-address {
          type inet:ipv4-address-no-zone;
          description "Destination Address";
        }
        uses RSVP-MGMT-HELLO-INSTANCE-DETAIL;
      }
    }
  }

  grouping SUMMARY {
    description "Common node of rsvp, rsvp-standby";

    container summary {
      description "RSVP summary information";
      uses RSVP-GLOBAL-INFO;
    }
  }

  grouping PSB-DETAILED-TABLE {
    description "Common node of rsvp, rsvp-standby";

    container psb-detaileds {
      description "Table of detailed info about path state blocks";

      list psb-detailed {
        description "Detailed info for a single path state block";
        leaf destination-address {
          type inet:ipv4-address-no-zone;
          description "Destination Address";
        }
        leaf destination-port {
          type uint32;
          description "Destination Port";
        }
        leaf protocol {
          type uint32;
          description "Protocol";
        }
        leaf extended-tunnel-id {
          type inet:ipv4-address-no-zone;
          description "Extended Tunnel ID";
        }
        leaf session-type {
          type Rsvp-session;
          description "Session Type";
        }
        leaf p2mp-id {
          type uint32;
          description "P2MP ID";
        }
        leaf source-address {
          type inet:ipv4-address-no-zone;
          description "Source Address";
        }
        leaf source-port {
          type uint32;
          description "Source Port ";
        }
        leaf sub-group-origin {
          type inet:ipv4-address-no-zone;
          description "Subgroup Origin";
        }
        leaf sub-group-id {
          type uint32;
          description "Subgroup ID";
        }
        leaf vrf-name {
          type xr:Cisco-ios-xr-string;
          description "VRF Name";
        }
        uses RSVP-MGMT-PATH-DETAIL;
      }
    }
  }

  grouping NSR {
    description "Common node of rsvp, rsvp-standby";

    container nsr {
      description "RSVP NSR information";

      container status {
        description "RSVP NSR status information";
        uses RSVP-NSR-ISSU-STATUS-INFO;
      }
    }
  }

  grouping GRACEFUL-RESTART {
    description "Common node of rsvp, rsvp-standby";

    container graceful-restart {
      description "Info about graceful-restart";
      uses RSVP-MGMT-GRACEFUL-RESTART;
    }
  }

  grouping FRR-SUMMARY {
    description "Common node of rsvp, rsvp-standby";

    container frr-summary {
      description "Fast Re-Route Summary State Information";
      uses RSVP-MGMT-FRR-STATES-COMPACT;
    }
  }

  grouping RSB-DETAILED-TABLE {
    description "Common node of rsvp, rsvp-standby";

    container rsb-detaileds {
      description
        "Table of detailed info about reservation state
        blocks";

      list rsb-detailed {
        description
          "Detailed info for a single reservation state
          block";
        leaf destination-address {
          type inet:ipv4-address-no-zone;
          description "Destination Address";
        }
        leaf destination-port {
          type uint32;
          description "Destination Port";
        }
        leaf protocol {
          type uint32;
          description "Protocol";
        }
        leaf extended-tunnel-id {
          type inet:ipv4-address-no-zone;
          description "Extended Tunnel ID";
        }
        leaf session-type {
          type Rsvp-session;
          description "Session Type";
        }
        leaf p2mp-id {
          type uint32;
          description "P2MP ID";
        }
        leaf source-address {
          type inet:ipv4-address-no-zone;
          description "Source Address";
        }
        leaf source-port {
          type uint32;
          description "Source Port ";
        }
        leaf sub-group-origin {
          type inet:ipv4-address-no-zone;
          description "Subgroup Origin";
        }
        leaf sub-group-id {
          type uint32;
          description "Subgroup ID";
        }
        leaf vrf-name {
          type xr:Cisco-ios-xr-string;
          description "VRF Name";
        }
        uses RSVP-MGMT-RESERVATION-DETAIL;
      }
    }
  }

  grouping HELLO-INSTANCE-BRIEF-TABLE {
    description "Common node of rsvp, rsvp-standby";

    container hello-instance-briefs {
      description "Table of brief info about hello instances";

      list hello-instance-brief {
        key "source-address destination-address";
        description "Brief info for a single hello instance";
        leaf source-address {
          type inet:ipv4-address-no-zone;
          description "Source Address";
        }
        leaf destination-address {
          type inet:ipv4-address-no-zone;
          description "Destination Address";
        }
        uses RSVP-MGMT-HELLO-INSTANCE-COMPACT;
      }
    }
  }

  grouping FRR-TABLE {
    description "Common node of rsvp, rsvp-standby";

    container frrs {
      description
        "Table of detailed info about Fast Re-route
        states";

      list frr {
        description
          "Detailed info for a single Fast Re-route state";
        leaf destination-address {
          type inet:ipv4-address-no-zone;
          description "Destination Address";
        }
        leaf destination-port {
          type uint32;
          description "Destination Port";
        }
        leaf protocol {
          type uint32;
          description "Protocol";
        }
        leaf extended-tunnel-id {
          type inet:ipv4-address-no-zone;
          description "Extended Tunnel ID";
        }
        leaf session-type {
          type Rsvp-session;
          description "Session Type";
        }
        leaf p2mp-id {
          type uint32;
          description "P2MP ID";
        }
        leaf source-address {
          type inet:ipv4-address-no-zone;
          description "Source Address";
        }
        leaf source-port {
          type uint32;
          description "Source Port";
        }
        leaf sub-group-origin {
          type inet:ipv4-address-no-zone;
          description "Subgroup Origin";
        }
        leaf sub-group-id {
          type uint32;
          description "Subgroup ID";
        }
        leaf vrf-name {
          type xr:Cisco-ios-xr-string;
          description "VRF Name";
        }
        uses RSVP-MGMT-FRR-STATES-DETAIL;
      }
    }
  }

  grouping CONTROLLER-SUMMARY-TABLE {
    description "Common node of rsvp, rsvp-standby";

    container controller-summaries {
      description
        "Table of summary info about RSVP-enabled
        controllers";

      list controller-summary {
        key "controller-name";
        description "Summary info about an RSVP-enabled controller";
        leaf controller-name {
          type xr:Interface-name;
          description "Controller Name";
        }
        uses RSVP-MGMT-INTERFACE-SUMMARY;
      }
    }
  }

  grouping SESSION-BRIEF-TABLE {
    description "Common node of rsvp, rsvp-standby";

    container session-briefs {
      description "Table of brief info about sessions";

      list session-brief {
        description "Brief info about session";
        leaf destination-address {
          type inet:ipv4-address-no-zone;
          description "Destination Address";
        }
        leaf destination-port {
          type uint32;
          description "Destination Port";
        }
        leaf protocol {
          type uint32;
          description "Protocol";
        }
        leaf extended-tunnel-id {
          type inet:ipv4-address-no-zone;
          description "Extended Tunnel ID";
        }
        leaf session-type {
          type Rsvp-session;
          description "Session Type";
        }
        leaf p2mp-id {
          type uint32;
          description "P2MP ID";
        }
        leaf vrf-name {
          type xr:Cisco-ios-xr-string;
          description "VRF Name";
        }
        uses RSVP-MGMT-SESSION-COMPACT;
      }
    }
  }

  grouping INTERFACE-DETAILED-TABLE {
    description "Common node of rsvp, rsvp-standby";

    container interface-detaileds {
      description
        "Table of detailed info about RSVP-enabled
        interfaces";

      list interface-detailed {
        key "interface-name";
        description "Detailed info about an RSVP-enabled interface";
        leaf interface-name {
          type xr:Interface-name;
          description "Interface Name";
        }
        uses RSVP-MGMT-INTERFACE-DETAIL;
      }
    }
  }

  grouping CONTROLLER-BRIEF-TABLE {
    description "Common node of rsvp, rsvp-standby";

    container controller-briefs {
      description
        "Table of brief info about RSVP-enabled
        controller";

      list controller-brief {
        key "controller-name";
        description "Brief info about an RSVP-enabled controller";
        leaf controller-name {
          type xr:Interface-name;
          description "Controller Name";
        }
        uses RSVP-MGMT-INTERFACE-COMPACT;
      }
    }
  }

  grouping CONTROLLER-DETAILED-TABLE {
    description "Common node of rsvp, rsvp-standby";

    container controller-detaileds {
      description
        "Table of detailed info about RSVP-enabled
        controllers";

      list controller-detailed {
        key "controller-name";
        description
          "Detailed info about an RSVP-enabled controller";
        leaf controller-name {
          type xr:Interface-name;
          description "Controller Name";
        }
        uses RSVP-MGMT-INTERFACE-DETAIL;
      }
    }
  }

  container rsvp-standby {
    config false;
    description "RSVP operational data for standby role";
    uses INTERFACE-NEIGHBOR-BRIEF-TABLE;
    uses CONTROLLER-SUMMARY-TABLE;
    uses AUTHENTICATION-BRIEF-TABLE;
    uses SESSION-BRIEF-TABLE;
    uses PSB-DETAILED-TABLE;
    uses CONTROLLER-DETAILED-TABLE;
    uses FRR-SUMMARY;
    uses RSB-DETAILED-TABLE;
    uses INTERFACE-SUMMARY-TABLE;
    uses HELLO-INSTANCE-BRIEF-TABLE;
    uses AUTHENTICATION-DETAIL-TABLE;
    uses RSB-BRIEF-TABLE;
    uses COUNTERS;
    uses INTERFACE-DETAILED-TABLE;
    uses CONTROLLER-BRIEF-TABLE;
    uses GRACEFUL-RESTART;
    uses HELLO-INTERFACE-INSTANCE-BRIEF-TABLE;
    uses HELLO-INTERFACE-INSTANCE-DETAIL-TABLE;
    uses INTERFACE-NEIGHBOR-DETAIL-TABLE;
    uses NSR;
    uses SUMMARY;
    uses FRR-TABLE;
    uses REQUEST-BRIEF-TABLE;
    uses REQUEST-DETAIL-TABLE;
    uses INTERFACE-BRIEF-TABLE;
    uses SESSION-DETAILED-TABLE;
    uses HELLO-INSTANCE-DETAIL-TABLE;
    uses GLOBAL-NEIGHBOR-DETAIL-TABLE;
    uses PSB-BRIEF-TABLE;
    uses GLOBAL-NEIGHBOR-BRIEF-TABLE;
  }

  container rsvp {
    config false;
    description "RSVP operational data";

    container issu {
      description "RSVP ISSU information";

      container status {
        description "RSVP ISSU status information";
        uses RSVP-NSR-ISSU-STATUS-INFO;
      }
    }

    container bw-pool-info {
      description "All B/W Pool info";
      uses RSVP-MGMT-GLBL-BW-POOL-INFO;
    }

    container pxsb-details {
      description "Table of detailed PXSB info";

      list pxsb-detail {
        description "Detailed PXSB info";
        leaf destination-address {
          type inet:ipv4-address-no-zone;
          description "Destination Address";
        }
        leaf destination-port {
          type uint32;
          description "Destination Port";
        }
        leaf protocol {
          type uint32;
          description "Protocol";
        }
        leaf extended-tunnel-id {
          type inet:ipv4-address-no-zone;
          description "Extended Tunnel ID";
        }
        leaf session-type {
          type Rsvp-session;
          description "Session Type";
        }
        leaf p2mp-id {
          type uint32;
          description "P2MP ID";
        }
        leaf source-address {
          type inet:ipv4-address-no-zone;
          description "Source Address";
        }
        leaf source-port {
          type uint32;
          description "Source Port";
        }
        leaf sub-group-origin {
          type inet:ipv4-address-no-zone;
          description "Subgroup Origin";
        }
        leaf sub-group-id {
          type uint32;
          description "Subgroup ID";
        }
        leaf vrf-name {
          type xr:Cisco-ios-xr-string;
          description "VRF Name";
        }
        uses RSVP-MGMT-PXSB-DETAIL;
      }
    }

    container rxsb-details {
      description "Table of detailed RXSB info";

      list rxsb-detail {
        description "Detailed RXSB info";
        leaf destination-address {
          type inet:ipv4-address-no-zone;
          description "Destination Address";
        }
        leaf destination-port {
          type uint32;
          description "Destination Port";
        }
        leaf protocol {
          type uint32;
          description "Protocol";
        }
        leaf extended-tunnel-id {
          type inet:ipv4-address-no-zone;
          description "Extended Tunnel ID";
        }
        leaf session-type {
          type Rsvp-session;
          description "Session Type";
        }
        leaf p2mp-id {
          type uint32;
          description "P2MP ID";
        }
        leaf source-address {
          type inet:ipv4-address-no-zone;
          description "Source Address";
        }
        leaf source-port {
          type uint32;
          description "Source Port";
        }
        leaf sub-group-origin {
          type inet:ipv4-address-no-zone;
          description "Subgroup Origin";
        }
        leaf sub-group-id {
          type uint32;
          description "Subgroup ID";
        }
        leaf vrf-name {
          type xr:Cisco-ios-xr-string;
          description "VRF Name";
        }
        uses RSVP-MGMT-RXSB-DETAIL;
      }
    }
    uses INTERFACE-NEIGHBOR-BRIEF-TABLE;
    uses CONTROLLER-SUMMARY-TABLE;
    uses AUTHENTICATION-BRIEF-TABLE;
    uses SESSION-BRIEF-TABLE;
    uses PSB-DETAILED-TABLE;
    uses CONTROLLER-DETAILED-TABLE;
    uses FRR-SUMMARY;
    uses RSB-DETAILED-TABLE;
    uses INTERFACE-SUMMARY-TABLE;
    uses HELLO-INSTANCE-BRIEF-TABLE;
    uses AUTHENTICATION-DETAIL-TABLE;
    uses RSB-BRIEF-TABLE;
    uses COUNTERS;
    uses INTERFACE-DETAILED-TABLE;
    uses CONTROLLER-BRIEF-TABLE;
    uses GRACEFUL-RESTART;
    uses HELLO-INTERFACE-INSTANCE-BRIEF-TABLE;
    uses HELLO-INTERFACE-INSTANCE-DETAIL-TABLE;
    uses INTERFACE-NEIGHBOR-DETAIL-TABLE;
    uses NSR;
    uses SUMMARY;
    uses FRR-TABLE;
    uses REQUEST-BRIEF-TABLE;
    uses REQUEST-DETAIL-TABLE;
    uses INTERFACE-BRIEF-TABLE;
    uses SESSION-DETAILED-TABLE;
    uses HELLO-INSTANCE-DETAIL-TABLE;
    uses GLOBAL-NEIGHBOR-DETAIL-TABLE;
    uses PSB-BRIEF-TABLE;
    uses GLOBAL-NEIGHBOR-BRIEF-TABLE;
  }
}
