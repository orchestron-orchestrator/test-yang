module Cisco-IOS-XR-um-ipv4-cfg {

  /*** NAMESPACE / PREFIX DEFINITION ***/

  namespace "http://cisco.com/ns/yang/Cisco-IOS-XR-um-ipv4-cfg";
  prefix um-ipv4-cfg;

  /*** LINKAGE (IMPORTS / INCLUDES) ***/

  import Cisco-IOS-XR-types {
    prefix xr;
  }

  import cisco-semver { prefix "semver"; }

  /*** META INFORMATION ***/

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ipv4 package configuration.

     This YANG module augments the
     modules with configuration data.

     Copyright (c) 2021-2022 by Cisco Systems, Inc.
     All rights reserved.";

  revision 2021-02-19 {
    description
      "Initial release";
    semver:module-version "1.0.0";
  }


  container ipv4 {
    description
      "Global IPv4 configuration commands";
    container source-route {
      presence "Indicates a source-route node is configured.";
      description
        "Process packets with source routing header options";
    }
    container ipc {
      description
        "IPv4 Inter Process Communication(IPC) related config";
      container ratelimit {
        description
          "IPC ratelimit in the IPv4 software datapath";
        leaf arm {
          type uint32 {
            range "5..100" {
              description
                "Number of IPCs per second (default is 10)";
            }
          }
          description
            "IPC rate-limiting to the ARM server";
        }
        leaf netio {
          type uint32 {
            range "10..300" {
              description
                "Number of IPCs per second (default is 100)";
            }
          }
          description
            "IPC rate-limiting for netio to send icmp error locally";
        }
        container rib {
          description
            "IPC rate-limiting to the RIB server";
          leaf icmp {
            type uint32 {
              range "5..200" {
                description
                  "Number of IPCs per second (default is 50)";
              }
            }
            description
              "IPC ratelimit to the RIB server for ICMP packets";
          }
          leaf io {
            type uint32 {
              range "5..100" {
                description
                  "Number of IPCs per second (default is 10)";
              }
            }
            description
              "IPC ratelimit to the RIB server for IO packets";
          }
        }
      }
    }
    container assembler {
      description
        "IPv4 Fragmented Packet Assembler";
      leaf timeout {
        type uint32 {
          range "1..120" {
            description
              "Number of seconds an assembly queue will hold before timeout";
          }
        }
        description
          "Number of seconds an assembly queue will hold before timeout";
      }
      leaf max-packets {
        type uint32 {
          range "1..50" {
            description
              "Percentage of total packets available in the system (default: 1000 packets)";
          }
        }
        description
          "Maxinum packets allowed in assembly queues";
      }
    }
    container unnumbered {
      description
        "Enable IPv4 processing without an explicit address";
      container mpls {
        description
          "Configure MPLS routing protocol parameters";
        leaf traffic-eng {
          type xr:Interface-name;
          description
            "IPv4 commands for MPLS Traffic Engineering";
        }
      }
    }
  }
}
