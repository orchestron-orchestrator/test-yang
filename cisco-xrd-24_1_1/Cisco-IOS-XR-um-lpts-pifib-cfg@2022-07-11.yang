module Cisco-IOS-XR-um-lpts-pifib-cfg {

  /*** NAMESPACE / PREFIX DEFINITION ***/

  namespace "http://cisco.com/ns/yang/Cisco-IOS-XR-um-lpts-pifib-cfg";
  prefix um-lpts-pifib-cfg;

  /*** LINKAGE (IMPORTS / INCLUDES) ***/

  import Cisco-IOS-XR-um-location-cfg {
    prefix location;
  }

  import cisco-semver { prefix "semver"; }

  /*** META INFORMATION ***/

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR lpts-pifib package configuration.

     This YANG module augments the
     modules with configuration data.

     Copyright (c) 2021-2022 by Cisco Systems, Inc.
     All rights reserved.";

  revision 2022-07-11 {
    description
      "Added missing description statement to nodes";
    semver:module-version "1.1.0";
  }

  revision "2021-05-10" {
    description
      "Initial release";
    semver:module-version "1.0.0";
  }

  feature pifib_policer_config_check {
    description
      "pifib policer config check";
  }

  feature pifib_local_policer_config_check {
    description
      "pifib local policer config check";
  }

  feature pifib_xipc_throt_policer_config_check {
    description
      "pifib xipc throt policer config check";
  }

  feature pifib_policer_node_check {
    description
      "pifib policer node check";
  }

  grouping LOCATION-BODY {
    description
      "Grouping for location";
    container lpts {
      if-feature "pifib_policer_config_check";
      if-feature "pifib_local_policer_config_check";
      description
        "lpts configuration commands";
      container pifib {
        description
          "pre-ifib configuration commands";
        container hardware {
          description
            "hardware configuration commands";
          container police {
            presence "Indicates a police node is configured.";
            description
              "ingress policers configuration command";
            container flow {
              description
                "lpts flow type";
              container fragment {
                description
                  "Fragmented IP packets";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container ospf {
                description
                  "OSPF ";
                container unicast {
                  description
                    "Unicast ";
                  container known {
                    description
                      "Known ";
                    leaf rate {
                      type uint32 {
                        range "0..4294967295" {
                          description
                            "Packets Per Second (actual Min and Max range depends on platform)";
                        }
                      }
                      description
                        "Rate in PPS";
                    }
                    leaf-list precedence {
                      type union {
                        type uint32 {
                          range "0..7" {
                            description
                              "Precedence value";
                          }
                        }
                        type enumeration {
                          enum critical {
                            value 5;
                            description
                              "Critical precedence (5)";
                          }
                          enum flash {
                            value 3;
                            description
                              "Flash precedence (3)";
                          }
                          enum flash-override {
                            value 4;
                            description
                              "Flash override precedence (4)";
                          }
                          enum immediate {
                            value 2;
                            description
                              "Immediate precedence (2)";
                          }
                          enum internet {
                            value 6;
                            description
                              "Internetwork control precedence (6)";
                          }
                          enum network {
                            value 7;
                            description
                              "Network control precedence (7)";
                          }
                          enum priority {
                            value 1;
                            description
                              "Priority precedence (1)";
                          }
                          enum routine {
                            value 0;
                            description
                              "Routine precedence (0)";
                          }
                        }
                      }
                      max-elements 8;
                      description
                        "TOS Precedence value(s)";
                    }
                  }
                  container default {
                    description
                      "Default ";
                    leaf rate {
                      type uint32 {
                        range "0..4294967295" {
                          description
                            "Packets Per Second (actual Min and Max range depends on platform)";
                        }
                      }
                      description
                        "Rate in PPS";
                    }
                    leaf-list precedence {
                      type union {
                        type uint32 {
                          range "0..7" {
                            description
                              "Precedence value";
                          }
                        }
                        type enumeration {
                          enum critical {
                            value 5;
                            description
                              "Critical precedence (5)";
                          }
                          enum flash {
                            value 3;
                            description
                              "Flash precedence (3)";
                          }
                          enum flash-override {
                            value 4;
                            description
                              "Flash override precedence (4)";
                          }
                          enum immediate {
                            value 2;
                            description
                              "Immediate precedence (2)";
                          }
                          enum internet {
                            value 6;
                            description
                              "Internetwork control precedence (6)";
                          }
                          enum network {
                            value 7;
                            description
                              "Network control precedence (7)";
                          }
                          enum priority {
                            value 1;
                            description
                              "Priority precedence (1)";
                          }
                          enum routine {
                            value 0;
                            description
                              "Routine precedence (0)";
                          }
                        }
                      }
                      max-elements 8;
                      description
                        "TOS Precedence value(s)";
                    }
                  }
                }
                container multicast {
                  description
                    "Multicast";
                  container known {
                    description
                      "Known ";
                    leaf rate {
                      type uint32 {
                        range "0..4294967295" {
                          description
                            "Packets Per Second (actual Min and Max range depends on platform)";
                        }
                      }
                      description
                        "Rate in PPS";
                    }
                    leaf-list precedence {
                      type union {
                        type uint32 {
                          range "0..7" {
                            description
                              "Precedence value";
                          }
                        }
                        type enumeration {
                          enum critical {
                            value 5;
                            description
                              "Critical precedence (5)";
                          }
                          enum flash {
                            value 3;
                            description
                              "Flash precedence (3)";
                          }
                          enum flash-override {
                            value 4;
                            description
                              "Flash override precedence (4)";
                          }
                          enum immediate {
                            value 2;
                            description
                              "Immediate precedence (2)";
                          }
                          enum internet {
                            value 6;
                            description
                              "Internetwork control precedence (6)";
                          }
                          enum network {
                            value 7;
                            description
                              "Network control precedence (7)";
                          }
                          enum priority {
                            value 1;
                            description
                              "Priority precedence (1)";
                          }
                          enum routine {
                            value 0;
                            description
                              "Routine precedence (0)";
                          }
                        }
                      }
                      max-elements 8;
                      description
                        "TOS Precedence value(s)";
                    }
                  }
                  container default {
                    description
                      "Default ";
                    leaf rate {
                      type uint32 {
                        range "0..4294967295" {
                          description
                            "Packets Per Second (actual Min and Max range depends on platform)";
                        }
                      }
                      description
                        "Rate in PPS";
                    }
                    leaf-list precedence {
                      type union {
                        type uint32 {
                          range "0..7" {
                            description
                              "Precedence value";
                          }
                        }
                        type enumeration {
                          enum critical {
                            value 5;
                            description
                              "Critical precedence (5)";
                          }
                          enum flash {
                            value 3;
                            description
                              "Flash precedence (3)";
                          }
                          enum flash-override {
                            value 4;
                            description
                              "Flash override precedence (4)";
                          }
                          enum immediate {
                            value 2;
                            description
                              "Immediate precedence (2)";
                          }
                          enum internet {
                            value 6;
                            description
                              "Internetwork control precedence (6)";
                          }
                          enum network {
                            value 7;
                            description
                              "Network control precedence (7)";
                          }
                          enum priority {
                            value 1;
                            description
                              "Priority precedence (1)";
                          }
                          enum routine {
                            value 0;
                            description
                              "Routine precedence (0)";
                          }
                        }
                      }
                      max-elements 8;
                      description
                        "TOS Precedence value(s)";
                    }
                  }
                }
              }
              container isis {
                description
                  "ISIS ";
                container known {
                  description
                    "Known ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
                container default {
                  description
                    "Default ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
              }
              container bfd {
                description
                  "BFD ";
                container known {
                  description
                    "Known ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
                container default {
                  description
                    "Default ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
                container multipath {
                  description
                    "Multipath ";
                  container known {
                    description
                      "Known ";
                    leaf rate {
                      type uint32 {
                        range "0..4294967295" {
                          description
                            "Packets Per Second (actual Min and Max range depends on platform)";
                        }
                      }
                      description
                        "Rate in PPS";
                    }
                    leaf-list precedence {
                      type union {
                        type uint32 {
                          range "0..7" {
                            description
                              "Precedence value";
                          }
                        }
                        type enumeration {
                          enum critical {
                            value 5;
                            description
                              "Critical precedence (5)";
                          }
                          enum flash {
                            value 3;
                            description
                              "Flash precedence (3)";
                          }
                          enum flash-override {
                            value 4;
                            description
                              "Flash override precedence (4)";
                          }
                          enum immediate {
                            value 2;
                            description
                              "Immediate precedence (2)";
                          }
                          enum internet {
                            value 6;
                            description
                              "Internetwork control precedence (6)";
                          }
                          enum network {
                            value 7;
                            description
                              "Network control precedence (7)";
                          }
                          enum priority {
                            value 1;
                            description
                              "Priority precedence (1)";
                          }
                          enum routine {
                            value 0;
                            description
                              "Routine precedence (0)";
                          }
                        }
                      }
                      max-elements 8;
                      description
                        "TOS Precedence value(s)";
                    }
                  }
                  container default {
                    description
                      "Default ";
                    leaf rate {
                      type uint32 {
                        range "0..4294967295" {
                          description
                            "Packets Per Second (actual Min and Max range depends on platform)";
                        }
                      }
                      description
                        "Rate in PPS";
                    }
                    leaf-list precedence {
                      type union {
                        type uint32 {
                          range "0..7" {
                            description
                              "Precedence value";
                          }
                        }
                        type enumeration {
                          enum critical {
                            value 5;
                            description
                              "Critical precedence (5)";
                          }
                          enum flash {
                            value 3;
                            description
                              "Flash precedence (3)";
                          }
                          enum flash-override {
                            value 4;
                            description
                              "Flash override precedence (4)";
                          }
                          enum immediate {
                            value 2;
                            description
                              "Immediate precedence (2)";
                          }
                          enum internet {
                            value 6;
                            description
                              "Internetwork control precedence (6)";
                          }
                          enum network {
                            value 7;
                            description
                              "Network control precedence (7)";
                          }
                          enum priority {
                            value 1;
                            description
                              "Priority precedence (1)";
                          }
                          enum routine {
                            value 0;
                            description
                              "Routine precedence (0)";
                          }
                        }
                      }
                      max-elements 8;
                      description
                        "TOS Precedence value(s)";
                    }
                  }
                }
                container blb {
                  description
                    "BLB ";
                  container known {
                    description
                      "Known ";
                    leaf rate {
                      type uint32 {
                        range "0..4294967295" {
                          description
                            "Packets Per Second (actual Min and Max range depends on platform)";
                        }
                      }
                      description
                        "Rate in PPS";
                    }
                    leaf-list precedence {
                      type union {
                        type uint32 {
                          range "0..7" {
                            description
                              "Precedence value";
                          }
                        }
                        type enumeration {
                          enum critical {
                            value 5;
                            description
                              "Critical precedence (5)";
                          }
                          enum flash {
                            value 3;
                            description
                              "Flash precedence (3)";
                          }
                          enum flash-override {
                            value 4;
                            description
                              "Flash override precedence (4)";
                          }
                          enum immediate {
                            value 2;
                            description
                              "Immediate precedence (2)";
                          }
                          enum internet {
                            value 6;
                            description
                              "Internetwork control precedence (6)";
                          }
                          enum network {
                            value 7;
                            description
                              "Network control precedence (7)";
                          }
                          enum priority {
                            value 1;
                            description
                              "Priority precedence (1)";
                          }
                          enum routine {
                            value 0;
                            description
                              "Routine precedence (0)";
                          }
                        }
                      }
                      max-elements 8;
                      description
                        "TOS Precedence value(s)";
                    }
                  }
                  container default {
                    description
                      "Default ";
                    leaf rate {
                      type uint32 {
                        range "0..4294967295" {
                          description
                            "Packets Per Second (actual Min and Max range depends on platform)";
                        }
                      }
                      description
                        "Rate in PPS";
                    }
                    leaf-list precedence {
                      type union {
                        type uint32 {
                          range "0..7" {
                            description
                              "Precedence value";
                          }
                        }
                        type enumeration {
                          enum critical {
                            value 5;
                            description
                              "Critical precedence (5)";
                          }
                          enum flash {
                            value 3;
                            description
                              "Flash precedence (3)";
                          }
                          enum flash-override {
                            value 4;
                            description
                              "Flash override precedence (4)";
                          }
                          enum immediate {
                            value 2;
                            description
                              "Immediate precedence (2)";
                          }
                          enum internet {
                            value 6;
                            description
                              "Internetwork control precedence (6)";
                          }
                          enum network {
                            value 7;
                            description
                              "Network control precedence (7)";
                          }
                          enum priority {
                            value 1;
                            description
                              "Priority precedence (1)";
                          }
                          enum routine {
                            value 0;
                            description
                              "Routine precedence (0)";
                          }
                        }
                      }
                      max-elements 8;
                      description
                        "TOS Precedence value(s)";
                    }
                  }
                }
                container singlepath {
                  description
                    "Singlepath ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
              }
              container bgp {
                description
                  "BGP ";
                container known {
                  description
                    "Known ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
                container configured {
                  description
                    "Configured";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
                container default {
                  description
                    "Default ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
              }
              container pim {
                description
                  "PIM ";
                container unicast {
                  description
                    "Unicast ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
                container multicast {
                  description
                    "Multicast";
                  container known {
                    description
                      "Known ";
                    leaf rate {
                      type uint32 {
                        range "0..4294967295" {
                          description
                            "Packets Per Second (actual Min and Max range depends on platform)";
                        }
                      }
                      description
                        "Rate in PPS";
                    }
                    leaf-list precedence {
                      type union {
                        type uint32 {
                          range "0..7" {
                            description
                              "Precedence value";
                          }
                        }
                        type enumeration {
                          enum critical {
                            value 5;
                            description
                              "Critical precedence (5)";
                          }
                          enum flash {
                            value 3;
                            description
                              "Flash precedence (3)";
                          }
                          enum flash-override {
                            value 4;
                            description
                              "Flash override precedence (4)";
                          }
                          enum immediate {
                            value 2;
                            description
                              "Immediate precedence (2)";
                          }
                          enum internet {
                            value 6;
                            description
                              "Internetwork control precedence (6)";
                          }
                          enum network {
                            value 7;
                            description
                              "Network control precedence (7)";
                          }
                          enum priority {
                            value 1;
                            description
                              "Priority precedence (1)";
                          }
                          enum routine {
                            value 0;
                            description
                              "Routine precedence (0)";
                          }
                        }
                      }
                      max-elements 8;
                      description
                        "TOS Precedence value(s)";
                    }
                  }
                  container default {
                    description
                      "Default ";
                    leaf rate {
                      type uint32 {
                        range "0..4294967295" {
                          description
                            "Packets Per Second (actual Min and Max range depends on platform)";
                        }
                      }
                      description
                        "Rate in PPS";
                    }
                    leaf-list precedence {
                      type union {
                        type uint32 {
                          range "0..7" {
                            description
                              "Precedence value";
                          }
                        }
                        type enumeration {
                          enum critical {
                            value 5;
                            description
                              "Critical precedence (5)";
                          }
                          enum flash {
                            value 3;
                            description
                              "Flash precedence (3)";
                          }
                          enum flash-override {
                            value 4;
                            description
                              "Flash override precedence (4)";
                          }
                          enum immediate {
                            value 2;
                            description
                              "Immediate precedence (2)";
                          }
                          enum internet {
                            value 6;
                            description
                              "Internetwork control precedence (6)";
                          }
                          enum network {
                            value 7;
                            description
                              "Network control precedence (7)";
                          }
                          enum priority {
                            value 1;
                            description
                              "Priority precedence (1)";
                          }
                          enum routine {
                            value 0;
                            description
                              "Routine precedence (0)";
                          }
                        }
                      }
                      max-elements 8;
                      description
                        "TOS Precedence value(s)";
                    }
                  }
                }
              }
              container igmp {
                description
                  "IGMP ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container icmp {
                description
                  "ICMP ";
                container local {
                  description
                    "Local interest packets ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
                container application {
                  description
                    "Specific application packets ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
                container control {
                  description
                    "Control packets ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
                container default {
                  description
                    "Default packets ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
                container generic {
                  description
                    "Generic application packets ";
                  container echo-reply {
                    description
                      "Echo-reply packets ";
                    leaf rate {
                      type uint32 {
                        range "0..4294967295" {
                          description
                            "Packets Per Second (actual Min and Max range depends on platform)";
                        }
                      }
                      description
                        "Rate in PPS";
                    }
                    leaf-list precedence {
                      type union {
                        type uint32 {
                          range "0..7" {
                            description
                              "Precedence value";
                          }
                        }
                        type enumeration {
                          enum critical {
                            value 5;
                            description
                              "Critical precedence (5)";
                          }
                          enum flash {
                            value 3;
                            description
                              "Flash precedence (3)";
                          }
                          enum flash-override {
                            value 4;
                            description
                              "Flash override precedence (4)";
                          }
                          enum immediate {
                            value 2;
                            description
                              "Immediate precedence (2)";
                          }
                          enum internet {
                            value 6;
                            description
                              "Internetwork control precedence (6)";
                          }
                          enum network {
                            value 7;
                            description
                              "Network control precedence (7)";
                          }
                          enum priority {
                            value 1;
                            description
                              "Priority precedence (1)";
                          }
                          enum routine {
                            value 0;
                            description
                              "Routine precedence (0)";
                          }
                        }
                      }
                      max-elements 8;
                      description
                        "TOS Precedence value(s)";
                    }
                  }
                }
              }
              container ldp {
                description
                  "LDP ";
                container tcp {
                  description
                    "TCP ";
                  container known {
                    description
                      "Known ";
                    leaf rate {
                      type uint32 {
                        range "0..4294967295" {
                          description
                            "Packets Per Second (actual Min and Max range depends on platform)";
                        }
                      }
                      description
                        "Rate in PPS";
                    }
                    leaf-list precedence {
                      type union {
                        type uint32 {
                          range "0..7" {
                            description
                              "Precedence value";
                          }
                        }
                        type enumeration {
                          enum critical {
                            value 5;
                            description
                              "Critical precedence (5)";
                          }
                          enum flash {
                            value 3;
                            description
                              "Flash precedence (3)";
                          }
                          enum flash-override {
                            value 4;
                            description
                              "Flash override precedence (4)";
                          }
                          enum immediate {
                            value 2;
                            description
                              "Immediate precedence (2)";
                          }
                          enum internet {
                            value 6;
                            description
                              "Internetwork control precedence (6)";
                          }
                          enum network {
                            value 7;
                            description
                              "Network control precedence (7)";
                          }
                          enum priority {
                            value 1;
                            description
                              "Priority precedence (1)";
                          }
                          enum routine {
                            value 0;
                            description
                              "Routine precedence (0)";
                          }
                        }
                      }
                      max-elements 8;
                      description
                        "TOS Precedence value(s)";
                    }
                  }
                  container configured {
                    description
                      "Configured";
                    leaf rate {
                      type uint32 {
                        range "0..4294967295" {
                          description
                            "Packets Per Second (actual Min and Max range depends on platform)";
                        }
                      }
                      description
                        "Rate in PPS";
                    }
                    leaf-list precedence {
                      type union {
                        type uint32 {
                          range "0..7" {
                            description
                              "Precedence value";
                          }
                        }
                        type enumeration {
                          enum critical {
                            value 5;
                            description
                              "Critical precedence (5)";
                          }
                          enum flash {
                            value 3;
                            description
                              "Flash precedence (3)";
                          }
                          enum flash-override {
                            value 4;
                            description
                              "Flash override precedence (4)";
                          }
                          enum immediate {
                            value 2;
                            description
                              "Immediate precedence (2)";
                          }
                          enum internet {
                            value 6;
                            description
                              "Internetwork control precedence (6)";
                          }
                          enum network {
                            value 7;
                            description
                              "Network control precedence (7)";
                          }
                          enum priority {
                            value 1;
                            description
                              "Priority precedence (1)";
                          }
                          enum routine {
                            value 0;
                            description
                              "Routine precedence (0)";
                          }
                        }
                      }
                      max-elements 8;
                      description
                        "TOS Precedence value(s)";
                    }
                  }
                  container default {
                    description
                      "Default ";
                    leaf rate {
                      type uint32 {
                        range "0..4294967295" {
                          description
                            "Packets Per Second (actual Min and Max range depends on platform)";
                        }
                      }
                      description
                        "Rate in PPS";
                    }
                    leaf-list precedence {
                      type union {
                        type uint32 {
                          range "0..7" {
                            description
                              "Precedence value";
                          }
                        }
                        type enumeration {
                          enum critical {
                            value 5;
                            description
                              "Critical precedence (5)";
                          }
                          enum flash {
                            value 3;
                            description
                              "Flash precedence (3)";
                          }
                          enum flash-override {
                            value 4;
                            description
                              "Flash override precedence (4)";
                          }
                          enum immediate {
                            value 2;
                            description
                              "Immediate precedence (2)";
                          }
                          enum internet {
                            value 6;
                            description
                              "Internetwork control precedence (6)";
                          }
                          enum network {
                            value 7;
                            description
                              "Network control precedence (7)";
                          }
                          enum priority {
                            value 1;
                            description
                              "Priority precedence (1)";
                          }
                          enum routine {
                            value 0;
                            description
                              "Routine precedence (0)";
                          }
                        }
                      }
                      max-elements 8;
                      description
                        "TOS Precedence value(s)";
                    }
                  }
                }
                container udp {
                  description
                    "UDP ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
              }
              container all-routers {
                description
                  "All Routers";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container lmp {
                description
                  "LMP ";
                container tcp {
                  description
                    "TCP ";
                  container known {
                    description
                      "Known ";
                    leaf rate {
                      type uint32 {
                        range "0..4294967295" {
                          description
                            "Packets Per Second (actual Min and Max range depends on platform)";
                        }
                      }
                      description
                        "Rate in PPS";
                    }
                    leaf-list precedence {
                      type union {
                        type uint32 {
                          range "0..7" {
                            description
                              "Precedence value";
                          }
                        }
                        type enumeration {
                          enum critical {
                            value 5;
                            description
                              "Critical precedence (5)";
                          }
                          enum flash {
                            value 3;
                            description
                              "Flash precedence (3)";
                          }
                          enum flash-override {
                            value 4;
                            description
                              "Flash override precedence (4)";
                          }
                          enum immediate {
                            value 2;
                            description
                              "Immediate precedence (2)";
                          }
                          enum internet {
                            value 6;
                            description
                              "Internetwork control precedence (6)";
                          }
                          enum network {
                            value 7;
                            description
                              "Network control precedence (7)";
                          }
                          enum priority {
                            value 1;
                            description
                              "Priority precedence (1)";
                          }
                          enum routine {
                            value 0;
                            description
                              "Routine precedence (0)";
                          }
                        }
                      }
                      max-elements 8;
                      description
                        "TOS Precedence value(s)";
                    }
                  }
                  container configured {
                    description
                      "Configured";
                    leaf rate {
                      type uint32 {
                        range "0..4294967295" {
                          description
                            "Packets Per Second (actual Min and Max range depends on platform)";
                        }
                      }
                      description
                        "Rate in PPS";
                    }
                    leaf-list precedence {
                      type union {
                        type uint32 {
                          range "0..7" {
                            description
                              "Precedence value";
                          }
                        }
                        type enumeration {
                          enum critical {
                            value 5;
                            description
                              "Critical precedence (5)";
                          }
                          enum flash {
                            value 3;
                            description
                              "Flash precedence (3)";
                          }
                          enum flash-override {
                            value 4;
                            description
                              "Flash override precedence (4)";
                          }
                          enum immediate {
                            value 2;
                            description
                              "Immediate precedence (2)";
                          }
                          enum internet {
                            value 6;
                            description
                              "Internetwork control precedence (6)";
                          }
                          enum network {
                            value 7;
                            description
                              "Network control precedence (7)";
                          }
                          enum priority {
                            value 1;
                            description
                              "Priority precedence (1)";
                          }
                          enum routine {
                            value 0;
                            description
                              "Routine precedence (0)";
                          }
                        }
                      }
                      max-elements 8;
                      description
                        "TOS Precedence value(s)";
                    }
                  }
                  container default {
                    description
                      "Default ";
                    leaf rate {
                      type uint32 {
                        range "0..4294967295" {
                          description
                            "Packets Per Second (actual Min and Max range depends on platform)";
                        }
                      }
                      description
                        "Rate in PPS";
                    }
                    leaf-list precedence {
                      type union {
                        type uint32 {
                          range "0..7" {
                            description
                              "Precedence value";
                          }
                        }
                        type enumeration {
                          enum critical {
                            value 5;
                            description
                              "Critical precedence (5)";
                          }
                          enum flash {
                            value 3;
                            description
                              "Flash precedence (3)";
                          }
                          enum flash-override {
                            value 4;
                            description
                              "Flash override precedence (4)";
                          }
                          enum immediate {
                            value 2;
                            description
                              "Immediate precedence (2)";
                          }
                          enum internet {
                            value 6;
                            description
                              "Internetwork control precedence (6)";
                          }
                          enum network {
                            value 7;
                            description
                              "Network control precedence (7)";
                          }
                          enum priority {
                            value 1;
                            description
                              "Priority precedence (1)";
                          }
                          enum routine {
                            value 0;
                            description
                              "Routine precedence (0)";
                          }
                        }
                      }
                      max-elements 8;
                      description
                        "TOS Precedence value(s)";
                    }
                  }
                }
                container udp {
                  description
                    "UDP ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
              }
              container rsvp {
                description
                  "RSVP ";
                container default {
                  description
                    "RSVP Default ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
                container known {
                  description
                    "RSVP Known ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
                container udp {
                  description
                    "UDP";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
              }
              container ike {
                description
                  "IKE ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container ipsec {
                description
                  "IPSEC ";
                container known {
                  description
                    "Known ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
                container default {
                  description
                    "Default ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
              }
              container msdp {
                description
                  "MSDP ";
                container known {
                  description
                    "Known ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
                container configured {
                  description
                    "Configured";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
                container default {
                  description
                    "Default";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
              }
              container snmp {
                description
                  "SNMP ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container ssh {
                description
                  "SSH ";
                container known {
                  description
                    "Known ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
                container default {
                  description
                    "Default ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
              }
              container http {
                description
                  "HTTP ";
                container known {
                  description
                    "Known ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
                container default {
                  description
                    "Default ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
              }
              container shttp {
                description
                  "SHTTP ";
                container known {
                  description
                    "Known ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
                container default {
                  description
                    "Default ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
              }
              container telnet {
                description
                  "TELNET ";
                container known {
                  description
                    "Known ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
                container default {
                  description
                    "Default ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
              }
              container css {
                description
                  "CSS ";
                container known {
                  description
                    "Known ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
                container default {
                  description
                    "Default ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
              }
              container rsh {
                description
                  "RSH ";
                container known {
                  description
                    "Known ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
                container default {
                  description
                    "Default ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
              }
              container udp {
                description
                  "UDP ";
                container known {
                  description
                    "Known ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
                container listen {
                  description
                    "Listen ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
                container configured {
                  description
                    "Config peer ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
                container default {
                  description
                    "Default ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
              }
              container tcp {
                description
                  "TCP ";
                container known {
                  description
                    "Known ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
                container listen {
                  description
                    "Listen ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
                container configured {
                  description
                    "Configured ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
                container default {
                  description
                    "Default ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
              }
              container multicast {
                description
                  "Multicast ";
                container known {
                  description
                    "Known ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
                container default {
                  description
                    "Default ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
              }
              container raw {
                description
                  "Raw ";
                container listen {
                  description
                    "Listen ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
                container default {
                  description
                    "Default ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
              }
              container ip-sla {
                description
                  "IP-SLA ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container eigrp {
                description
                  "EIGRP ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container rip {
                description
                  "RIP ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container l2tpv3 {
                description
                  "L2TPv3 ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container pcep {
                description
                  "PCEP ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container gre {
                description
                  "GRE ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container vrrp {
                description
                  "VRRP ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container hsrp {
                description
                  "HSRP ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container mpls {
                description
                  "MPLS ";
                container oam {
                  description
                    "Oam ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
              }
              container l2tpv2 {
                description
                  "L2TPv2 ";
                container default {
                  description
                    "Default ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
                container known {
                  description
                    "Known ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
              }
              container dns {
                description
                  "DNS ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container radius {
                description
                  "RADIUS ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container tacacs {
                description
                  "TACACS ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container ntp {
                description
                  "NTP ";
                container default {
                  description
                    "Default ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
                container known {
                  description
                    "Known ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
              }
              container mipv6 {
                description
                  "MIPv6 ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container amt {
                description
                  "AMT ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container sdac {
                description
                  "SDAC-TCP ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container radius-coa {
                description
                  "RADIUS COA ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container rel-udp {
                description
                  "Syslog/netflow packets";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container dhcpv4 {
                description
                  "DHCPv4 ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container dhcpv6 {
                description
                  "DHCPv6 ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container onepk {
                description
                  "ONEPK ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container tpa {
                description
                  "Third Party Applications";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container ietf-bob {
                description
                  "IETF BOB Packets";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container xipc {
                if-feature "pifib_xipc_throt_policer_config_check";
                description
                  "XIPC rate limit";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container pm-twamp {
                description
                  "PM TWAMP Packets";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
            }
          }
        }
      }
    }
  }

  augment "/location:locations/location:location" {
    description
      "This augment extends active nodes configuration";
    uses LOCATION-BODY;
  }

  augment "/location:locations/location:preconfigured-location" {
    description
      "This augment extends preconfigured nodes
       configuration";
    uses LOCATION-BODY;
  }

  container lpts {
    if-feature "pifib_policer_config_check";
    if-feature "pifib_local_policer_config_check";
    description
      "lpts configuration commands";
    container pifib {
      description
        "pre-ifib configuration commands";
      container hardware {
        description
          "hardware configuration commands";
        container police {
          presence "Indicates a police node is configured.";
          description
            "ingress policers configuration command";
          container flow {
            description
              "lpts flow type";
            container fragment {
              description
                "Fragmented IP packets";
              leaf rate {
                type uint32 {
                  range "0..4294967295" {
                    description
                      "Packets Per Second (actual Min and Max range depends on platform)";
                  }
                }
                description
                  "Rate in PPS";
              }
              leaf-list precedence {
                type union {
                  type uint32 {
                    range "0..7" {
                      description
                        "Precedence value";
                    }
                  }
                  type enumeration {
                    enum critical {
                      value 5;
                      description
                        "Critical precedence (5)";
                    }
                    enum flash {
                      value 3;
                      description
                        "Flash precedence (3)";
                    }
                    enum flash-override {
                      value 4;
                      description
                        "Flash override precedence (4)";
                    }
                    enum immediate {
                      value 2;
                      description
                        "Immediate precedence (2)";
                    }
                    enum internet {
                      value 6;
                      description
                        "Internetwork control precedence (6)";
                    }
                    enum network {
                      value 7;
                      description
                        "Network control precedence (7)";
                    }
                    enum priority {
                      value 1;
                      description
                        "Priority precedence (1)";
                    }
                    enum routine {
                      value 0;
                      description
                        "Routine precedence (0)";
                    }
                  }
                }
                max-elements 8;
                description
                  "TOS Precedence value(s)";
              }
            }
            container ospf {
              description
                "OSPF ";
              container unicast {
                description
                  "Unicast ";
                container known {
                  description
                    "Known ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
                container default {
                  description
                    "Default ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
              }
              container multicast {
                description
                  "Multicast";
                container known {
                  description
                    "Known ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
                container default {
                  description
                    "Default ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
              }
            }
            container isis {
              description
                "ISIS ";
              container known {
                description
                  "Known ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container default {
                description
                  "Default ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
            }
            container bfd {
              description
                "BFD ";
              container known {
                description
                  "Known ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container default {
                description
                  "Default ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container multipath {
                description
                  "Multipath ";
                container known {
                  description
                    "Known ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
                container default {
                  description
                    "Default ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
              }
              container blb {
                description
                  "BLB ";
                container known {
                  description
                    "Known ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
                container default {
                  description
                    "Default ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
              }
              container singlepath {
                description
                  "Singlepath ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
            }
            container bgp {
              description
                "BGP ";
              container known {
                description
                  "Known ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container configured {
                description
                  "Configured";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container default {
                description
                  "Default ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
            }
            container pim {
              description
                "PIM ";
              container unicast {
                description
                  "Unicast ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container multicast {
                description
                  "Multicast";
                container known {
                  description
                    "Known ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
                container default {
                  description
                    "Default ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
              }
            }
            container igmp {
              description
                "IGMP ";
              leaf rate {
                type uint32 {
                  range "0..4294967295" {
                    description
                      "Packets Per Second (actual Min and Max range depends on platform)";
                  }
                }
                description
                  "Rate in PPS";
              }
              leaf-list precedence {
                type union {
                  type uint32 {
                    range "0..7" {
                      description
                        "Precedence value";
                    }
                  }
                  type enumeration {
                    enum critical {
                      value 5;
                      description
                        "Critical precedence (5)";
                    }
                    enum flash {
                      value 3;
                      description
                        "Flash precedence (3)";
                    }
                    enum flash-override {
                      value 4;
                      description
                        "Flash override precedence (4)";
                    }
                    enum immediate {
                      value 2;
                      description
                        "Immediate precedence (2)";
                    }
                    enum internet {
                      value 6;
                      description
                        "Internetwork control precedence (6)";
                    }
                    enum network {
                      value 7;
                      description
                        "Network control precedence (7)";
                    }
                    enum priority {
                      value 1;
                      description
                        "Priority precedence (1)";
                    }
                    enum routine {
                      value 0;
                      description
                        "Routine precedence (0)";
                    }
                  }
                }
                max-elements 8;
                description
                  "TOS Precedence value(s)";
              }
            }
            container icmp {
              description
                "ICMP ";
              container local {
                description
                  "Local interest packets ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container application {
                description
                  "Specific application packets ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container control {
                description
                  "Control packets ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container default {
                description
                  "Default packets ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container generic {
                description
                  "Generic application packets ";
                container echo-reply {
                  description
                    "Echo-reply packets ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
              }
            }
            container ldp {
              description
                "LDP ";
              container tcp {
                description
                  "TCP ";
                container known {
                  description
                    "Known ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
                container configured {
                  description
                    "Configured";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
                container default {
                  description
                    "Default ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
              }
              container udp {
                description
                  "UDP ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
            }
            container all-routers {
              description
                "All Routers";
              leaf rate {
                type uint32 {
                  range "0..4294967295" {
                    description
                      "Packets Per Second (actual Min and Max range depends on platform)";
                  }
                }
                description
                  "Rate in PPS";
              }
              leaf-list precedence {
                type union {
                  type uint32 {
                    range "0..7" {
                      description
                        "Precedence value";
                    }
                  }
                  type enumeration {
                    enum critical {
                      value 5;
                      description
                        "Critical precedence (5)";
                    }
                    enum flash {
                      value 3;
                      description
                        "Flash precedence (3)";
                    }
                    enum flash-override {
                      value 4;
                      description
                        "Flash override precedence (4)";
                    }
                    enum immediate {
                      value 2;
                      description
                        "Immediate precedence (2)";
                    }
                    enum internet {
                      value 6;
                      description
                        "Internetwork control precedence (6)";
                    }
                    enum network {
                      value 7;
                      description
                        "Network control precedence (7)";
                    }
                    enum priority {
                      value 1;
                      description
                        "Priority precedence (1)";
                    }
                    enum routine {
                      value 0;
                      description
                        "Routine precedence (0)";
                    }
                  }
                }
                max-elements 8;
                description
                  "TOS Precedence value(s)";
              }
            }
            container lmp {
              description
                "LMP ";
              container tcp {
                description
                  "TCP ";
                container known {
                  description
                    "Known ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
                container configured {
                  description
                    "Configured";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
                container default {
                  description
                    "Default ";
                  leaf rate {
                    type uint32 {
                      range "0..4294967295" {
                        description
                          "Packets Per Second (actual Min and Max range depends on platform)";
                      }
                    }
                    description
                      "Rate in PPS";
                  }
                  leaf-list precedence {
                    type union {
                      type uint32 {
                        range "0..7" {
                          description
                            "Precedence value";
                        }
                      }
                      type enumeration {
                        enum critical {
                          value 5;
                          description
                            "Critical precedence (5)";
                        }
                        enum flash {
                          value 3;
                          description
                            "Flash precedence (3)";
                        }
                        enum flash-override {
                          value 4;
                          description
                            "Flash override precedence (4)";
                        }
                        enum immediate {
                          value 2;
                          description
                            "Immediate precedence (2)";
                        }
                        enum internet {
                          value 6;
                          description
                            "Internetwork control precedence (6)";
                        }
                        enum network {
                          value 7;
                          description
                            "Network control precedence (7)";
                        }
                        enum priority {
                          value 1;
                          description
                            "Priority precedence (1)";
                        }
                        enum routine {
                          value 0;
                          description
                            "Routine precedence (0)";
                        }
                      }
                    }
                    max-elements 8;
                    description
                      "TOS Precedence value(s)";
                  }
                }
              }
              container udp {
                description
                  "UDP ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
            }
            container rsvp {
              description
                "RSVP ";
              container default {
                description
                  "RSVP Default ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container known {
                description
                  "RSVP Known ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container udp {
                description
                  "UDP";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
            }
            container ike {
              description
                "IKE ";
              leaf rate {
                type uint32 {
                  range "0..4294967295" {
                    description
                      "Packets Per Second (actual Min and Max range depends on platform)";
                  }
                }
                description
                  "Rate in PPS";
              }
              leaf-list precedence {
                type union {
                  type uint32 {
                    range "0..7" {
                      description
                        "Precedence value";
                    }
                  }
                  type enumeration {
                    enum critical {
                      value 5;
                      description
                        "Critical precedence (5)";
                    }
                    enum flash {
                      value 3;
                      description
                        "Flash precedence (3)";
                    }
                    enum flash-override {
                      value 4;
                      description
                        "Flash override precedence (4)";
                    }
                    enum immediate {
                      value 2;
                      description
                        "Immediate precedence (2)";
                    }
                    enum internet {
                      value 6;
                      description
                        "Internetwork control precedence (6)";
                    }
                    enum network {
                      value 7;
                      description
                        "Network control precedence (7)";
                    }
                    enum priority {
                      value 1;
                      description
                        "Priority precedence (1)";
                    }
                    enum routine {
                      value 0;
                      description
                        "Routine precedence (0)";
                    }
                  }
                }
                max-elements 8;
                description
                  "TOS Precedence value(s)";
              }
            }
            container ipsec {
              description
                "IPSEC ";
              container known {
                description
                  "Known ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container default {
                description
                  "Default ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
            }
            container msdp {
              description
                "MSDP ";
              container known {
                description
                  "Known ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container configured {
                description
                  "Configured";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container default {
                description
                  "Default";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
            }
            container snmp {
              description
                "SNMP ";
              leaf rate {
                type uint32 {
                  range "0..4294967295" {
                    description
                      "Packets Per Second (actual Min and Max range depends on platform)";
                  }
                }
                description
                  "Rate in PPS";
              }
              leaf-list precedence {
                type union {
                  type uint32 {
                    range "0..7" {
                      description
                        "Precedence value";
                    }
                  }
                  type enumeration {
                    enum critical {
                      value 5;
                      description
                        "Critical precedence (5)";
                    }
                    enum flash {
                      value 3;
                      description
                        "Flash precedence (3)";
                    }
                    enum flash-override {
                      value 4;
                      description
                        "Flash override precedence (4)";
                    }
                    enum immediate {
                      value 2;
                      description
                        "Immediate precedence (2)";
                    }
                    enum internet {
                      value 6;
                      description
                        "Internetwork control precedence (6)";
                    }
                    enum network {
                      value 7;
                      description
                        "Network control precedence (7)";
                    }
                    enum priority {
                      value 1;
                      description
                        "Priority precedence (1)";
                    }
                    enum routine {
                      value 0;
                      description
                        "Routine precedence (0)";
                    }
                  }
                }
                max-elements 8;
                description
                  "TOS Precedence value(s)";
              }
            }
            container ssh {
              description
                "SSH ";
              container known {
                description
                  "Known ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container default {
                description
                  "Default ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
            }
            container http {
              description
                "HTTP ";
              container known {
                description
                  "Known ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container default {
                description
                  "Default ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
            }
            container shttp {
              description
                "SHTTP ";
              container known {
                description
                  "Known ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container default {
                description
                  "Default ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
            }
            container telnet {
              description
                "TELNET ";
              container known {
                description
                  "Known ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container default {
                description
                  "Default ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
            }
            container css {
              description
                "CSS ";
              container known {
                description
                  "Known ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container default {
                description
                  "Default ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
            }
            container rsh {
              description
                "RSH ";
              container known {
                description
                  "Known ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container default {
                description
                  "Default ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
            }
            container udp {
              description
                "UDP ";
              container known {
                description
                  "Known ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container listen {
                description
                  "Listen ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container configured {
                description
                  "Config peer ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container default {
                description
                  "Default ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
            }
            container tcp {
              description
                "TCP ";
              container known {
                description
                  "Known ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container listen {
                description
                  "Listen ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container configured {
                description
                  "Configured ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container default {
                description
                  "Default ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
            }
            container multicast {
              description
                "Multicast ";
              container known {
                description
                  "Known ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container default {
                description
                  "Default ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
            }
            container raw {
              description
                "Raw ";
              container listen {
                description
                  "Listen ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container default {
                description
                  "Default ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
            }
            container ip-sla {
              description
                "IP-SLA ";
              leaf rate {
                type uint32 {
                  range "0..4294967295" {
                    description
                      "Packets Per Second (actual Min and Max range depends on platform)";
                  }
                }
                description
                  "Rate in PPS";
              }
              leaf-list precedence {
                type union {
                  type uint32 {
                    range "0..7" {
                      description
                        "Precedence value";
                    }
                  }
                  type enumeration {
                    enum critical {
                      value 5;
                      description
                        "Critical precedence (5)";
                    }
                    enum flash {
                      value 3;
                      description
                        "Flash precedence (3)";
                    }
                    enum flash-override {
                      value 4;
                      description
                        "Flash override precedence (4)";
                    }
                    enum immediate {
                      value 2;
                      description
                        "Immediate precedence (2)";
                    }
                    enum internet {
                      value 6;
                      description
                        "Internetwork control precedence (6)";
                    }
                    enum network {
                      value 7;
                      description
                        "Network control precedence (7)";
                    }
                    enum priority {
                      value 1;
                      description
                        "Priority precedence (1)";
                    }
                    enum routine {
                      value 0;
                      description
                        "Routine precedence (0)";
                    }
                  }
                }
                max-elements 8;
                description
                  "TOS Precedence value(s)";
              }
            }
            container eigrp {
              description
                "EIGRP ";
              leaf rate {
                type uint32 {
                  range "0..4294967295" {
                    description
                      "Packets Per Second (actual Min and Max range depends on platform)";
                  }
                }
                description
                  "Rate in PPS";
              }
              leaf-list precedence {
                type union {
                  type uint32 {
                    range "0..7" {
                      description
                        "Precedence value";
                    }
                  }
                  type enumeration {
                    enum critical {
                      value 5;
                      description
                        "Critical precedence (5)";
                    }
                    enum flash {
                      value 3;
                      description
                        "Flash precedence (3)";
                    }
                    enum flash-override {
                      value 4;
                      description
                        "Flash override precedence (4)";
                    }
                    enum immediate {
                      value 2;
                      description
                        "Immediate precedence (2)";
                    }
                    enum internet {
                      value 6;
                      description
                        "Internetwork control precedence (6)";
                    }
                    enum network {
                      value 7;
                      description
                        "Network control precedence (7)";
                    }
                    enum priority {
                      value 1;
                      description
                        "Priority precedence (1)";
                    }
                    enum routine {
                      value 0;
                      description
                        "Routine precedence (0)";
                    }
                  }
                }
                max-elements 8;
                description
                  "TOS Precedence value(s)";
              }
            }
            container rip {
              description
                "RIP ";
              leaf rate {
                type uint32 {
                  range "0..4294967295" {
                    description
                      "Packets Per Second (actual Min and Max range depends on platform)";
                  }
                }
                description
                  "Rate in PPS";
              }
              leaf-list precedence {
                type union {
                  type uint32 {
                    range "0..7" {
                      description
                        "Precedence value";
                    }
                  }
                  type enumeration {
                    enum critical {
                      value 5;
                      description
                        "Critical precedence (5)";
                    }
                    enum flash {
                      value 3;
                      description
                        "Flash precedence (3)";
                    }
                    enum flash-override {
                      value 4;
                      description
                        "Flash override precedence (4)";
                    }
                    enum immediate {
                      value 2;
                      description
                        "Immediate precedence (2)";
                    }
                    enum internet {
                      value 6;
                      description
                        "Internetwork control precedence (6)";
                    }
                    enum network {
                      value 7;
                      description
                        "Network control precedence (7)";
                    }
                    enum priority {
                      value 1;
                      description
                        "Priority precedence (1)";
                    }
                    enum routine {
                      value 0;
                      description
                        "Routine precedence (0)";
                    }
                  }
                }
                max-elements 8;
                description
                  "TOS Precedence value(s)";
              }
            }
            container l2tpv3 {
              description
                "L2TPv3 ";
              leaf rate {
                type uint32 {
                  range "0..4294967295" {
                    description
                      "Packets Per Second (actual Min and Max range depends on platform)";
                  }
                }
                description
                  "Rate in PPS";
              }
              leaf-list precedence {
                type union {
                  type uint32 {
                    range "0..7" {
                      description
                        "Precedence value";
                    }
                  }
                  type enumeration {
                    enum critical {
                      value 5;
                      description
                        "Critical precedence (5)";
                    }
                    enum flash {
                      value 3;
                      description
                        "Flash precedence (3)";
                    }
                    enum flash-override {
                      value 4;
                      description
                        "Flash override precedence (4)";
                    }
                    enum immediate {
                      value 2;
                      description
                        "Immediate precedence (2)";
                    }
                    enum internet {
                      value 6;
                      description
                        "Internetwork control precedence (6)";
                    }
                    enum network {
                      value 7;
                      description
                        "Network control precedence (7)";
                    }
                    enum priority {
                      value 1;
                      description
                        "Priority precedence (1)";
                    }
                    enum routine {
                      value 0;
                      description
                        "Routine precedence (0)";
                    }
                  }
                }
                max-elements 8;
                description
                  "TOS Precedence value(s)";
              }
            }
            container pcep {
              description
                "PCEP ";
              leaf rate {
                type uint32 {
                  range "0..4294967295" {
                    description
                      "Packets Per Second (actual Min and Max range depends on platform)";
                  }
                }
                description
                  "Rate in PPS";
              }
              leaf-list precedence {
                type union {
                  type uint32 {
                    range "0..7" {
                      description
                        "Precedence value";
                    }
                  }
                  type enumeration {
                    enum critical {
                      value 5;
                      description
                        "Critical precedence (5)";
                    }
                    enum flash {
                      value 3;
                      description
                        "Flash precedence (3)";
                    }
                    enum flash-override {
                      value 4;
                      description
                        "Flash override precedence (4)";
                    }
                    enum immediate {
                      value 2;
                      description
                        "Immediate precedence (2)";
                    }
                    enum internet {
                      value 6;
                      description
                        "Internetwork control precedence (6)";
                    }
                    enum network {
                      value 7;
                      description
                        "Network control precedence (7)";
                    }
                    enum priority {
                      value 1;
                      description
                        "Priority precedence (1)";
                    }
                    enum routine {
                      value 0;
                      description
                        "Routine precedence (0)";
                    }
                  }
                }
                max-elements 8;
                description
                  "TOS Precedence value(s)";
              }
            }
            container gre {
              description
                "GRE ";
              leaf rate {
                type uint32 {
                  range "0..4294967295" {
                    description
                      "Packets Per Second (actual Min and Max range depends on platform)";
                  }
                }
                description
                  "Rate in PPS";
              }
              leaf-list precedence {
                type union {
                  type uint32 {
                    range "0..7" {
                      description
                        "Precedence value";
                    }
                  }
                  type enumeration {
                    enum critical {
                      value 5;
                      description
                        "Critical precedence (5)";
                    }
                    enum flash {
                      value 3;
                      description
                        "Flash precedence (3)";
                    }
                    enum flash-override {
                      value 4;
                      description
                        "Flash override precedence (4)";
                    }
                    enum immediate {
                      value 2;
                      description
                        "Immediate precedence (2)";
                    }
                    enum internet {
                      value 6;
                      description
                        "Internetwork control precedence (6)";
                    }
                    enum network {
                      value 7;
                      description
                        "Network control precedence (7)";
                    }
                    enum priority {
                      value 1;
                      description
                        "Priority precedence (1)";
                    }
                    enum routine {
                      value 0;
                      description
                        "Routine precedence (0)";
                    }
                  }
                }
                max-elements 8;
                description
                  "TOS Precedence value(s)";
              }
            }
            container vrrp {
              description
                "VRRP ";
              leaf rate {
                type uint32 {
                  range "0..4294967295" {
                    description
                      "Packets Per Second (actual Min and Max range depends on platform)";
                  }
                }
                description
                  "Rate in PPS";
              }
              leaf-list precedence {
                type union {
                  type uint32 {
                    range "0..7" {
                      description
                        "Precedence value";
                    }
                  }
                  type enumeration {
                    enum critical {
                      value 5;
                      description
                        "Critical precedence (5)";
                    }
                    enum flash {
                      value 3;
                      description
                        "Flash precedence (3)";
                    }
                    enum flash-override {
                      value 4;
                      description
                        "Flash override precedence (4)";
                    }
                    enum immediate {
                      value 2;
                      description
                        "Immediate precedence (2)";
                    }
                    enum internet {
                      value 6;
                      description
                        "Internetwork control precedence (6)";
                    }
                    enum network {
                      value 7;
                      description
                        "Network control precedence (7)";
                    }
                    enum priority {
                      value 1;
                      description
                        "Priority precedence (1)";
                    }
                    enum routine {
                      value 0;
                      description
                        "Routine precedence (0)";
                    }
                  }
                }
                max-elements 8;
                description
                  "TOS Precedence value(s)";
              }
            }
            container hsrp {
              description
                "HSRP ";
              leaf rate {
                type uint32 {
                  range "0..4294967295" {
                    description
                      "Packets Per Second (actual Min and Max range depends on platform)";
                  }
                }
                description
                  "Rate in PPS";
              }
              leaf-list precedence {
                type union {
                  type uint32 {
                    range "0..7" {
                      description
                        "Precedence value";
                    }
                  }
                  type enumeration {
                    enum critical {
                      value 5;
                      description
                        "Critical precedence (5)";
                    }
                    enum flash {
                      value 3;
                      description
                        "Flash precedence (3)";
                    }
                    enum flash-override {
                      value 4;
                      description
                        "Flash override precedence (4)";
                    }
                    enum immediate {
                      value 2;
                      description
                        "Immediate precedence (2)";
                    }
                    enum internet {
                      value 6;
                      description
                        "Internetwork control precedence (6)";
                    }
                    enum network {
                      value 7;
                      description
                        "Network control precedence (7)";
                    }
                    enum priority {
                      value 1;
                      description
                        "Priority precedence (1)";
                    }
                    enum routine {
                      value 0;
                      description
                        "Routine precedence (0)";
                    }
                  }
                }
                max-elements 8;
                description
                  "TOS Precedence value(s)";
              }
            }
            container mpls {
              description
                "MPLS ";
              container oam {
                description
                  "Oam ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
            }
            container l2tpv2 {
              description
                "L2TPv2 ";
              container default {
                description
                  "Default ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container known {
                description
                  "Known ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container fragment {
                description
                  "L2TPv2 fragmented packets";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
            }
            container dns {
              description
                "DNS ";
              leaf rate {
                type uint32 {
                  range "0..4294967295" {
                    description
                      "Packets Per Second (actual Min and Max range depends on platform)";
                  }
                }
                description
                  "Rate in PPS";
              }
              leaf-list precedence {
                type union {
                  type uint32 {
                    range "0..7" {
                      description
                        "Precedence value";
                    }
                  }
                  type enumeration {
                    enum critical {
                      value 5;
                      description
                        "Critical precedence (5)";
                    }
                    enum flash {
                      value 3;
                      description
                        "Flash precedence (3)";
                    }
                    enum flash-override {
                      value 4;
                      description
                        "Flash override precedence (4)";
                    }
                    enum immediate {
                      value 2;
                      description
                        "Immediate precedence (2)";
                    }
                    enum internet {
                      value 6;
                      description
                        "Internetwork control precedence (6)";
                    }
                    enum network {
                      value 7;
                      description
                        "Network control precedence (7)";
                    }
                    enum priority {
                      value 1;
                      description
                        "Priority precedence (1)";
                    }
                    enum routine {
                      value 0;
                      description
                        "Routine precedence (0)";
                    }
                  }
                }
                max-elements 8;
                description
                  "TOS Precedence value(s)";
              }
            }
            container radius {
              description
                "RADIUS ";
              leaf rate {
                type uint32 {
                  range "0..4294967295" {
                    description
                      "Packets Per Second (actual Min and Max range depends on platform)";
                  }
                }
                description
                  "Rate in PPS";
              }
              leaf-list precedence {
                type union {
                  type uint32 {
                    range "0..7" {
                      description
                        "Precedence value";
                    }
                  }
                  type enumeration {
                    enum critical {
                      value 5;
                      description
                        "Critical precedence (5)";
                    }
                    enum flash {
                      value 3;
                      description
                        "Flash precedence (3)";
                    }
                    enum flash-override {
                      value 4;
                      description
                        "Flash override precedence (4)";
                    }
                    enum immediate {
                      value 2;
                      description
                        "Immediate precedence (2)";
                    }
                    enum internet {
                      value 6;
                      description
                        "Internetwork control precedence (6)";
                    }
                    enum network {
                      value 7;
                      description
                        "Network control precedence (7)";
                    }
                    enum priority {
                      value 1;
                      description
                        "Priority precedence (1)";
                    }
                    enum routine {
                      value 0;
                      description
                        "Routine precedence (0)";
                    }
                  }
                }
                max-elements 8;
                description
                  "TOS Precedence value(s)";
              }
            }
            container tacacs {
              description
                "TACACS ";
              leaf rate {
                type uint32 {
                  range "0..4294967295" {
                    description
                      "Packets Per Second (actual Min and Max range depends on platform)";
                  }
                }
                description
                  "Rate in PPS";
              }
              leaf-list precedence {
                type union {
                  type uint32 {
                    range "0..7" {
                      description
                        "Precedence value";
                    }
                  }
                  type enumeration {
                    enum critical {
                      value 5;
                      description
                        "Critical precedence (5)";
                    }
                    enum flash {
                      value 3;
                      description
                        "Flash precedence (3)";
                    }
                    enum flash-override {
                      value 4;
                      description
                        "Flash override precedence (4)";
                    }
                    enum immediate {
                      value 2;
                      description
                        "Immediate precedence (2)";
                    }
                    enum internet {
                      value 6;
                      description
                        "Internetwork control precedence (6)";
                    }
                    enum network {
                      value 7;
                      description
                        "Network control precedence (7)";
                    }
                    enum priority {
                      value 1;
                      description
                        "Priority precedence (1)";
                    }
                    enum routine {
                      value 0;
                      description
                        "Routine precedence (0)";
                    }
                  }
                }
                max-elements 8;
                description
                  "TOS Precedence value(s)";
              }
            }
            container ntp {
              description
                "NTP ";
              container default {
                description
                  "Default ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
              container known {
                description
                  "Known ";
                leaf rate {
                  type uint32 {
                    range "0..4294967295" {
                      description
                        "Packets Per Second (actual Min and Max range depends on platform)";
                    }
                  }
                  description
                    "Rate in PPS";
                }
                leaf-list precedence {
                  type union {
                    type uint32 {
                      range "0..7" {
                        description
                          "Precedence value";
                      }
                    }
                    type enumeration {
                      enum critical {
                        value 5;
                        description
                          "Critical precedence (5)";
                      }
                      enum flash {
                        value 3;
                        description
                          "Flash precedence (3)";
                      }
                      enum flash-override {
                        value 4;
                        description
                          "Flash override precedence (4)";
                      }
                      enum immediate {
                        value 2;
                        description
                          "Immediate precedence (2)";
                      }
                      enum internet {
                        value 6;
                        description
                          "Internetwork control precedence (6)";
                      }
                      enum network {
                        value 7;
                        description
                          "Network control precedence (7)";
                      }
                      enum priority {
                        value 1;
                        description
                          "Priority precedence (1)";
                      }
                      enum routine {
                        value 0;
                        description
                          "Routine precedence (0)";
                      }
                    }
                  }
                  max-elements 8;
                  description
                    "TOS Precedence value(s)";
                }
              }
            }
            container mipv6 {
              description
                "MIPv6 ";
              leaf rate {
                type uint32 {
                  range "0..4294967295" {
                    description
                      "Packets Per Second (actual Min and Max range depends on platform)";
                  }
                }
                description
                  "Rate in PPS";
              }
              leaf-list precedence {
                type union {
                  type uint32 {
                    range "0..7" {
                      description
                        "Precedence value";
                    }
                  }
                  type enumeration {
                    enum critical {
                      value 5;
                      description
                        "Critical precedence (5)";
                    }
                    enum flash {
                      value 3;
                      description
                        "Flash precedence (3)";
                    }
                    enum flash-override {
                      value 4;
                      description
                        "Flash override precedence (4)";
                    }
                    enum immediate {
                      value 2;
                      description
                        "Immediate precedence (2)";
                    }
                    enum internet {
                      value 6;
                      description
                        "Internetwork control precedence (6)";
                    }
                    enum network {
                      value 7;
                      description
                        "Network control precedence (7)";
                    }
                    enum priority {
                      value 1;
                      description
                        "Priority precedence (1)";
                    }
                    enum routine {
                      value 0;
                      description
                        "Routine precedence (0)";
                    }
                  }
                }
                max-elements 8;
                description
                  "TOS Precedence value(s)";
              }
            }
            container amt {
              description
                "AMT ";
              leaf rate {
                type uint32 {
                  range "0..4294967295" {
                    description
                      "Packets Per Second (actual Min and Max range depends on platform)";
                  }
                }
                description
                  "Rate in PPS";
              }
              leaf-list precedence {
                type union {
                  type uint32 {
                    range "0..7" {
                      description
                        "Precedence value";
                    }
                  }
                  type enumeration {
                    enum critical {
                      value 5;
                      description
                        "Critical precedence (5)";
                    }
                    enum flash {
                      value 3;
                      description
                        "Flash precedence (3)";
                    }
                    enum flash-override {
                      value 4;
                      description
                        "Flash override precedence (4)";
                    }
                    enum immediate {
                      value 2;
                      description
                        "Immediate precedence (2)";
                    }
                    enum internet {
                      value 6;
                      description
                        "Internetwork control precedence (6)";
                    }
                    enum network {
                      value 7;
                      description
                        "Network control precedence (7)";
                    }
                    enum priority {
                      value 1;
                      description
                        "Priority precedence (1)";
                    }
                    enum routine {
                      value 0;
                      description
                        "Routine precedence (0)";
                    }
                  }
                }
                max-elements 8;
                description
                  "TOS Precedence value(s)";
              }
            }
            container sdac {
              description
                "SDAC-TCP ";
              leaf rate {
                type uint32 {
                  range "0..4294967295" {
                    description
                      "Packets Per Second (actual Min and Max range depends on platform)";
                  }
                }
                description
                  "Rate in PPS";
              }
              leaf-list precedence {
                type union {
                  type uint32 {
                    range "0..7" {
                      description
                        "Precedence value";
                    }
                  }
                  type enumeration {
                    enum critical {
                      value 5;
                      description
                        "Critical precedence (5)";
                    }
                    enum flash {
                      value 3;
                      description
                        "Flash precedence (3)";
                    }
                    enum flash-override {
                      value 4;
                      description
                        "Flash override precedence (4)";
                    }
                    enum immediate {
                      value 2;
                      description
                        "Immediate precedence (2)";
                    }
                    enum internet {
                      value 6;
                      description
                        "Internetwork control precedence (6)";
                    }
                    enum network {
                      value 7;
                      description
                        "Network control precedence (7)";
                    }
                    enum priority {
                      value 1;
                      description
                        "Priority precedence (1)";
                    }
                    enum routine {
                      value 0;
                      description
                        "Routine precedence (0)";
                    }
                  }
                }
                max-elements 8;
                description
                  "TOS Precedence value(s)";
              }
            }
            container radius-coa {
              description
                "RADIUS COA ";
              leaf rate {
                type uint32 {
                  range "0..4294967295" {
                    description
                      "Packets Per Second (actual Min and Max range depends on platform)";
                  }
                }
                description
                  "Rate in PPS";
              }
              leaf-list precedence {
                type union {
                  type uint32 {
                    range "0..7" {
                      description
                        "Precedence value";
                    }
                  }
                  type enumeration {
                    enum critical {
                      value 5;
                      description
                        "Critical precedence (5)";
                    }
                    enum flash {
                      value 3;
                      description
                        "Flash precedence (3)";
                    }
                    enum flash-override {
                      value 4;
                      description
                        "Flash override precedence (4)";
                    }
                    enum immediate {
                      value 2;
                      description
                        "Immediate precedence (2)";
                    }
                    enum internet {
                      value 6;
                      description
                        "Internetwork control precedence (6)";
                    }
                    enum network {
                      value 7;
                      description
                        "Network control precedence (7)";
                    }
                    enum priority {
                      value 1;
                      description
                        "Priority precedence (1)";
                    }
                    enum routine {
                      value 0;
                      description
                        "Routine precedence (0)";
                    }
                  }
                }
                max-elements 8;
                description
                  "TOS Precedence value(s)";
              }
            }
            container rel-udp {
              description
                "Syslog/netflow packets";
              leaf rate {
                type uint32 {
                  range "0..4294967295" {
                    description
                      "Packets Per Second (actual Min and Max range depends on platform)";
                  }
                }
                description
                  "Rate in PPS";
              }
              leaf-list precedence {
                type union {
                  type uint32 {
                    range "0..7" {
                      description
                        "Precedence value";
                    }
                  }
                  type enumeration {
                    enum critical {
                      value 5;
                      description
                        "Critical precedence (5)";
                    }
                    enum flash {
                      value 3;
                      description
                        "Flash precedence (3)";
                    }
                    enum flash-override {
                      value 4;
                      description
                        "Flash override precedence (4)";
                    }
                    enum immediate {
                      value 2;
                      description
                        "Immediate precedence (2)";
                    }
                    enum internet {
                      value 6;
                      description
                        "Internetwork control precedence (6)";
                    }
                    enum network {
                      value 7;
                      description
                        "Network control precedence (7)";
                    }
                    enum priority {
                      value 1;
                      description
                        "Priority precedence (1)";
                    }
                    enum routine {
                      value 0;
                      description
                        "Routine precedence (0)";
                    }
                  }
                }
                max-elements 8;
                description
                  "TOS Precedence value(s)";
              }
            }
            container dhcpv4 {
              description
                "DHCPv4 ";
              leaf rate {
                type uint32 {
                  range "0..4294967295" {
                    description
                      "Packets Per Second (actual Min and Max range depends on platform)";
                  }
                }
                description
                  "Rate in PPS";
              }
              leaf-list precedence {
                type union {
                  type uint32 {
                    range "0..7" {
                      description
                        "Precedence value";
                    }
                  }
                  type enumeration {
                    enum critical {
                      value 5;
                      description
                        "Critical precedence (5)";
                    }
                    enum flash {
                      value 3;
                      description
                        "Flash precedence (3)";
                    }
                    enum flash-override {
                      value 4;
                      description
                        "Flash override precedence (4)";
                    }
                    enum immediate {
                      value 2;
                      description
                        "Immediate precedence (2)";
                    }
                    enum internet {
                      value 6;
                      description
                        "Internetwork control precedence (6)";
                    }
                    enum network {
                      value 7;
                      description
                        "Network control precedence (7)";
                    }
                    enum priority {
                      value 1;
                      description
                        "Priority precedence (1)";
                    }
                    enum routine {
                      value 0;
                      description
                        "Routine precedence (0)";
                    }
                  }
                }
                max-elements 8;
                description
                  "TOS Precedence value(s)";
              }
            }
            container dhcpv6 {
              description
                "DHCPv6 ";
              leaf rate {
                type uint32 {
                  range "0..4294967295" {
                    description
                      "Packets Per Second (actual Min and Max range depends on platform)";
                  }
                }
                description
                  "Rate in PPS";
              }
              leaf-list precedence {
                type union {
                  type uint32 {
                    range "0..7" {
                      description
                        "Precedence value";
                    }
                  }
                  type enumeration {
                    enum critical {
                      value 5;
                      description
                        "Critical precedence (5)";
                    }
                    enum flash {
                      value 3;
                      description
                        "Flash precedence (3)";
                    }
                    enum flash-override {
                      value 4;
                      description
                        "Flash override precedence (4)";
                    }
                    enum immediate {
                      value 2;
                      description
                        "Immediate precedence (2)";
                    }
                    enum internet {
                      value 6;
                      description
                        "Internetwork control precedence (6)";
                    }
                    enum network {
                      value 7;
                      description
                        "Network control precedence (7)";
                    }
                    enum priority {
                      value 1;
                      description
                        "Priority precedence (1)";
                    }
                    enum routine {
                      value 0;
                      description
                        "Routine precedence (0)";
                    }
                  }
                }
                max-elements 8;
                description
                  "TOS Precedence value(s)";
              }
            }
            container onepk {
              description
                "ONEPK ";
              leaf rate {
                type uint32 {
                  range "0..4294967295" {
                    description
                      "Packets Per Second (actual Min and Max range depends on platform)";
                  }
                }
                description
                  "Rate in PPS";
              }
              leaf-list precedence {
                type union {
                  type uint32 {
                    range "0..7" {
                      description
                        "Precedence value";
                    }
                  }
                  type enumeration {
                    enum critical {
                      value 5;
                      description
                        "Critical precedence (5)";
                    }
                    enum flash {
                      value 3;
                      description
                        "Flash precedence (3)";
                    }
                    enum flash-override {
                      value 4;
                      description
                        "Flash override precedence (4)";
                    }
                    enum immediate {
                      value 2;
                      description
                        "Immediate precedence (2)";
                    }
                    enum internet {
                      value 6;
                      description
                        "Internetwork control precedence (6)";
                    }
                    enum network {
                      value 7;
                      description
                        "Network control precedence (7)";
                    }
                    enum priority {
                      value 1;
                      description
                        "Priority precedence (1)";
                    }
                    enum routine {
                      value 0;
                      description
                        "Routine precedence (0)";
                    }
                  }
                }
                max-elements 8;
                description
                  "TOS Precedence value(s)";
              }
            }
            container tpa {
              description
                "Third Party Applications";
              leaf rate {
                type uint32 {
                  range "0..4294967295" {
                    description
                      "Packets Per Second (actual Min and Max range depends on platform)";
                  }
                }
                description
                  "Rate in PPS";
              }
              leaf-list precedence {
                type union {
                  type uint32 {
                    range "0..7" {
                      description
                        "Precedence value";
                    }
                  }
                  type enumeration {
                    enum critical {
                      value 5;
                      description
                        "Critical precedence (5)";
                    }
                    enum flash {
                      value 3;
                      description
                        "Flash precedence (3)";
                    }
                    enum flash-override {
                      value 4;
                      description
                        "Flash override precedence (4)";
                    }
                    enum immediate {
                      value 2;
                      description
                        "Immediate precedence (2)";
                    }
                    enum internet {
                      value 6;
                      description
                        "Internetwork control precedence (6)";
                    }
                    enum network {
                      value 7;
                      description
                        "Network control precedence (7)";
                    }
                    enum priority {
                      value 1;
                      description
                        "Priority precedence (1)";
                    }
                    enum routine {
                      value 0;
                      description
                        "Routine precedence (0)";
                    }
                  }
                }
                max-elements 8;
                description
                  "TOS Precedence value(s)";
              }
            }
            container ietf-bob {
              description
                "IETF BOB Packets";
              leaf rate {
                type uint32 {
                  range "0..4294967295" {
                    description
                      "Packets Per Second (actual Min and Max range depends on platform)";
                  }
                }
                description
                  "Rate in PPS";
              }
              leaf-list precedence {
                type union {
                  type uint32 {
                    range "0..7" {
                      description
                        "Precedence value";
                    }
                  }
                  type enumeration {
                    enum critical {
                      value 5;
                      description
                        "Critical precedence (5)";
                    }
                    enum flash {
                      value 3;
                      description
                        "Flash precedence (3)";
                    }
                    enum flash-override {
                      value 4;
                      description
                        "Flash override precedence (4)";
                    }
                    enum immediate {
                      value 2;
                      description
                        "Immediate precedence (2)";
                    }
                    enum internet {
                      value 6;
                      description
                        "Internetwork control precedence (6)";
                    }
                    enum network {
                      value 7;
                      description
                        "Network control precedence (7)";
                    }
                    enum priority {
                      value 1;
                      description
                        "Priority precedence (1)";
                    }
                    enum routine {
                      value 0;
                      description
                        "Routine precedence (0)";
                    }
                  }
                }
                max-elements 8;
                description
                  "TOS Precedence value(s)";
              }
            }
            container xipc {
              if-feature "pifib_xipc_throt_policer_config_check";
              description
                "XIPC rate limit";
              leaf rate {
                type uint32 {
                  range "0..4294967295" {
                    description
                      "Packets Per Second (actual Min and Max range depends on platform)";
                  }
                }
                description
                  "Rate in PPS";
              }
              leaf-list precedence {
                type union {
                  type uint32 {
                    range "0..7" {
                      description
                        "Precedence value";
                    }
                  }
                  type enumeration {
                    enum critical {
                      value 5;
                      description
                        "Critical precedence (5)";
                    }
                    enum flash {
                      value 3;
                      description
                        "Flash precedence (3)";
                    }
                    enum flash-override {
                      value 4;
                      description
                        "Flash override precedence (4)";
                    }
                    enum immediate {
                      value 2;
                      description
                        "Immediate precedence (2)";
                    }
                    enum internet {
                      value 6;
                      description
                        "Internetwork control precedence (6)";
                    }
                    enum network {
                      value 7;
                      description
                        "Network control precedence (7)";
                    }
                    enum priority {
                      value 1;
                      description
                        "Priority precedence (1)";
                    }
                    enum routine {
                      value 0;
                      description
                        "Routine precedence (0)";
                    }
                  }
                }
                max-elements 8;
                description
                  "TOS Precedence value(s)";
              }
            }
            container pm-twamp {
              description
                "PM TWAMP Packets";
              leaf rate {
                type uint32 {
                  range "0..4294967295" {
                    description
                      "Packets Per Second (actual Min and Max range depends on platform)";
                  }
                }
                description
                  "Rate in PPS";
              }
              leaf-list precedence {
                type union {
                  type uint32 {
                    range "0..7" {
                      description
                        "Precedence value";
                    }
                  }
                  type enumeration {
                    enum critical {
                      value 5;
                      description
                        "Critical precedence (5)";
                    }
                    enum flash {
                      value 3;
                      description
                        "Flash precedence (3)";
                    }
                    enum flash-override {
                      value 4;
                      description
                        "Flash override precedence (4)";
                    }
                    enum immediate {
                      value 2;
                      description
                        "Immediate precedence (2)";
                    }
                    enum internet {
                      value 6;
                      description
                        "Internetwork control precedence (6)";
                    }
                    enum network {
                      value 7;
                      description
                        "Network control precedence (7)";
                    }
                    enum priority {
                      value 1;
                      description
                        "Priority precedence (1)";
                    }
                    enum routine {
                      value 0;
                      description
                        "Routine precedence (0)";
                    }
                  }
                }
                max-elements 8;
                description
                  "TOS Precedence value(s)";
              }
            }
          }
        }
      }
    }
  }
}
