module Cisco-IOS-XR-um-domain-cfg {

  /*** NAMESPACE / PREFIX DEFINITION ***/

  namespace "http://cisco.com/ns/yang/Cisco-IOS-XR-um-domain-cfg";
  prefix um-domain-cfg;

  /*** LINKAGE (IMPORTS / INCLUDES) ***/

  import Cisco-IOS-XR-types {
    prefix xr;
  }
  import ietf-inet-types {
    prefix inet;
  }

  import cisco-semver { prefix "semver"; }

  /*** META INFORMATION ***/

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR domain package configuration.

     This YANG module augments the
     modules with configuration data.

     Copyright (c) 2021-2022 by Cisco Systems, Inc.
     All rights reserved.";

  revision 2021-02-04 {
    description
      "Initial release";
    semver:module-version "1.0.0";
  }


  container domain {
    description
      "Domain service related commands";
    container list {
      description
        "Domain name to complete unqualified host names";
      list domain {
        key "order domain-name";
        description
          "A domain name";
        leaf order {
          type uint32;
          description
            "This is used to sort the servers in the
             order of precedence";
        }
        leaf domain-name {
          type xr:Cisco-ios-xr-string {
            length "1..1024" {
              description
                "A domain name";
            }
          }
          description
            "A domain name";
        }
      }
    }
    container lookup {
      description
        "Enable Domain Name System hostname translation";
      container disable {
        presence "Indicates a disable node is configured.";
        description
          "Disable Domain Name System hostname translation";
      }
      leaf source-interface {
        type xr:Interface-name;
        description
          "Specify source interface for DNS resolver";
      }
    }
    leaf name {
      type xr:Cisco-ios-xr-string {
        length "1..800" {
          description
            "Default domain name";
        }
      }
      description
        "Define the default domain name";
    }
    container ipv4 {
      description
        "ipv4 hosts";
      container hosts {
        description
          "Add an entry to the ip hostname table";
        list host {
          key "host-name";
          description
            "Name of host";
          leaf host-name {
            type string {
              length "1..800" {
                description
                  "Name of host";
              }
            }
            description
              "Name of host";
          }
          leaf-list ip-address {
            type inet:ipv4-address-no-zone;
            min-elements 1;
            max-elements 8;
            description
              "Host IP address (maximum of 8)";
          }
        }
      }
    }
    container name-servers {
      description
        "Specify address of name server to use";
      list name-server {
        key "order address";
        description
          "Specify address of name server to use";
        leaf order {
          type uint32;
          description
            "This is used to sort the servers in the
             order of precedence";
        }
        leaf address {
          type inet:ip-address-no-zone;
          description
            "Specify address of name server to use";
        }
      }
    }
    container ipv6 {
      description
        "Ipv6 hosts";
      container host {
        description
          "Add an entry to the ipv6 hostname table";
        list host {
          key "host-name";
          description
            "Name of host";
          leaf host-name {
            type string {
              length "1..800" {
                description
                  "Name of host";
              }
            }
            description
              "Name of host";
          }
          leaf-list ipv6-address {
            type inet:ipv6-address-no-zone;
            min-elements 1;
            max-elements 4;
            description
              "IPv6 name or address (maximum four addresses)";
          }
        }
      }
    }
    leaf multicast {
      type xr:Cisco-ios-xr-string {
        length "1..800" {
          description
            "Default multicast domain name";
        }
      }
      description
        "Define the domain name for multicast address lookups";
    }
    container vrfs {
      description
        "VRF name for domain services";
      list vrf {
        key "vrf-name";
        description
          "VRF name for domain services";
        leaf vrf-name {
          type xr:Cisco-ios-xr-string {
            length "1..32" {
              description
                "VRF name";
            }
          }
          description
            "VRF name for domain services";
        }
        container list {
          description
            "Domain name to complete unqualified host names";
          list domain {
            key "order domain-name";
            description
              "A domain name";
            leaf order {
              type uint32;
              description
                "This is used to sort the servers in the
                 order of precedence";
            }
            leaf domain-name {
              type xr:Cisco-ios-xr-string {
                length "1..1024" {
                  description
                    "A domain name";
                }
              }
              description
                "A domain name";
            }
          }
        }
        container lookup {
          description
            "Enable Domain Name System hostname translation";
          container disable {
            presence "Indicates a disable node is configured.";
            description
              "Disable Domain Name System hostname translation";
          }
          leaf source-interface {
            type xr:Interface-name;
            description
              "Specify source interface for DNS resolver";
          }
        }
        leaf name {
          type xr:Cisco-ios-xr-string {
            length "1..800" {
              description
                "Default domain name";
            }
          }
          description
            "Define the default domain name";
        }
        container ipv4 {
          description
            "ipv4 hosts";
          container hosts {
            description
              "Add an entry to the ip hostname table";
            list host {
              key "host-name";
              description
                "Name of host";
              leaf host-name {
                type string {
                  length "1..800" {
                    description
                      "Name of host";
                  }
                }
                description
                  "Name of host";
              }
              leaf-list ip-address {
                type inet:ipv4-address-no-zone;
                min-elements 1;
                max-elements 8;
                description
                  "Host IP address (maximum of 8)";
              }
            }
          }
        }
        container name-servers {
          description
            "Specify address of name server to use";
          list name-server {
            key "order address";
            description
              "Specify address of name server to use";
            leaf order {
              type uint32;
              description
                "This is used to sort the servers in the
                 order of precedence";
            }
            leaf address {
              type inet:ip-address-no-zone;
              description
                "Specify address of name server to use";
            }
          }
        }
        container ipv6 {
          description
            "Ipv6 hosts";
          container host {
            description
              "Add an entry to the ipv6 hostname table";
            list host {
              key "host-name";
              description
                "Name of host";
              leaf host-name {
                type string {
                  length "1..800" {
                    description
                      "Name of host";
                  }
                }
                description
                  "Name of host";
              }
              leaf-list ipv6-address {
                type inet:ipv6-address-no-zone;
                min-elements 1;
                max-elements 4;
                description
                  "IPv6 name or address (maximum four addresses)";
              }
            }
          }
        }
        leaf multicast {
          type xr:Cisco-ios-xr-string {
            length "1..800" {
              description
                "Default multicast domain name";
            }
          }
          description
            "Define the domain name for multicast address lookups";
        }
      }
    }
    container default-flows {
      description
        "default LPTS flows programming";
      container disable {
        presence "Indicates a disable node is configured.";
        description
          "disables default flows programming";
      }
    }
  }
}
