submodule Cisco-IOS-XR-segment-routing-ms-oper-sub1 {

  belongs-to Cisco-IOS-XR-segment-routing-ms-oper {
    prefix Cisco-IOS-XR-segment-routing-ms-oper;
  }

  /*** LINKAGE (IMPORTS / INCLUDES) ***/

  import cisco-semver { prefix "semver"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR segment-routing-ms package operational data.

     Copyright (c) 2013-2023 by Cisco Systems, Inc.
     All rights reserved.";

  revision "2023-08-11" {
    description
      "Increase in interface name length
       2021-12-01
         Increase in interface name length";
    semver:module-version "2.1.0";
  }

  revision "2019-07-19" {
    description
      "Additional items added to operational model.";
    semver:module-version "2.0.0";
  }

  revision "2019-04-05" {
    description
      "Establish semantic version baseline.";
    semver:module-version "1.0.0";
  }

  revision "2017-09-07" {
    description
      "Fixed type translation error.";
  }

  revision "2015-11-09" {
    description
      "IOS XR 6.0 revision.";
  }

  grouping MPLS-LSD-SRLB-INCONSISTENCY {
    description "SRLB Inconsistency";
    leaf start-srlb-range {
      type uint32;
      description
        "Start label of Segment Routing Local Block range";
    }
    leaf end-srlb-range {
      type uint32;
      description "End label of Segment Routing Local Block range";
    }
  }
}
