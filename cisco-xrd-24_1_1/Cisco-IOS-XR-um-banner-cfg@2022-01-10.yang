module Cisco-IOS-XR-um-banner-cfg {

  /*** NAMESPACE / PREFIX DEFINITION ***/

  namespace "http://cisco.com/ns/yang/Cisco-IOS-XR-um-banner-cfg";
  prefix um-banner-cfg;

  /*** LINKAGE (IMPORTS / INCLUDES) ***/
  import cisco-semver { prefix "semver"; }

  /*** META INFORMATION ***/

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR banner package configuration.

     This YANG module augments the
     modules with configuration data.

     Copyright (c) 2020-2022 by Cisco Systems, Inc.
     All rights reserved.";

  revision 2022-01-10 {
    description
      "Updated the description for list banner and leaf banner-type under container banners
       2021-12-12
         Removed the string length constraint from leaf line under container banners ";
    semver:module-version "1.0.0";
  }

  revision "2020-12-14" {
    description
      "Initial release";
    semver:module-version "1.0.0";
  }

  container locale {
    description
      "Define the geographical locale";
    leaf language {
      type enumeration {
        enum aa {
          value 1;
          description
            "Afar";
        }
        enum ab {
          value 2;
          description
            "Abkhazian";
        }
        enum af {
          value 3;
          description
            "Afrikaans";
        }
        enum am {
          value 4;
          description
            "Amharic";
        }
        enum ar {
          value 5;
          description
            "Arabic";
        }
        enum as {
          value 6;
          description
            "Assamese";
        }
        enum ay {
          value 7;
          description
            "Aymara";
        }
        enum az {
          value 8;
          description
            "Azerbaijani";
        }
        enum ba {
          value 9;
          description
            "Bashkir";
        }
        enum be {
          value 10;
          description
            "Byelorussian";
        }
        enum bg {
          value 11;
          description
            "Bulgarian";
        }
        enum bh {
          value 12;
          description
            "Bihari";
        }
        enum bi {
          value 13;
          description
            "Bislama";
        }
        enum bn {
          value 14;
          description
            "Bengali; Bangla";
        }
        enum bo {
          value 15;
          description
            "Tibetan";
        }
        enum br {
          value 16;
          description
            "Breton";
        }
        enum ca {
          value 17;
          description
            "Catalan";
        }
        enum co {
          value 18;
          description
            "Corsican";
        }
        enum cs {
          value 19;
          description
            "Czech";
        }
        enum cy {
          value 20;
          description
            "Welsh";
        }
        enum da {
          value 21;
          description
            "Danish";
        }
        enum de {
          value 22;
          description
            "German";
        }
        enum dz {
          value 23;
          description
            "Bhutani";
        }
        enum el {
          value 24;
          description
            "Greek";
        }
        enum en {
          value 25;
          description
            "English";
        }
        enum eo {
          value 26;
          description
            "Esperanto";
        }
        enum es {
          value 27;
          description
            "Spanish";
        }
        enum et {
          value 28;
          description
            "Estonian";
        }
        enum eu {
          value 29;
          description
            "Basque";
        }
        enum fa {
          value 30;
          description
            "Persian";
        }
        enum fi {
          value 31;
          description
            "Finnish";
        }
        enum fj {
          value 32;
          description
            "Fiji";
        }
        enum fo {
          value 33;
          description
            "Faroese";
        }
        enum fr {
          value 34;
          description
            "French";
        }
        enum fy {
          value 35;
          description
            "Frisian";
        }
        enum ga {
          value 36;
          description
            "Irish";
        }
        enum gd {
          value 37;
          description
            "Scots Gaelic";
        }
        enum gl {
          value 38;
          description
            "Galician";
        }
        enum gn {
          value 39;
          description
            "Guarani";
        }
        enum gu {
          value 40;
          description
            "Gujarati";
        }
        enum ha {
          value 41;
          description
            "Hausa";
        }
        enum he {
          value 42;
          description
            "Hebrew";
        }
        enum hi {
          value 43;
          description
            "Hindi";
        }
        enum hr {
          value 44;
          description
            "Croatian";
        }
        enum hu {
          value 45;
          description
            "Hungarian";
        }
        enum hy {
          value 46;
          description
            "Armenian";
        }
        enum ia {
          value 47;
          description
            "Interlingua";
        }
        enum id {
          value 48;
          description
            "Indonesian";
        }
        enum ie {
          value 49;
          description
            "Interlingue";
        }
        enum ik {
          value 50;
          description
            "Inupiak";
        }
        enum is {
          value 51;
          description
            "Icelandic";
        }
        enum it {
          value 52;
          description
            "Italian";
        }
        enum iu {
          value 53;
          description
            "Inuktitut";
        }
        enum ja {
          value 54;
          description
            "Japanese";
        }
        enum jw {
          value 55;
          description
            "Javanese";
        }
        enum ka {
          value 56;
          description
            "Georgian";
        }
        enum kk {
          value 57;
          description
            "Kazakh";
        }
        enum kl {
          value 58;
          description
            "Greenlandic";
        }
        enum km {
          value 59;
          description
            "Cambodian";
        }
        enum kn {
          value 60;
          description
            "Kannada";
        }
        enum ko {
          value 61;
          description
            "Korean";
        }
        enum ks {
          value 62;
          description
            "Kashmiri";
        }
        enum ku {
          value 63;
          description
            "Kurdish";
        }
        enum ky {
          value 64;
          description
            "Kirghiz";
        }
        enum la {
          value 65;
          description
            "Latin";
        }
        enum ln {
          value 66;
          description
            "Lingala";
        }
        enum lo {
          value 67;
          description
            "Laothian";
        }
        enum lt {
          value 68;
          description
            "Lithuanian";
        }
        enum lv {
          value 69;
          description
            "Latvian, Lettish";
        }
        enum mg {
          value 70;
          description
            "Malagasy";
        }
        enum mi {
          value 71;
          description
            "Maori";
        }
        enum mk {
          value 72;
          description
            "Macedonian";
        }
        enum ml {
          value 73;
          description
            "Malayalam";
        }
        enum mn {
          value 74;
          description
            "Mongolian";
        }
        enum mo {
          value 75;
          description
            "Moldavian";
        }
        enum mr {
          value 76;
          description
            "Marathi";
        }
        enum ms {
          value 77;
          description
            "Malay";
        }
        enum mt {
          value 78;
          description
            "Maltese";
        }
        enum my {
          value 79;
          description
            "Burmese";
        }
        enum na {
          value 80;
          description
            "Nauru";
        }
        enum ne {
          value 81;
          description
            "Nepali";
        }
        enum nl {
          value 82;
          description
            "Dutch";
        }
        enum no {
          value 83;
          description
            "Norwegian";
        }
        enum oc {
          value 84;
          description
            "Occitan";
        }
        enum om {
          value 85;
          description
            "(Afan) Oromo";
        }
        enum or {
          value 86;
          description
            "Oriya";
        }
        enum pa {
          value 87;
          description
            "Punjabi";
        }
        enum pl {
          value 88;
          description
            "Polish";
        }
        enum ps {
          value 89;
          description
            "Pashto, Pushto";
        }
        enum pt {
          value 90;
          description
            "Portuguese";
        }
        enum qu {
          value 91;
          description
            "Quechua";
        }
        enum rm {
          value 92;
          description
            "Rhaeto-Romance";
        }
        enum rn {
          value 93;
          description
            "Kirundi";
        }
        enum ro {
          value 94;
          description
            "Romanian";
        }
        enum ru {
          value 95;
          description
            "Russian";
        }
        enum rw {
          value 96;
          description
            "Kinyarwanda";
        }
        enum sa {
          value 97;
          description
            "Sanskrit";
        }
        enum sd {
          value 98;
          description
            "Sindhi";
        }
        enum sg {
          value 99;
          description
            "Sangho";
        }
        enum sh {
          value 100;
          description
            "Serbo-Croatian";
        }
        enum si {
          value 101;
          description
            "Sinhalese";
        }
        enum sk {
          value 102;
          description
            "Slovak";
        }
        enum sl {
          value 103;
          description
            "Slovenian";
        }
        enum sm {
          value 104;
          description
            "Samoan";
        }
        enum sn {
          value 105;
          description
            "Shona";
        }
        enum so {
          value 106;
          description
            "Somali";
        }
        enum sq {
          value 107;
          description
            "Albanian";
        }
        enum sr {
          value 108;
          description
            "Serbian";
        }
        enum ss {
          value 109;
          description
            "Siswati";
        }
        enum st {
          value 110;
          description
            "Sesotho";
        }
        enum su {
          value 111;
          description
            "Sundanese";
        }
        enum sv {
          value 112;
          description
            "Swedish";
        }
        enum sw {
          value 113;
          description
            "Swahili";
        }
        enum ta {
          value 114;
          description
            "Tamil";
        }
        enum te {
          value 115;
          description
            "Telugu";
        }
        enum tg {
          value 116;
          description
            "Tajik";
        }
        enum th {
          value 117;
          description
            "Thai";
        }
        enum ti {
          value 118;
          description
            "Tigrinya";
        }
        enum tk {
          value 119;
          description
            "Turkmen";
        }
        enum tl {
          value 120;
          description
            "Tagalog";
        }
        enum tn {
          value 121;
          description
            "Setswana";
        }
        enum to {
          value 122;
          description
            "Tonga";
        }
        enum tr {
          value 123;
          description
            "Turkish";
        }
        enum ts {
          value 124;
          description
            "Tsonga";
        }
        enum tt {
          value 125;
          description
            "Tatar";
        }
        enum tw {
          value 126;
          description
            "Twi";
        }
        enum ug {
          value 127;
          description
            "Uighur";
        }
        enum uk {
          value 128;
          description
            "Ukrainian";
        }
        enum ur {
          value 129;
          description
            "Urdu";
        }
        enum uz {
          value 130;
          description
            "Uzbek";
        }
        enum vi {
          value 131;
          description
            "Vietnamese";
        }
        enum vo {
          value 132;
          description
            "Volapuk";
        }
        enum wo {
          value 133;
          description
            "Wolof";
        }
        enum xh {
          value 134;
          description
            "Xhosa";
        }
        enum yi {
          value 135;
          description
            "Yiddish";
        }
        enum yo {
          value 136;
          description
            "Yoruba";
        }
        enum za {
          value 137;
          description
            "Zhuang";
        }
        enum zh {
          value 138;
          description
            "Chinese";
        }
        enum zu {
          value 139;
          description
            "Zulu";
        }
      }
      description
        "Define the language";
    }
    leaf country {
      type enumeration {
        enum AD {
          value 1;
          description
            "Andorra";
        }
        enum AE {
          value 2;
          description
            "United Arab Emirates";
        }
        enum AF {
          value 3;
          description
            "Afghanistan";
        }
        enum AG {
          value 4;
          description
            "Antigua and Barbuda";
        }
        enum AI {
          value 5;
          description
            "Anguilla";
        }
        enum AL {
          value 6;
          description
            "Albania";
        }
        enum AM {
          value 7;
          description
            "Armenia";
        }
        enum AN {
          value 8;
          description
            "Netherlands Antilles";
        }
        enum AO {
          value 9;
          description
            "Angola";
        }
        enum AQ {
          value 10;
          description
            "Antarctica";
        }
        enum AR {
          value 11;
          description
            "Argentina";
        }
        enum AS {
          value 12;
          description
            "American Samoa";
        }
        enum AT {
          value 13;
          description
            "Austria";
        }
        enum AU {
          value 14;
          description
            "Australia";
        }
        enum AW {
          value 15;
          description
            "Aruba";
        }
        enum AZ {
          value 16;
          description
            "Azerbaijan";
        }
        enum BA {
          value 17;
          description
            "Bosnia and Herzegovina";
        }
        enum BB {
          value 18;
          description
            "Barbados";
        }
        enum BD {
          value 19;
          description
            "Bangladesh";
        }
        enum BE {
          value 20;
          description
            "Belgium";
        }
        enum BF {
          value 21;
          description
            "Burkina Faso";
        }
        enum BG {
          value 22;
          description
            "Bulgaria";
        }
        enum BH {
          value 23;
          description
            "Bahrain";
        }
        enum BI {
          value 24;
          description
            "Burundi";
        }
        enum BJ {
          value 25;
          description
            "Benin";
        }
        enum BM {
          value 26;
          description
            "Bermuda";
        }
        enum BN {
          value 27;
          description
            "Brunei Darussalam";
        }
        enum BO {
          value 28;
          description
            "Bolivia";
        }
        enum BR {
          value 29;
          description
            "Brazil";
        }
        enum BS {
          value 30;
          description
            "Bahamas";
        }
        enum BT {
          value 31;
          description
            "Bhutan";
        }
        enum BV {
          value 32;
          description
            "Bouvet Island";
        }
        enum BW {
          value 33;
          description
            "Botswana";
        }
        enum BY {
          value 34;
          description
            "Belarus";
        }
        enum BZ {
          value 35;
          description
            "Belize";
        }
        enum CA {
          value 36;
          description
            "Canada";
        }
        enum CC {
          value 37;
          description
            "Cocos (Keeling) Islands";
        }
        enum CD {
          value 38;
          description
            "Congo, The Democratic Republic of the (Zaire)";
        }
        enum CF {
          value 39;
          description
            "Central African Republic";
        }
        enum CG {
          value 40;
          description
            "Congo";
        }
        enum CH {
          value 41;
          description
            "Switzerland";
        }
        enum CI {
          value 42;
          description
            "Cote D'Ivoire";
        }
        enum CK {
          value 43;
          description
            "Cook Islands";
        }
        enum CL {
          value 44;
          description
            "Chile";
        }
        enum CM {
          value 45;
          description
            "Cameroon";
        }
        enum CN {
          value 46;
          description
            "China";
        }
        enum CO {
          value 47;
          description
            "Colombia";
        }
        enum CR {
          value 48;
          description
            "Costa Rica";
        }
        enum CU {
          value 49;
          description
            "Cuba";
        }
        enum CV {
          value 50;
          description
            "Cape Verde";
        }
        enum CX {
          value 51;
          description
            "Christmas Island";
        }
        enum CY {
          value 52;
          description
            "Cyprus";
        }
        enum CZ {
          value 53;
          description
            "Czech Republic";
        }
        enum DE {
          value 54;
          description
            "Germany";
        }
        enum DJ {
          value 55;
          description
            "Djibouti";
        }
        enum DK {
          value 56;
          description
            "Denmark";
        }
        enum DM {
          value 57;
          description
            "Dominica";
        }
        enum DO {
          value 58;
          description
            "Dominican Republic";
        }
        enum DZ {
          value 59;
          description
            "Algeria";
        }
        enum EC {
          value 60;
          description
            "Ecuador";
        }
        enum EE {
          value 61;
          description
            "Estonia";
        }
        enum EG {
          value 62;
          description
            "Egypt";
        }
        enum EH {
          value 63;
          description
            "Western Sahara";
        }
        enum ER {
          value 64;
          description
            "Eritrea";
        }
        enum ES {
          value 65;
          description
            "Spain";
        }
        enum ET {
          value 66;
          description
            "Ethiopia";
        }
        enum FI {
          value 67;
          description
            "Finland";
        }
        enum FJ {
          value 68;
          description
            "Fiji";
        }
        enum FK {
          value 69;
          description
            "Falkland Islands (Malvinas)";
        }
        enum FM {
          value 70;
          description
            "Micronesia, Federated States of";
        }
        enum FO {
          value 71;
          description
            "Faroe Islands";
        }
        enum FR {
          value 72;
          description
            "France";
        }
        enum GA {
          value 73;
          description
            "Gabon";
        }
        enum GB {
          value 74;
          description
            "United Kingdom";
        }
        enum GD {
          value 75;
          description
            "Grenada";
        }
        enum GE {
          value 76;
          description
            "Georgia";
        }
        enum GF {
          value 77;
          description
            "French Guiana";
        }
        enum GH {
          value 78;
          description
            "Ghana";
        }
        enum GI {
          value 79;
          description
            "Gibraltar";
        }
        enum GL {
          value 80;
          description
            "Greenland";
        }
        enum GM {
          value 81;
          description
            "Gambia";
        }
        enum GN {
          value 82;
          description
            "Guinea";
        }
        enum GP {
          value 83;
          description
            "Guadeloupe";
        }
        enum GQ {
          value 84;
          description
            "Equatorial Guinea";
        }
        enum GR {
          value 85;
          description
            "Greece";
        }
        enum GS {
          value 86;
          description
            "South Georgia and the South Sandwich Islands";
        }
        enum GT {
          value 87;
          description
            "Guatemala";
        }
        enum GU {
          value 88;
          description
            "Guam";
        }
        enum GW {
          value 89;
          description
            "Guinea-Bissau";
        }
        enum GY {
          value 90;
          description
            "Guyana";
        }
        enum HK {
          value 91;
          description
            "Hong Kong";
        }
        enum HM {
          value 92;
          description
            "Heard Island and McDonald Islands";
        }
        enum HN {
          value 93;
          description
            "Honduras";
        }
        enum HR {
          value 94;
          description
            "Croatia";
        }
        enum HT {
          value 95;
          description
            "Haiti";
        }
        enum HU {
          value 96;
          description
            "Hungary";
        }
        enum ID {
          value 97;
          description
            "Indonesia";
        }
        enum IE {
          value 98;
          description
            "Ireland";
        }
        enum IL {
          value 99;
          description
            "Israel";
        }
        enum IN {
          value 100;
          description
            "India";
        }
        enum IO {
          value 101;
          description
            "British Indian Ocean Territory";
        }
        enum IQ {
          value 102;
          description
            "Iraq";
        }
        enum IR {
          value 103;
          description
            "Iran, Islamic Republic of";
        }
        enum IS {
          value 104;
          description
            "Iceland";
        }
        enum IT {
          value 105;
          description
            "Italy";
        }
        enum JM {
          value 106;
          description
            "Jamaica";
        }
        enum JO {
          value 107;
          description
            "Jordan";
        }
        enum JP {
          value 108;
          description
            "Japan";
        }
        enum KE {
          value 109;
          description
            "Kenya";
        }
        enum KG {
          value 110;
          description
            "Kyrgyzstan";
        }
        enum KH {
          value 111;
          description
            "Cambodia";
        }
        enum KI {
          value 112;
          description
            "Kiribati";
        }
        enum KM {
          value 113;
          description
            "Comoros";
        }
        enum KN {
          value 114;
          description
            "Saint Kitts and Nevis";
        }
        enum KP {
          value 115;
          description
            "Korea, Democratic People's Republic of";
        }
        enum KR {
          value 116;
          description
            "Korea, Republic of";
        }
        enum KW {
          value 117;
          description
            "Kuwait";
        }
        enum KY {
          value 118;
          description
            "Cayman Islands";
        }
        enum KZ {
          value 119;
          description
            "Kazakstan";
        }
        enum LA {
          value 120;
          description
            "Lao People's Democratic Republic";
        }
        enum LB {
          value 121;
          description
            "Lebanon";
        }
        enum LC {
          value 122;
          description
            "Saint Lucia";
        }
        enum LI {
          value 123;
          description
            "Liechtenstein";
        }
        enum LK {
          value 124;
          description
            "Sri Lanka";
        }
        enum LR {
          value 125;
          description
            "Liberia";
        }
        enum LS {
          value 126;
          description
            "Lesotho";
        }
        enum LT {
          value 127;
          description
            "Lithuania";
        }
        enum LU {
          value 128;
          description
            "Luxembourg";
        }
        enum LV {
          value 129;
          description
            "Latvia";
        }
        enum LY {
          value 130;
          description
            "Libyan Arab Jamahiriya";
        }
        enum MA {
          value 131;
          description
            "Morocco";
        }
        enum MC {
          value 132;
          description
            "Monaco";
        }
        enum MD {
          value 133;
          description
            "Moldova, Republic of";
        }
        enum MG {
          value 134;
          description
            "Madagascar";
        }
        enum MH {
          value 135;
          description
            "Marshall Islands";
        }
        enum MK {
          value 136;
          description
            "Macedonia, The Former Yugoslav Republic of";
        }
        enum ML {
          value 137;
          description
            "Mali";
        }
        enum MM {
          value 138;
          description
            "Myanmar";
        }
        enum MN {
          value 139;
          description
            "Mongolia";
        }
        enum MO {
          value 140;
          description
            "Macau";
        }
        enum MP {
          value 141;
          description
            "Northern Mariana Islands";
        }
        enum MQ {
          value 142;
          description
            "Martinique";
        }
        enum MR {
          value 143;
          description
            "Mauritania";
        }
        enum MS {
          value 144;
          description
            "Montserrat";
        }
        enum MT {
          value 145;
          description
            "Malta";
        }
        enum MU {
          value 146;
          description
            "Mauritius";
        }
        enum MV {
          value 147;
          description
            "Maldives";
        }
        enum MW {
          value 148;
          description
            "Malawi";
        }
        enum MX {
          value 149;
          description
            "Mexico";
        }
        enum MY {
          value 150;
          description
            "Malaysia";
        }
        enum MZ {
          value 151;
          description
            "Mozambique";
        }
        enum NA {
          value 152;
          description
            "Namibia";
        }
        enum NC {
          value 153;
          description
            "New Caledonia";
        }
        enum NE {
          value 154;
          description
            "Niger";
        }
        enum NF {
          value 155;
          description
            "Norfolk Island";
        }
        enum NG {
          value 156;
          description
            "Nigeria";
        }
        enum NI {
          value 157;
          description
            "Nicaragua";
        }
        enum NL {
          value 158;
          description
            "Netherlands";
        }
        enum NO {
          value 159;
          description
            "Norway";
        }
        enum NP {
          value 160;
          description
            "Nepal";
        }
        enum NR {
          value 161;
          description
            "Nauru";
        }
        enum NU {
          value 162;
          description
            "Niue";
        }
        enum NZ {
          value 163;
          description
            "New Zealand";
        }
        enum OM {
          value 164;
          description
            "Oman";
        }
        enum PA {
          value 165;
          description
            "Panama";
        }
        enum PE {
          value 166;
          description
            "Peru";
        }
        enum PF {
          value 167;
          description
            "French Polynesia";
        }
        enum PG {
          value 168;
          description
            "Papua New Guinea";
        }
        enum PH {
          value 169;
          description
            "Philippines";
        }
        enum PK {
          value 170;
          description
            "Pakistan";
        }
        enum PL {
          value 171;
          description
            "Poland";
        }
        enum PM {
          value 172;
          description
            "Saint Pierre and Miquelon";
        }
        enum PN {
          value 173;
          description
            "Pitcairn";
        }
        enum PR {
          value 174;
          description
            "Puerto Rico";
        }
        enum PT {
          value 175;
          description
            "Portugal";
        }
        enum PW {
          value 176;
          description
            "Palau";
        }
        enum PY {
          value 177;
          description
            "Paraguay";
        }
        enum QA {
          value 178;
          description
            "Qatar";
        }
        enum RE {
          value 179;
          description
            "Reunion";
        }
        enum RO {
          value 180;
          description
            "Romania";
        }
        enum RU {
          value 181;
          description
            "Russian Federation";
        }
        enum RW {
          value 182;
          description
            "Rwanda";
        }
        enum SA {
          value 183;
          description
            "Saudi Arabia";
        }
        enum SB {
          value 184;
          description
            "Solomon Islands";
        }
        enum SC {
          value 185;
          description
            "Seychelles";
        }
        enum SD {
          value 186;
          description
            "Sudan";
        }
        enum SE {
          value 187;
          description
            "Sweden";
        }
        enum SG {
          value 188;
          description
            "Singapore";
        }
        enum SH {
          value 189;
          description
            "Saint Helena";
        }
        enum SI {
          value 190;
          description
            "Slovenia";
        }
        enum SJ {
          value 191;
          description
            "Svalbard and Jan Mayen";
        }
        enum SK {
          value 192;
          description
            "Slovakia";
        }
        enum SL {
          value 193;
          description
            "Sierra Leone";
        }
        enum SM {
          value 194;
          description
            "San Marino";
        }
        enum SN {
          value 195;
          description
            "Senegal";
        }
        enum SO {
          value 196;
          description
            "Somalia";
        }
        enum SR {
          value 197;
          description
            "Suriname";
        }
        enum ST {
          value 198;
          description
            "Sao Tome and Principe";
        }
        enum SV {
          value 199;
          description
            "El Salvador";
        }
        enum SY {
          value 200;
          description
            "Syrian Arab Republic";
        }
        enum SZ {
          value 201;
          description
            "Swaziland";
        }
        enum TC {
          value 202;
          description
            "Turks and Caicos Islands";
        }
        enum TD {
          value 203;
          description
            "Chad";
        }
        enum TF {
          value 204;
          description
            "French Southern Territories";
        }
        enum TG {
          value 205;
          description
            "Togo";
        }
        enum TH {
          value 206;
          description
            "Thailand";
        }
        enum TJ {
          value 207;
          description
            "Tajikistan";
        }
        enum TK {
          value 208;
          description
            "Tokelau";
        }
        enum TM {
          value 209;
          description
            "Turkmenistan";
        }
        enum TN {
          value 210;
          description
            "Tunisia";
        }
        enum TO {
          value 211;
          description
            "Tonga";
        }
        enum TP {
          value 212;
          description
            "East Timor";
        }
        enum TR {
          value 213;
          description
            "Turkey";
        }
        enum TT {
          value 214;
          description
            "Trinidad and Tobago";
        }
        enum TV {
          value 215;
          description
            "Tuvalu";
        }
        enum TW {
          value 216;
          description
            "Taiwan, Province of China";
        }
        enum TZ {
          value 217;
          description
            "Tanzania, United Republic of";
        }
        enum UA {
          value 218;
          description
            "Ukraine";
        }
        enum UG {
          value 219;
          description
            "Uganda";
        }
        enum UM {
          value 220;
          description
            "United States Minor Outlying Islands";
        }
        enum US {
          value 221;
          description
            "United States";
        }
        enum UY {
          value 222;
          description
            "Uruguay";
        }
        enum UZ {
          value 223;
          description
            "Uzbekistan";
        }
        enum VA {
          value 224;
          description
            "Holy See (Vatican City State)";
        }
        enum VC {
          value 225;
          description
            "Saint Vincent and The Grenadines";
        }
        enum VE {
          value 226;
          description
            "Venezuela";
        }
        enum VG {
          value 227;
          description
            "Virgin Islands, British";
        }
        enum VI {
          value 228;
          description
            "Virgin Islands, U.S.";
        }
        enum VN {
          value 229;
          description
            "Vietnam";
        }
        enum VU {
          value 230;
          description
            "Vanuatu";
        }
        enum WF {
          value 231;
          description
            "Wallis and Futuna";
        }
        enum WS {
          value 232;
          description
            "Samoa";
        }
        enum YE {
          value 233;
          description
            "Yemen";
        }
        enum YT {
          value 234;
          description
            "Mayotte";
        }
        enum YU {
          value 235;
          description
            "Yugoslavia";
        }
        enum ZA {
          value 236;
          description
            "South Africa";
        }
        enum ZM {
          value 237;
          description
            "Zambia";
        }
        enum ZW {
          value 238;
          description
            "Zimbabwe";
        }
      }
      description
        "Define the country";
    }
  }
  container banners {
    description
      "Define a login banner";
    list banner {
      key "banner-type";
      description
        "Define the banner";
      leaf banner-type {
        type enumeration {
          enum exec {
            value 0;
            description
              "Set EXEC process creation banner";
          }
          enum incoming {
            value 1;
            description
              "Set incoming terminal line banner";
          }
          enum motd {
            value 2;
            description
              "Set Message of the Day banner";
          }
          enum login {
            value 3;
            description
              "Set login banner";
          }
          enum slip-ppp {
            value 4;
            description
              "Set Message for SLIP/PPP";
          }
          enum prompt-timeout {
            value 5;
            description
              "Set Message for login authentication timeout";
          }
        }
        description
          "Select the banner type";
      }
      leaf line {
        type string;
        mandatory true;
        description
          "c banner-text c, where 'c' is a delimiting character";
      }
    }
  }
  container default-value {
    description
      "Default character-bits values";
    leaf exec-character-bits {
      type uint32 {
        range "7..8" {
          description
            "Bits per character";
        }
      }
      description
        "Size of characters to the command exec";
    }
  }
}
