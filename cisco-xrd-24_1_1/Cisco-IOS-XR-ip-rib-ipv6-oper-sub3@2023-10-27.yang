submodule Cisco-IOS-XR-ip-rib-ipv6-oper-sub3 {

  belongs-to Cisco-IOS-XR-ip-rib-ipv6-oper {
    prefix Cisco-IOS-XR-ip-rib-ipv6-oper;
  }

  /*** LINKAGE (IMPORTS / INCLUDES) ***/

  import cisco-semver { prefix "semver"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ip-rib-ipv6 package operational data.

     Copyright (c) 2013-2023 by Cisco Systems, Inc.
     All rights reserved.";

  revision "2023-10-27" {
    description
      "Minor protocol and infosource field renaming for consistency
       2023-10-06
         Add IID Context for NextHop Groups
       2023-09-20
         Consolidate RIB schemas to use unioned IPv4/IPv6 address
       2023-08-31
         Update RIB-EDM-PATH-IP-TUNNEL-INFO
       2023-02-16
         Update RIB NHID info
       2022-12-13
         Modify RIB opaque redist history
       2022-12-02
         Modify RIB redist history
       2022-11-23
         Modify RIB stats
       2022-11-03
         Update IID Context for Segment List Identifier
       2022-09-13
         Add IID Context for Segment List Identifier
       2022-08-29
         Segment List Identifier added to a routes path
       2022-08-18
         Updated IID entry infromation to display IID as an IPv6 prefix
       2022-07-04
         Add IID Context for L2VPN IP Tunnels. Add Remote Tunnel Endpoint ID: RTEP ID, to resolve via tunnel.
       2022-06-03
         Static Sid State has algo field
       2022-05-31
         SRv6 Adjacency Contexts updated to use interface name
       2022-05-11
         has-aft added to route
       2022-04-26
         Clear AFT stats added
       2022-02-18
         Add client id, proto id, flags, backup number and distance to opaque bag Added table-id for opaque redistribution history
       2022-02-03
         Add SID resource usage information
       2022-01-11
         Add IID Context for AFT NextHop Groups
       2021-12-16
         Updated aft route and path attributes with vrf names
       2021-12-16
         Added VNI to ip tunnel info path attribute
       2021-12-14
         Updated aft route and path attributes
       2021-11-26
         Add IID Local to known Protocol Types, and sync with existing types in ipv4-oper
       2021-11-25
         Added is delayed delete flag on routes local SID list
       2021-11-17
         Add AFT id path and route attributes
       2021-10-29
         Added Opaque redistribution history
       2021-09-24
         New path vpn attribute for ip tunnels";
    semver:module-version "5.0.0";
  }

  revision "2021-08-08" {
    description
      "SRv6 uSID context extended with uDX
      2021-07-20
          Flexible Algorithm attribute added to IP Route
      2021-06-24
          IID context extended with EVPN ELAN support SRv6 SID context extended with EVPN ELAN support uDT2U uDT2M EndDT2U EndDT2M L2 Path attribute extended with support for Split Horizong Group and BridgeID
      2021-03-31
          SRv6 SID Manager include per operation mode block parameters
      2021-03-25
          Add FIB redistribution flag to route bag
      2021-03-14
          SRv6 SID context extensions";
    semver:module-version "4.1.0";
  }

  revision "2020-12-11" {
    description
      "Add forwarding sidlist
      2020-09-30
           Nexthop notification model now includes client specific registration flags
      2020-09-24
           Changes to SRv6 uSID platform capabilities
      2020-07-24
           SRv6 uSID context extended for evpn";
    semver:module-version "4.0.0";
  }

  revision "2020-05-29" {
    description
      "Updated the max number of elements for opaque stats to 16 Extended rib edm path to include IID info and SID Format type
      2020-04-30
         Updated sidmgr oper to add contexts for F1 SID: DT6, DX6
      2020-04-02
         Increased path_num size in redist hist route bag to 16 bits
      2019-12-05
         Extended SidMgr info to include uSID platform capabilities
      2019-11-21
         Extended SidMgr info to include flag string and anycast flag";
    semver:module-version "3.0.0";
  }

  revision "2019-11-05" {
    description
      "Extended Nexthop and NexhopPrefix paths to include all by NH flags
      2019-10-22
         Extended rib_edm_client_stats_summary to include client stats on bcdl ugs Extended rib_edm_local_label to support AIB prefer Added EDM support for large SID stack Extended rib_edm_path to include recursion length field Extended rib_edm_path to include metric field Extended iidmgr_summary to include oor summary info Extended rib_edm_route to include l3 route type field";
    semver:module-version "2.0.0";
  }

  revision "2019-06-28" {
    description
      "Fixed NexthopPrefix path";
    semver:module-version "1.0.0";
  }

  revision "2019-06-15" {
    description
      "Fixed IPv6 Address format for Nexthops";
  }

  revision "2019-06-08" {
    description
      "Added RPF list and NHIDs";
  }

  revision "2019-05-30" {
    description
      "Fixed adverts and backup paths";
  }

  revision "2019-05-17" {
    description
      "Added Nexthops Summary, Nexthop Route, Longer Routes, Redist Clients and Client Stasts";
  }

  revision "2019-04-25" {
    description
      "Updated yang schema to extend Native Yang model for the data exposed via CLI";
  }

  revision "2019-04-05" {
    description
      "Establish semantic version baseline.";
  }

  revision "2019-02-21" {
    description
      "Yang evaluator: updates to schema descriptions and ranges";
  }

  revision "2019-01-11" {
    description
      "Route lookup key is limited to Prefix and Prefix Length";
  }

  revision "2018-11-20" {
    description
      "Add keys for route lookup via restconf.";
  }

  revision "2018-11-06" {
    description
      "Support Algorithm Label List per route";
  }

  revision "2017-09-07" {
    description
      "Fixed type translation error.";
  }

  revision "2015-11-09" {
    description
      "IOS XR 6.0 revision.";
  }

  grouping RIB-EDM-PROTO {
    description "Information of a rib protocol";
    leaf protocol-name {
      type string;
      description "Name";
    }
    leaf protocol-instance {
      type string;
      description "Instance";
    }
    leaf protocol-version {
      type uint32;
      description "Proto version";
    }
    leaf number-of-redistribution-clients {
      type uint32;
      description "Number of redist clients";
    }
    leaf number-of-protocol-clients {
      type uint32;
      description "Number of proto clients";
    }
    leaf number-of-routes {
      type uint32;
      description "Number of routes (including deleted)";
    }
    leaf number-of-active-routes {
      type uint32;
      description "Number of active routes (not deleted)";
    }
    leaf number-of-deleted-routes {
      type uint32;
      description "Number of deleted routes";
    }
    leaf number-of-paths {
      type uint32;
      description "Number of paths for all routes";
    }
    leaf protocol-route-memory {
      type uint32;
      description "Memory for proto's routes and paths";
    }
    leaf backup-routes-count {
      type uint32;
      description "Number of backup routes";
    }
  }
}
