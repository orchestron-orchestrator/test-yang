module Cisco-IOS-XR-um-hw-module-quad-cfg {

  /*** NAMESPACE / PREFIX DEFINITION ***/

  namespace "http://cisco.com/ns/yang/Cisco-IOS-XR-um-hw-module-quad-cfg";
  prefix um-hw-module-quad-cfg;

  /*** LINKAGE (IMPORTS / INCLUDES) ***/

  import Cisco-IOS-XR-um-location-cfg {
    prefix location;
  }

  import cisco-semver { prefix "semver"; }

  /*** META INFORMATION ***/

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR hw-module-quad package configuration.

     This YANG module augments the
     modules with configuration data.

     Copyright (c) 2020-2022 by Cisco Systems, Inc.
     All rights reserved.";

  revision 2022-07-11 {
    description
      "Added missing description statement to nodes";
    semver:module-version "1.1.0";
  }

  revision "2020-12-14" {
    description
      "Initial release";
    semver:module-version "1.0.0";
  }

  grouping LOCATION-BODY {
    description
      "Grouping for location";
    container instances {
      description
        "quad configuration";
      list instance {
        must 'quad';
        key "instance-id";
        description
          "0 for LC ports, 1+ for MPA instances";
        leaf instance-id {
          type uint32 {
            range "0..5";
          }
          description
            "Instance number";
        }
        list quad {
          key "quad-id";
          description
            "Configure quad.";
          leaf quad-id {
            type uint32 {
              range "0..11" {
                description
                  "configure quad properties";
              }
            }
            description
              "Configure quad.";
          }
          leaf mode {
            type string;
            mandatory true;
            description
              "select mode 10g or 25g for a quad (group of 2 or 4 ports)";
          }
        }
      }
    }
  }

  augment "/location:locations/location:location" {
    description
      "This augment extends active nodes configuration";
    uses LOCATION-BODY;
  }

  augment "/location:locations/location:preconfigured-location" {
    description
      "This augment extends preconfigured nodes
       configuration";
    uses LOCATION-BODY;
  }
}
