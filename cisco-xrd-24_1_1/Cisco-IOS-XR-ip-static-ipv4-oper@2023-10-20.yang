module Cisco-IOS-XR-ip-static-ipv4-oper {

  /*** NAMESPACE / PREFIX DEFINITION ***/

  namespace "http://cisco.com/ns/yang"+
    "/Cisco-IOS-XR-ip-static-ipv4-oper";


  prefix "ip-static-ipv4-oper";

  /*** LINKAGE (IMPORTS / INCLUDES) ***/

  import Cisco-IOS-XR-types { prefix "xr"; }

  import cisco-semver { prefix "semver"; }

  include Cisco-IOS-XR-ip-static-ipv4-oper-sub1 {
    revision-date 2023-10-20;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ip-static-ipv4 package operational data.

     This module contains definitions
     for the following management objects:
       ipv4-local: Local Routing Information
       ipv4-static: Static Routing Information
       ipv4-connected: Connected Routing Information

     Copyright (c) 2013-2023 by Cisco Systems, Inc.
     All rights reserved.";

  revision "2023-10-20" {
    description
      "Fixed support for ipv4-sr-policy-detail
       2023-06-21
         Added new elements to display nodeDB and Protect events
       2021-10-29
         Added leaf node for ip address algorithm";
    semver:module-version "2.0.0";
  }

  revision "2020-11-20" {
    description
      "Added leaf node for prefer RIB over LDP";
    semver:module-version "1.2.0";
  }

  revision "2019-12-12" {
    description
      "Added leaf node for FlexAlgo for srv6";
    semver:module-version "1.1.0";
  }

  revision "2019-06-01" {
    description
      "Added oper ipv4 support for fridb, colocation, sr-policy
      2019-05-13
         Added ipv4 support for bfd sessions, object track database and segment routing";
    semver:module-version "1.1.0";
  }

  revision "2019-04-05" {
    description
      "Establish semantic version baseline.";
    semver:module-version "1.0.0";
  }

  revision "2019-01-03" {
    description
      "Added oper ipv4 support";
  }

  revision "2015-11-09" {
    description
      "IOS XR 6.0 revision.";
  }

  typedef Safi {
    type enumeration {
      enum unicast {
        value 1;
        description "unicast type";
      }
      enum multicast {
        value 2;
        description "multicast type";
      }
    }
    description "Safi";
  }
  typedef Afi {
    type enumeration {
      enum ipv4 {
        value 1;
        description "ipv4 addressfamily";
      }
      enum ipv6 {
        value 2;
        description "ipv6 addressfamily";
      }
    }
    description "Afi";
  }
  typedef Ipv4friafi {
    type enumeration {
      enum ipv4 {
        value 1;
        description "ipv4 addressfamily";
      }
      enum ipv6 {
        value 2;
        description "ipv6 addressfamily";
      }
    }
    description "Ipv4friafi";
  }
  typedef Ipv4frisafi {
    type enumeration {
      enum unicast {
        value 1;
        description "unicast type";
      }
      enum multicast {
        value 2;
        description "multicast type";
      }
    }
    description "Ipv4frisafi";
  }

  grouping TOPO-VRF-TABLE {
    description
      "Common node of ipv4-static, ipv4-local,
      ipv4-connected";

    container topo-vrfs {
      description "vrf list for Topology";

      list topo-vrf {
        key "vrf-name";
        description "vrf name";
        leaf vrf-name {
          type xr:Cisco-ios-xr-string;
          description "The name of thei vrf";
        }

        list topo-table {
          key "table-name";
          description "Topology table name";
          leaf table-name {
            type xr:Cisco-ios-xr-string;
            description "The name of the atble";
          }

          list topo-afi {
            key "afi";
            description "Topology address family type";
            leaf afi {
              type Afi;
              description "IPv4 AFI";
            }

            list topo-safi {
              key "safi";
              description "Topology SAFI type";

              container destinations {
                description "route info";

                list destination {
                  description
                    "Destinatioin address and prefix length";
                  leaf prefix {
                    type xr:Cisco-ios-xr-string;
                    description "detaination address prefix";
                  }
                  leaf prefix-length {
                    type xr:Hex-integer;
                    description "detaination prefix length";
                  }
                  uses IPV4-STATIC-ROUTE-BD;
                }
              }
              leaf safi {
                type Safi;
                description "IPv4 SAFI";
              }
            }
          }
        }
      }
    }
  }

  grouping NHVRF-TABLE {
    description
      "Common node of ipv4-static, ipv4-local,
      ipv4-connected";

    container nhvrfs {
      description "next-hop's vrf list";

      list nhvrf {
        key "vrf-name";
        description "vrf name";
        leaf vrf-name {
          type xr:Cisco-ios-xr-string;
          description "The name of thei vrf";
        }

        list nh-table {
          key "table-name";
          description "next-hop table name";
          leaf table-name {
            type xr:Cisco-ios-xr-string;
            description "The name of the atble";
          }

          list nhafi {
            key "afi";
            description "next-hop address family type";
            leaf afi {
              type Afi;
              description "IPv4 AFI";
            }

            list nhsafi {
              key "safi";
              description "next-hop safi(unicat|multicast) type";

              container nh-addresses {
                description "next hop Database";

                list nh-address {
                  key "next-hop-addr";
                  description "next-hop address to display";
                  leaf next-hop-addr {
                    type xr:Cisco-ios-xr-string;
                    description "next hop address";
                  }
                  uses IPV4-STATIC-NHDB-BD;
                }
              }
              leaf safi {
                type Safi;
                description "IPv4 SAFI";
              }
            }
          }
        }
      }
    }
  }

  grouping TABLE {
    description
      "Common node of ipv4-static, ipv4-local,
      ipv4-connected";

    container table-ids {
      description "list of Tables";

      list table-id {
        key "table-id";
        description "Table ID to display";
        leaf table-id {
          type xr:Hex-integer;
          description "Table ID";
        }
        uses IP-STATIC-TDB-BD;
      }
    }
  }

  grouping IPV4-PROTECT-NODE-DB {
    description "Common node of ipv4-local, ipv4-connected";

    container ipv4-protect-nodes {
      description "ipv4 Protect Node Database";

      list ipv4-protect-node {
        key "node";
        description "Protect Node to display";
        leaf node {
          type xr:Node-id;
          description "Node ID";
        }
        uses IPV4-STATIC-PROT-NODE-BD;
      }
    }
  }

  grouping BFDVRF-TABLE {
    description
      "Common node of ipv4-static, ipv4-local,
      ipv4-connected";

    container bfdvrfs {
      description "BFD's vrf list";

      list bfdvrf {
        key "vrf-name";
        description "vrf name";
        leaf vrf-name {
          type xr:Cisco-ios-xr-string;
          description "The name of the vrf";
        }

        list bfd-table {
          key "table-name";
          description "BFD table name";
          leaf table-name {
            type xr:Cisco-ios-xr-string;
            description "The name of the table";
          }

          list bfdafi {
            key "afi";
            description "BFD address family type";
            leaf afi {
              type Afi;
              description "IPv4 AFI";
            }

            list bfdsafi {
              key "safi";
              description "BFD safi(unicat|multicast) type";

              container bfd-addresses {
                description "list of BFD sessions";

                list bfd-address {
                  key "bfd-next-hop-addr";
                  description "BFD next-hop address to display";
                  leaf bfd-next-hop-addr {
                    type xr:Cisco-ios-xr-string;
                    description "BFD next hop address";
                  }
                  uses IPV4-STATIC-NHDB-BFD-BD;
                }
              }
              leaf safi {
                type Safi;
                description "IPv4 SAFI";
              }
            }
          }
        }
      }
    }
  }

  grouping IPV4-IF-DB {
    description
      "Common node of ipv4-static, ipv4-local,
      ipv4-connected";

    container ipv4vrfs {
      description "ipv4 interface database";

      list ipv4vrf {
        key "vrf-name";
        description "vrf name";
        leaf vrf-name {
          type xr:Cisco-ios-xr-string;
          description "The name of the";
        }

        list ipv4-table {
          key "table-name";
          description "table name";
          leaf table-name {
            type xr:Cisco-ios-xr-string;
            description "The name of the atble";
          }

          list ipv4afi {
            key "afi";
            description "address family type";
            leaf afi {
              type Afi;
              description "IPv4 AFI";
            }

            list ipv4safi {
              key "safi";
              description "unicast|multicast";
              leaf safi {
                type Safi;
                description "IPv4 SAFI";
              }

              list ipv4-interface {
                key "interface-name";
                description "Interface to display";
                leaf interface-name {
                  type xr:Interface-name;
                  description "Interface name";
                }
                uses IPV4-STATIC-IDB-BD;
              }
            }
          }
        }
      }
    }
  }

  grouping TABLE-EVENTS {
    description
      "Common node of ipv4-static, ipv4-local,
      ipv4-connected";

    container table-events-ids {
      description "list of Tables";

      list table-events-id {
        key "table-id";
        description "Table ID to display events info";
        leaf table-id {
          type xr:Hex-integer;
          description "Table ID";
        }
        uses EVT-HIST-INFO;
      }
    }
  }

  grouping IPV4FRIDB {
    description "Common node of ipv4-local, ipv4-connected";

    container ipv4fridbvrfs {
      description "ipv4 forward database";

      list ipv4fridbvrf {
        key "vrf-name";
        description "vrf name";
        leaf vrf-name {
          type xr:Cisco-ios-xr-string;
          description "Forward DB vrf name";
        }

        list ipv4fridb-table {
          key "table-name";
          description "table name";
          leaf table-name {
            type xr:Cisco-ios-xr-string;
            description "The name of the forward DB table";
          }

          list ipv4fridbafi {
            key "afitype";
            description "address family type";
            leaf afitype {
              type Ipv4friafi;
              description "IPv4 AFI";
            }

            list ipv4fridbsafi {
              key "safitype";
              description "unicast|multicast";
              leaf safitype {
                type Ipv4frisafi;
                description "IPv4 SAFI";
              }

              list ipv4fridb-interface {
                key "interface-name";
                description "forward DB Interface to display";
                leaf interface-name {
                  type xr:Interface-name;
                  description "forward DB Interface name";
                }
                uses IP-STATIC-FRIDB-BD;
              }
            }
          }
        }
      }
    }
  }

  grouping IPV4-PROTECT-NODE-EVENTS-DB {
    description "Common node of ipv4-local, ipv4-connected";

    container ipv4-protect-node-events {
      description "Protect interface event info";

      list ipv4-protect-node-event {
        key "node";
        description "Protect interface event";
        leaf node {
          type xr:Node-id;
          description "Node ID";
        }

        list ipv4-protect-interface-event {
          key "name";
          description "Protect Interface to display";
          leaf name {
            type xr:Interface-name;
            description "Interface Name";
          }
          uses IPV4-STATIC-PROT-INTF-EVENT-BD;
        }
      }
    }
  }

  container ipv4-local {
    config false;
    description "Local Routing Information";
    uses IPV4-PROTECT-NODE-DB;
    uses IPV4-IF-DB;
    uses NHVRF-TABLE;
    uses IPV4-PROTECT-NODE-EVENTS-DB;
    uses IPV4FRIDB;
    uses TABLE-EVENTS;
    uses BFDVRF-TABLE;
    uses TOPO-VRF-TABLE;
    uses TABLE;
  }

  container ipv4-static {
    config false;
    description "Static Routing Information";

    container ipv4-sr-policy-details {
      description "ipv4 sr-policy interface database";

      list ipv4-sr-policy-detail {
        key "srpolicy";
        description "sr policy to display";
        leaf srpolicy {
          type xr:Cisco-ios-xr-string;
          description "sr policy name";
        }
        uses IPV4-STATIC-XTC-DB-BD;
      }
    }

    container track-object-names {
      description "list of track objects";

      list track-object-name {
        key "ot-name";
        description "Track object to display";
        leaf ot-name {
          type xr:Cisco-ios-xr-string;
          description "The name of the tacking object";
        }
        uses IPV4-STATIC-OTDB-BD;
      }
    }

    container colocationvrf-names {
      description "list of colocation vrfs";

      list colocationvrf-name {
        key "vrf";
        description
          "vrf name of table id to display colocation list";
        leaf vrf {
          type xr:Cisco-ios-xr-string;
          description "vrf name";
        }

        list colocation-table {
          key "table-name";
          description "table name to display colocation list";
          leaf table-name {
            type xr:Cisco-ios-xr-string;
            description "table name";
          }

          list colocation-afi {
            key "afi";
            description "Colocation address family type";
            leaf afi {
              type Afi;
              description "IPv4 AFI";
            }

            list colocation-safi {
              key "safi";
              description "Colocation safi(unicat|multicast) type";

              container colo-table-ids {
                description "tables to display colocation list";

                list colo-table-id {
                  key "table-id";
                  description "table to display colocation list";
                  leaf table-id {
                    type xr:Hex-integer;
                    description "Table ID";
                  }
                  uses IP-STATIC-COLOCATION-BD;
                }
              }
              leaf safi {
                type Safi;
                description "IPv4 SAFI";
              }
            }
          }
        }
      }
    }

    container exp-paths {
      description "list of isegment routes";

      list exp-path {
        key "exp-path";
        description "Explicit path to display";
        leaf exp-path {
          type xr:Cisco-ios-xr-string;
          description "The name of the tacking object";
        }
        uses IPV4-STATIC-TEDB-BD;
      }
    }
    uses IPV4-IF-DB;
    uses NHVRF-TABLE;
    uses TABLE-EVENTS;
    uses BFDVRF-TABLE;
    uses TOPO-VRF-TABLE;
    uses TABLE;
  }

  container ipv4-connected {
    config false;
    description "Connected Routing Information";
    uses IPV4-PROTECT-NODE-DB;
    uses IPV4-IF-DB;
    uses NHVRF-TABLE;
    uses IPV4-PROTECT-NODE-EVENTS-DB;
    uses IPV4FRIDB;
    uses TABLE-EVENTS;
    uses BFDVRF-TABLE;
    uses TOPO-VRF-TABLE;
    uses TABLE;
  }
}
