module Cisco-IOS-XR-controller-ots-otdr-act {
  namespace "http://cisco.com/ns/yang/Cisco-IOS-XR-controller-ots-otdr-act";
  prefix controller-ots-otdr-act;

  import Cisco-IOS-XR-types {
     prefix xr;
   }

  import cisco-semver { prefix "semver"; }

  organization
    "Cisco Systems, Inc.";
  contact
    "Cisco Systems, Inc.
     Customer Service
     Postal: 170 West Tasman Drive
     San Jose, CA 95134
     Tel: +1 800 553-NETS
     E-mail: cs-yang@cisco.com";
  description
    "This module contains a collection of YANG definitions
     for Cisco IOS-XR tone pattern for controller-ots module.
     Copyright (c) 2018-2023 by Cisco Systems, Inc.
     All rights reserved.";

  revision 2022-12-22 {
    description
      "OTDR action support for ots controllers";
    semver:module-version "1.0.0";
  }


  typedef Scan-type {
     type enumeration {
       enum stop {
         value 0;
         description "scan stop";
       }
       enum start {
         value 1;
         description "scan start";
       }
     }
     description "Scan type";
  }

  rpc ots-controller-otdr {
    description
      "ots controller OTDR generation";
    input {
      leaf controller {
        type xr:Interface-name;
        description
          "Controller name in R/S/I/P format";
      }
      leaf otdr-scan-rx {
        type Scan-type;
        description
          "OTDR SCAN at RX : Select otdr-scan-rx as start or stop";
      }
      leaf otdr-scan-tx {
        type Scan-type;
        description
          "OTDR SCAN at TX : select otdr-scan-tx as start or stop";
      }
    }
  }
}
