module Cisco-IOS-XR-ipv4-ospf-act {
  namespace "http://cisco.com/ns/yang/Cisco-IOS-XR-ipv4-ospf-act";
  prefix ospf-act;

  import cisco-semver {
    prefix semver;
  }
  import Cisco-IOS-XR-types {
    prefix xr;
  }
  import ietf-inet-types {
    prefix inet;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR OSPF action package configuration.

     Copyright (c) 2016-2020, 2022 by Cisco Systems, Inc.
     All rights reserved.";

  revision 2020-08-13 {
    description
      "Added xr-task name ospf to restrict unlimited permission";
    semver:module-version "1.1.0";
  }

  revision "2019-10-01" {
    description
      "Made changes to be RFC6087 compliant";
    semver:module-version "1.1.0";
  }

  revision "2019-04-05" {
    description
      "Establish semantic version baseline.";
    semver:module-version "1.0.0";
  }

  revision "2016-09-14" {
    description
      "IOS XR 6.2.1 revision.";
  }

  grouping OSPF-STAT-ATTRIBUTES {
    description
      "OSPF Stat Attributes";
    leaf process {
      type empty;
      description
        "Reset OSPF process";
    }
    leaf redistribution {
      type empty;
      description
        "Clear OSPF route redistrbution";
    }
    leaf route {
      type empty;
      description
        "Clear OSPF route table";
    }
    container stats {
      description
        "OSPF counters and statistics";
      leaf spf {
        type empty;
        description
          "SPF statistics";
      }
      leaf message-queue {
        type empty;
        description
          "Message-queue statistics";
      }
      container interface {
        description
          "OSPF interface statistics";
        leaf interface-name {
          type xr:Interface-name;
          description
            "OSPF Interface name";
        }
      }
      container neighbor {
        description
          "Neighbor statistics per interface or neighbor id";
        leaf neighbor-id {
          type inet:ipv4-address;
          description
            "Neighbor ID";
        }
        container interface {
          description
            "OSPF Interface";
          leaf interface-name {
            type xr:Interface-name;
            description
              "OSPF interface statistics";
          }
        }
      }
    }
  }

  rpc clear-ospf-routes {
    description
      "Clear OSPF route table";
    input {
      container instance {
        description
          "Clear data from OSPF instance";
        leaf instance-identifier {
          type string;
          description
            "OSPF process instance identifier";
        }
      }
      leaf route {
        type empty;
        mandatory true;
        description
          "Clear OSPF route table";
      }
    }
  }
  rpc clear-ospf-redistribution {
    description
      "Clear OSPF route redistribution";
    input {
      container instance {
        description
          "Clear data from OSPF instance";
        leaf instance-identifier {
          type string;
          description
            "OSPF process instance identifier";
        }
      }
      leaf redistribution {
        type empty;
        mandatory true;
        description
          "Clear OSPF route redistribution";
      }
    }
  }
  rpc clear-ospf-statistics {
    description
      "Clear OSPF counters and statistics";
    input {
      container instance {
        description
          "Clear data from OSPF instance";
        leaf instance-identifier {
          type string;
          description
            "OSPF process instance identifier";
        }
      }
      leaf all {
        type empty;
        description
          "All OSPF counters and statistics";
      }
      leaf message-queue {
        type empty;
        description
          "Message-queue statistics";
      }
      leaf spf {
        type empty;
        description
          "SPF statistics";
      }
      leaf neighbor {
        type empty;
        description
          "Neighbor statistics per neighbor id";
      }
      leaf interface-name {
        type empty;
        description
          "OSPF interface statistics";
      }
    }
  }
  rpc clear-ospf-statistics-neighbor {
    description
      "Clear OSPF neighbor statistics per interface or neighbor id";
    input {
      container instance {
        description
          "Clear data from OSPF instance";
        leaf instance-identifier {
          type string;
          description
            "OSPF process instance identifier";
        }
      }
      container neighbor {
        description
          "OSPF neighbor";
        leaf neighbor-id {
          type inet:ipv4-address;
          description
            "Neighbor ID";
        }
        leaf interface-name {
          type xr:Interface-name;
          description
            "Interface";
        }
      }
    }
  }
  rpc clear-ospf-statistics-interface {
    description
      "Clear OSPF interface statistics";
    input {
      container instance {
        description
          "Clear data from OSPF instance";
        leaf instance-identifier {
          type string;
          description
            "OSPF process instance identifier";
        }
      }
      container interface {
        description
          "OSPF interface";
        leaf interface-name {
          type xr:Interface-name;
          description
            "OSPF interface statistics";
        }
      }
    }
  }
  rpc clear-ospf-process {
    description
      "Clear (reset) OSPF process";
    input {
      container instance {
        description
          "Clear data from OSPF instance";
        leaf instance-identifier {
          type string;
          description
            "OSPF process instance identifier";
        }
      }
      leaf process {
        type empty;
        mandatory true;
        description
          "Reset OSPF process";
      }
    }
  }
  rpc clear-ospf-instance-vrf {
    description
      "Clear one or more non-default OSPF VRFs in process";
    input {
      container instance {
        description
          "OSPF instance name";
        leaf instance-identifier {
          type string;
          mandatory true;
          description
            "OSPF process instance identifier";
        }
        container vrf {
          description
            "Clear one or more non-default OSPF VRFs in process";
          leaf vrf-name {
            type string;
            description
              "OSPF VRF name";
          }
          uses OSPF-STAT-ATTRIBUTES;
        }
        container all {
          description
            "Clear all non-default OSPF VRFs";
          uses OSPF-STAT-ATTRIBUTES;
        }
        container all-inclusive {
          description
            "Clear all non-default and default OSPF VRFs";
          uses OSPF-STAT-ATTRIBUTES;
        }
      }
    }
  }
}
