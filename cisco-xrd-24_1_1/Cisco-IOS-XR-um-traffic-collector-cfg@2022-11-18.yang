module Cisco-IOS-XR-um-traffic-collector-cfg {

  /*** NAMESPACE / PREFIX DEFINITION ***/

  namespace "http://cisco.com/ns/yang/Cisco-IOS-XR-um-traffic-collector-cfg";
  prefix um-traffic-collector-cfg;

  /*** LINKAGE (IMPORTS / INCLUDES) ***/

  import Cisco-IOS-XR-types {
    prefix xr;
  }

  import cisco-semver { prefix "semver"; }

  /*** META INFORMATION ***/

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR traffic-collector package configuration.

     This YANG module augments the
     modules with configuration data.

     Copyright (c) 2021-2022 by Cisco Systems, Inc.
     All rights reserved.";

  revision 2022-11-18 {
    description
      "Config to disable tc oc-aft stats";
    semver:module-version "1.1.0";
  }

  revision "2021-06-29" {
    description
      "Initial release";
    semver:module-version "1.0.0";
  }

  container traffic-collector {
    presence "Indicates a traffic-collector node is configured.";
    description
      "Traffic Collector";
    container interfaces {
      description
        "Configure an External interface";
      list interface {
        key "interface-name";
        description
          "Configure an External interface";
        leaf interface-name {
          type xr:Interface-name;
          description
            "Configure an External interface";
        }
      }
    }
    container statistics {
      presence "Indicates a statistics node is configured.";
      description
        "Configure statistics related parameters";
      leaf collection-interval {
        type enumeration {
          enum 1 {
            value 1;
            description
              "1 minute (default)";
          }
          enum 2 {
            value 2;
            description
              "2 minutes";
          }
          enum 3 {
            value 3;
            description
              "3 minutes";
          }
          enum 4 {
            value 4;
            description
              "4 minutes";
          }
          enum 5 {
            value 5;
            description
              "5 minutes";
          }
          enum 6 {
            value 6;
            description
              "6 minutes";
          }
          enum 10 {
            value 10;
            description
              "10 minutes";
          }
          enum 12 {
            value 12;
            description
              "12 minutes";
          }
          enum 15 {
            value 15;
            description
              "15 minutes";
          }
          enum 20 {
            value 20;
            description
              "20 minutes";
          }
          enum 30 {
            value 30;
            description
              "30 minutes";
          }
          enum 60 {
            value 60;
            description
              "60 minutes";
          }
        }
        description
          "Configure statistics collection interval";
      }
      container history-minute-timeout {
        presence "Indicates a history-minute-timeout node is configured.";
        description
          "Change history-timeout to represent minutes instead of hours";
      }
      leaf history-timeout {
        type uint32 {
          range "0..720" {
            description
              "Timeout interval (hours, 0 to specify immediate timeout. default is 48)";
          }
        }
        description
          "Configure statistics history timeout interval";
      }
      leaf history-size {
        type uint32 {
          range "1..10" {
            description
              "History size (default is 5)";
          }
        }
        description
          "Configure statistics history size";
      }
    }
    container oc-aft {
      description
        "Configure OC-AFT stats related parameters";
      leaf collection-interval {
        type enumeration {
          enum 1 {
            value 1;
            description
              "1 minute (default)";
          }
          enum 2 {
            value 2;
            description
              "2 minutes";
          }
          enum 3 {
            value 3;
            description
              "3 minutes";
          }
          enum 4 {
            value 4;
            description
              "4 minutes";
          }
          enum 5 {
            value 5;
            description
              "5 minutes";
          }
          enum 6 {
            value 6;
            description
              "6 minutes";
          }
          enum 10 {
            value 10;
            description
              "10 minutes";
          }
          enum 12 {
            value 12;
            description
              "12 minutes";
          }
          enum 15 {
            value 15;
            description
              "15 minutes";
          }
          enum 20 {
            value 20;
            description
              "20 minutes";
          }
          enum 30 {
            value 30;
            description
              "30 minutes";
          }
          enum 60 {
            value 60;
            description
              "60 minutes";
          }
        }
        description
          "Configure statistics collection interval";
      }
      container stats-disable {
        presence "Indicates a stats-disable node is configured.";
        description
          "Disable periodic streaming/collection of AFT label stats";
      }
    }
  }
}
