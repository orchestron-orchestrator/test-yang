submodule Cisco-IOS-XR-es-ace-cfg {

  belongs-to Cisco-IOS-XR-es-acl-cfg {
    prefix es-acl-cfg;
  }

  import cisco-semver { prefix "semver"; }
  
  import Cisco-IOS-XR-es-acl-datatypes {
    prefix "es-acl-dt";
  }

  import Cisco-IOS-XR-types {
    prefix "xr";
  }

  organization "Cisco Systems, Inc.";

  contact
    "Cisco Systems, Inc.
     Customer Service

     Postal: 170 West Tasman Drive
     San Jose, CA 95134

     Tel: +1 800 553-NETS

     E-mail: cs-yang@cisco.com";

  description
    "This module contains a collection of YANG definitions
     for Cisco IOS-XR ES ACL entry configuration.

     Copyright (c) 2015-2019, 2022-2023 by Cisco Systems, Inc.
     All rights reserved.";

  revision "2022-08-16" {
    description
      "Deprecated the native model, replaced by UM model.";
  }

  revision "2019-04-05" {
    description
      "Establish semantic version baseline.";
    semver:module-version "1.0.0";
  }
  
  revision "2018-02-26" {
    description
      "6.5.1 revision.
       Fixed datatypes for below leaves:
       - vlan1, vlan2
       - inner-vlan1, inner-vlan2
       - cos, inner-cos
       - dei, inner-dei
       - log-option"; 
  }

  revision "2018-02-21" {
    description
      "Changed ether-type-number to type Hex-integer-16.";
  }

  revision "2018-01-03" {
    description
      "6.4.1 revision.
       Fixed a few typos in the description.";
  }

  revision "2017-05-01" {
    description
      "Fixing backward compatibility error in module.";
  }

  revision "2015-11-09" {
    description
      "Initial revision.";
  }

  typedef es-acl-grant-enum {
    type enumeration {
      enum deny {
        value 0;
        description "Deny";
      }
      enum permit {
        value 1;
        description "Permit";
      }
    }
    description "ES ACL forwarding action.";
  }

  typedef es-acl-address {
     type string {
       pattern '([0-9a-fA-F]{1,4}(\.[0-9a-fA-F]{1,4}){2})';
     }
     description "ES ACL address";
  }

  grouping ES-ACL-CONFIG-ACE {
    description "ES ACE entry.";
    leaf grant {
      type es-acl-grant-enum;
      description "Forwarding action for the packet. This is required 
                   for any non-remark ACE. Leave unspecified otherwise.";
    }

    container source-network {
      description "Source network settings.";
      leaf source-address {
        type es-acl-address;
        description "Source address to match, leave unspecified
                     for any.";
      }
      leaf source-wild-card-bits {
        type es-acl-address;
        description "Wildcard bits to apply to source address
                     (if specified), leave unspecified for no
                     wildcarding.";
      }
    }

    container destination-network {
      description "Destination network settings.";
      leaf destination-address {
        type es-acl-address;
        description "Destination address to match (if a protocol
                     was specified), leave unspecified for any.";
      }
      leaf destination-wild-card-bits {
        type es-acl-address;
        description "Wildcard bits to apply to destination address
                     (if specified), leave unspecified for no
                     wildcarding.";
      }
    }
    leaf vlan1 {
      type es-acl-dt:Es-acl-vlan-range;
      description "This 12-bit VLAN-ID in the VLAN Tag header uniquely
                   identifies the VLAN. It can be used for the lower bound
                   (in range) or single value. Any value not in the
                   permissible range will be rejected.";
      reference "IEEE 802.1Q";             
    }
    leaf vlan2 {
      type es-acl-dt:Es-acl-vlan-range;
      description "This 12 bit VLAN-ID in the VLAN Tag header uniquely
                   identifies the VLAN. It is used in the upper bound
                   (in range). Any value not in the permissible range
                   will be rejected.";
      reference "IEEE 802.1Q";
    }
    leaf cos {
      type es-acl-dt:Es-acl-cos-range;
      description "Class of Service value. Any value not in the 
                   permissible range will be rejected."; 
      reference "IEEE 802.1p";
    }
    leaf dei {
      type es-acl-dt:Es-acl-dei-range;
      description "Discard Eligibility Indication bit. User can specify 
                   1 to indicate the bit is set. Leave unspecified
                   otherwise."; 
      reference "RFC 7180 Section 7";
    }
    leaf inner-vlan1 {
      type es-acl-dt:Es-acl-vlan-range;
      description "This represents the QinQ vlan identifier. It can be used for
                   the lower bound (in range) or single value. Any value not 
                   in the permissible range will be rejected.";
      reference "IEEE 802.1Q";
    }
    leaf inner-vlan2 {
      type es-acl-dt:Es-acl-vlan-range;
      description "This represents the QinQ vlan identifier. It is used in 
                   the upper bound (in range). Any value not in the permissible
                   range will be rejected.";
      reference "IEEE 802.1Q";              
    }
    leaf inner-cos {
      type es-acl-dt:Es-acl-cos-range;
      description "Class of Service of Inner Header. Any value not in the
                   permissible range will be rejected."; 
      reference "IEEE 802.1p";
    }
    leaf inner-dei {
      type es-acl-dt:Es-acl-dei-range;
      description "Discard Eligibility Indication for Inner Header. User 
                   can specify 1 to indicate the bit is set. Leave 
                   unspecified otherwise.";
      reference "RFC 7180 Section 7";             
    }

    leaf remark {
      type string {
        length  "0..255";
      }  
      description "Description for the access-list-entry/rule."; 
    } 

    leaf ether-type-number {
      type xr:Hex-integer-16;
      description "Ethernet type Number in Hex. Any value not in the
                   permissible range will be rejected.";
      reference "IEEE 802 Ether types";
    }
 
    leaf capture {
      type boolean;
      description "Enable capture if set to TRUE.";
    } 

    leaf log-option {
      type es-acl-dt:Es-acl-log-range;
      description "Log the packet on this access-list-entry/rule.
                   User can specify 1 to enable logging
                   the match, leave unspecified otherwise."; 
    }

    leaf sequence-str {
      type string {
        length  "1..64";
      }
      description "Sequence String for the ace.";
    }
   
  }
}
