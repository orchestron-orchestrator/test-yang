module Cisco-IOS-XR-fib-common-oper {

  /*** NAMESPACE / PREFIX DEFINITION ***/

  namespace "http://cisco.com/ns/yang/Cisco-IOS-XR-fib-common-oper";


  prefix "fib-common-oper";

  /*** LINKAGE (IMPORTS / INCLUDES) ***/

  import ietf-inet-types { prefix "inet"; }

  import ietf-yang-types { prefix "yang"; }

  import Cisco-IOS-XR-types { prefix "xr"; }

  import cisco-semver { prefix "semver"; }

  include Cisco-IOS-XR-fib-common-oper-sub8 {
    revision-date 2024-01-12;
  }

  include Cisco-IOS-XR-fib-common-oper-sub7 {
    revision-date 2024-01-12;
  }

  include Cisco-IOS-XR-fib-common-oper-sub6 {
    revision-date 2024-01-12;
  }

  include Cisco-IOS-XR-fib-common-oper-sub5 {
    revision-date 2024-01-12;
  }

  include Cisco-IOS-XR-fib-common-oper-sub4 {
    revision-date 2024-01-12;
  }

  include Cisco-IOS-XR-fib-common-oper-sub3 {
    revision-date 2024-01-12;
  }

  include Cisco-IOS-XR-fib-common-oper-sub2 {
    revision-date 2024-01-12;
  }

  include Cisco-IOS-XR-fib-common-oper-sub1 {
    revision-date 2024-01-12;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR fib-common package operational data.

     This module contains definitions
     for the following management objects:
       fib-statistics: cef interface drops operational data
       fib: FIB operational data
       oc-aft-l3: Openconfig L3 abstract forwarding table data
       mpls-forwarding: MPLS forwarding operational data
       cef-accounting: CEF accounting operational data

     Copyright (c) 2013-2024 by Cisco Systems, Inc.
     All rights reserved.";

  revision "2024-01-12" {
    description
      "Add back error/oor state for telemetry in oc-aft-l3 model
       2023-12-01
         Add platform-pbtsv6-support to platform capabilities
       2023-11-27
         Optimized schema for linklocal. Added is-non-recursive field to IP prefixes.
       2023-10-25
         Added GIL ID in PWHE information and Interface List attribute
       2023-10-19
         Added NextHop group ID to ext client output
       2023-10-11
         Added schema for external client, fixed schema for hardware egress/ingress
       2023-10-10
         Added and modified NPU mask and PWHE information
       2023-10-04
         Added encap-id and stat-id to recursive-nexthop dependents.
       2023-10-02
         Added VXLAN TEP tables.
       2023-09-21
         Eliminate name conflicts between keys and values
       2023-09-18
         Separated schema of linklocal prefix table from generic prefix table.
       2023-09-14
         Added via-nexthop-group to show cef output
       2023-08-15
         Added new errors sub-tree.
       2023-07-31
         Made hierarchical-loadbalancing parameters mandatory
       2023-07-28
         Internal cleanup, some type name changes.
       2023-07-26
         Fixed schema for exact-route and linklocal
       2023-07-17
         Changed pbts related variable type from static to dynamic array
       2023-07-13
         Added is-unresolved and is-frr to prefix tables
       2023-07-07
         Standardized leaf names and types throughout.
       2023-06-26
         Fix schema for hardware egress/ingress option
       2023-06-15
         Changed vni-info-key-type to an enum and added tblid-vni-key to vni-info-key-type
       2023-06-02
         Two Stage platform ObjectId capability added for cef-misc
       2023-06-01
         Added new field to ltep-nve-tunnels in order keep track of destination address protocol
       2023-05-31
         SRv6 accounting support added for FIB cef
       2023-05-25
         SRv6 accounting support added for FIB cef-accounting
       2023-05-24
         Added new detail field for hardware egress/ingress option
       2023-05-11
         Added class-id to support full exact-route functionality
       2023-05-08
         Remove oc-aft model from fib oper model
       2023-05-04
         Added new field to rtep-tunnels in order keep track of destination address protocol
       2023-04-24
         Combined separate evni tables for BGP and RTEP-ID to single evni table
       2023-04-15
         Added changes for show cef Interface
       2023-04-14
         Added hardware ingress and egress path for evni
       2023-04-05
         Added srv6_hardware ingress/egress
       2023-03-31
         Added resource-summary-infos and modified ip-prefix-detail
       2023-03-29
         Changed recursive nexthop display to be generic for address types
       2023-03-28
         Modified Interface List ID size from 16-bit to 32-bit
       2023-03-28
         Modifed fib_sh_policy_rl_entry rate field to uint64_t
       2023-03-20
         Added some preprograming related fields.
       2023-03-18
         Removed node tag from cef-accounting container.
       2023-03-06
         Added global policy table
       2023-02-07
         Added Exact route schema changes
       2023-02-06
         Added proto-retry-db-summary.
       2023-02-06
         Added disable-rfc5549-ipv4-over-ipv6-nexthop platform capability.
       2023-01-27
         Updated schema for ResourceHardwareIngress and Egress support
       2023-01-27
         Added exceptions-v4, exceptions-v6 and exceptions-mpls.
       2023-01-25
         Added global-retry-db-summary.
       2023-01-24
         Added cef-table-summary, drops-v6 and drops-mpls.
       2023-01-23
         srv6 accounting support
       2023-01-20
         Summary statistics: Added udp-src-port-msb information
       2023-01-04
         Updated evni-tunnel-bgp keys for VxLAN support
       2022-12-20
         Added changes for NHInfoHardwareIngress and NHInfoHardwareEgress in schema file.
       2022-12-06
         Added destionation address to Tunnel Decap, added destination address and underlay table id to Tunnel Decap-NVE
       2022-11-07
         protocol origin changes
       2022-11-01
         Updated FIB ext-client info bag to support ECD LTEP registrations
       2022-10-17
         CNHG changes
       2022-10-05
         Added PWHE and NPU mask for interface details
       2022-10-04
         Tunnel Encap/Decap: Added Prefix Length to the source and destination addresses
       2022-09-22
         Rate limiter statistics: Added drop stats
       2022-09-15
         Added Internal ID in PW-HE extension
       2022-08-29
         Summary statistics: Added udp-port information
       2022-07-19
         Added async-ack-support to FIB-SH-PLAT-CAPABILITIES, and ack-status, ack-latency, to FIB-GRIBI-ENTRY-INFO and FIB-GLOBAL-GRIBI-ENTRY.
       2022-07-07
         Added VRF base filtering for MPLS label stats
       2022-06-14
         Added program id, dst_ip and src_ip in next-hop and nhg fib.bag
       2022-06-13
         Added destination address to nve-ltep bag
       2022-05-13
         Added aft vrf-id to gribi bags
       2022-04-27
         Added vxlan-vni-id to ltep-tunnel
       2022-04-25
         Added RNH state
       2022-04-08
         Added table statistics
       2022-03-31
         Added sr-frr-nhid to frr-nhinfo-pending
       2022-03-24
         Added retry counts to object summary attributes
       2022-03-15
         Added vxlan-tunnels
       2022-03-01
         Added policy and hardware ingress and egress paths
       2022-02-16
         Added some SRv6 SIDs data
       2021-12-14
         Added gribi-table and hardware ingress and egress paths
       2021-11-26
         Added ltep-tunnels and hardware ingress and egress paths
       2021-11-05
         Added rtep-tunnels and hardware ingress and egress paths
       2021-11-03
         Added ltep-nve-tunnels hardware ingress and egress paths
       2021-10-23
         Added ltep-nve-tunnels and added object-id to object-base";
    semver:module-version "5.0.0";
  }

  revision "2021-10-17" {
    description
      "Modify the type of list fsum-attr-cnt
      2021-09-17
          Rename lists unicast-prefix, broadcast-prefix and leafs num-retry-objects, old-unresolved-entries, new-unresolved-entries, unresolved-entries
      2021-07-30
          Added evpn bridge ID and SHG ID to srv6-information-for-path bag
      2021-07-06
          Added global-main subtree and support show CLIs for FIB IPC infra
      2021-05-25
          Migrate NHINFO to TI infra";
    semver:module-version "4.0.0";
  }

  revision "2020-12-02" {
    description
      "Adding per-object accounting.
      2020-10-20
           NBC documentation of CSCvu06764, CSCvv14573,CSCvv76648
      2020-05-26
           Update SRv6 Block Space naming convention
      2020-05-05
           changes related to treat SRv6 and SID as well-known when parsing XML for yang";
    semver:module-version "3.0.0";
  }

  revision "2020-01-16" {
    description
      "NBC documentation of CSCvs27272,CSCvs22018,CSCvs45512
      2019-10-29
         Updated srv6 global bag";
    semver:module-version "2.0.0";
  }

  revision "2019-09-27" {
    description
      "IOS XR 7.0.x revision.";
    semver:module-version "1.1.0";
  }

  revision "2019-04-05" {
    description
      "Establish semantic version baseline.";
    semver:module-version "1.0.0";
  }

  revision "2019-04-02" {
    description
      "Fixed schema descriptions.";
  }

  revision "2017-09-07" {
    description
      "Fixed type translation error.";
  }

  revision "2017-05-01" {
    description
      "Fixing backward compatibility error in module.";
  }

  revision "2017-01-20" {
    description
      "IOS XR 6.2.1 revision";
  }

  revision "2015-11-09" {
    description
      "IOS XR 6.0 revision.";
  }

  typedef Fib-global-policy {
    type enumeration {
      enum fib-global-policy-tbl-invalid {
        value 0;
        description "Invalid";
      }
      enum fib-global-policy-tbl-saf-type {
        value 1;
        description "saf";
      }
      enum fib-global-policy-tbl-rl-type {
        value 2;
        description "rate limit";
      }
      enum fib-global-policy-tbl-udp-port-type {
        value 3;
        description "udp port";
      }
    }
    description "Fib global policy";
  }
  typedef Fib-route-source {
    type enumeration {
      enum lsd {
        value 5;
        description "LSD";
      }
      enum rib {
        value 7;
        description "RIB";
      }
      enum mrib {
        value 14;
        description "MRIB";
      }
    }
    description "Fib route source";
  }
  typedef Fib-protocol {
    type enumeration {
      enum ipv4 {
        value 0;
        description "ipv4 protocol";
      }
      enum ipv6 {
        value 1;
        description "ipv6 protocol";
      }
      enum mpls {
        value 2;
        description "MPLS protocol";
      }
    }
    description "Fib protocol";
  }
  typedef Fib-adjacency {
    type enumeration {
      enum none {
        value 0;
        description "Invalid type of adjacency";
      }
      enum tx-nh {
        value 1;
        description "Tx Nhinfo type of adjacency";
      }
      enum tx-interface {
        value 2;
        description "Tx Interface type of adjacency";
      }
    }
    description "Fib adjacency";
  }
  typedef Resource-summary-info-dir {
    type enumeration {
      enum rsrc-summary-ingress {
        value 0;
        description "show ingress";
      }
      enum rsrc-summary-egress {
        value 1;
        description "show egress";
      }
    }
    description "Resource summary info dir";
  }
  typedef Prefix-hardware-table {
    type enumeration {
      enum sw-flg {
        value 0;
        description "Software";
      }
      enum hw-egress-flg {
        value 32;
        description "Hardware Egress";
      }
      enum hw-egress-detail-flg {
        value 33;
        description "Hardware Egress detail";
      }
      enum hw-ingress-flg {
        value 64;
        description "Hardware Ingress";
      }
      enum hw-ingress-detail-flg {
        value 65;
        description "Hardware Ingress detail";
      }
    }
    description "Prefix hardware table";
  }
  typedef Fib-object {
    type enumeration {
      enum none {
        value 0;
        description "None";
      }
      enum adjacency {
        value 8;
        description "NHINFO";
      }
      enum all {
        value 23;
        description "ALL";
      }
    }
    description "Fib object";
  }
  typedef Fibipv6-flow-label {
    type uint32 {
      range "0..1048575";
    }
    description "Fibipv6 flow label";
  }
  typedef Ipvpn-tunnel {
    type enumeration {
      enum ipvpn-tunnel-type-invalid {
        value 0;
        description "Invalid";
      }
      enum ipvpn-tunnel-type-l2tp {
        value 1;
        description "l2tpv3";
      }
      enum ipvpn-tunnel-type-mgre {
        value 2;
        description "merge";
      }
      enum ipvpn-tunnel-type-vxlan-l2 {
        value 3;
        description "vxlan l2";
      }
      enum ipvpn-tunnel-type-gre {
        value 4;
        description "gre";
      }
      enum ipvpn-tunnel-type-ip {
        value 5;
        description "ip";
      }
      enum ipvpn-tunnel-type-te {
        value 6;
        description "te";
      }
      enum ipvpn-tunnel-type-vxlan-l3 {
        value 7;
        description "vxlan l3";
      }
      enum ipvpn-tunnel-type-vxlan-l3-sfi {
        value 8;
        description "vxlan l3 sfi";
      }
      enum ipvpn-tunnel-type-mpl-so-udp {
        value 9;
        description "mpls udp";
      }
      enum ipvpn-tunnel-type-nh {
        value 10;
        description "ip nh";
      }
      enum ipvpn-tunnel-type-nh-tbl {
        value 11;
        description "ip nh tbl";
      }
      enum ipvpn-tunnel-type-vxlan {
        value 12;
        description "vxlan";
      }
      enum ipvpn-tunnel-type-per-interface {
        value 13;
        description "per intf";
      }
      enum ipvpn-tunnel-type-max {
        value 14;
        description "max";
      }
    }
    description "Ipvpn tunnel";
  }
  typedef Resource-summary-info-hardware {
    type enumeration {
      enum rsrc-summary-no-hardware {
        value 0;
        description "show no hardware";
      }
      enum rsrc-summary-hardware {
        value 1;
        description "show detail";
      }
    }
    description "Resource summary info hardware";
  }
  typedef Fib-interest {
    type enumeration {
      enum fib-interest-type-ip-reach-notif {
        value 0;
        description "IP Reachability Notification";
      }
      enum fib-interest-type-eos0-ldi-notif {
        value 1;
        description "EOS0 LDI Notification";
      }
      enum fib-interest-type-ip-ldi-notif {
        value 2;
        description "IP LDI Notification";
      }
      enum fib-interest-type-nh-notif {
        value 3;
        description "NH Notification";
      }
      enum fib-interest-type-lsm-id-notif {
        value 4;
        description "LSM ID Notification";
      }
      enum fib-interest-type-mpls-reach-notif {
        value 5;
        description "MPLS Reachability Notification";
      }
      enum fib-interest-type-label-eos0-ldi-notif {
        value 6;
        description "Label EOS0 LDI Reachability";
      }
      enum fib-interest-type-label-eos1-ldi-notif {
        value 7;
        description "Label EOS1 LDI Reachability";
      }
      enum fib-interest-type-mpls-route-notif {
        value 8;
        description "IP Reachability";
      }
    }
    description "Fib interest";
  }
  typedef Resource-summary-info-detail {
    type enumeration {
      enum rsrc-summary-no-detail {
        value 0;
        description "show no detail";
      }
      enum rsrc-summary-detail {
        value 131072;
        description "show detail";
      }
    }
    description "Resource summary info detail";
  }
  typedef Fib-object-attribute {
    type enumeration {
      enum none {
        value 0;
        description "Invalid type of attribute";
      }
      enum error {
        value 1;
        description "Error type of attribute";
      }
      enum out-of-resource {
        value 2;
        description "Out-of-Resource type of attribute";
      }
      enum adjacency {
        value 3;
        description "Adjacency type of attribute";
      }
    }
    description "Fib object attribute";
  }
  typedef Fibafi-proto {
    type enumeration {
      enum ipv4 {
        value 0;
        description "ipv4 protocol";
      }
      enum ipv4-mpls {
        value 1;
        description "ipv4 mpls protocol";
      }
      enum ipv6 {
        value 2;
        description "ipv6 protocol";
      }
      enum ipv6-mpls {
        value 3;
        description "ipv6 mpls protocol";
      }
    }
    description "Fibafi proto";
  }
  typedef Fib-label {
    type uint32 {
      range "16..1048575";
    }
    description "Fib label";
  }
  typedef Fibllc-entry {
    type enumeration {
      enum xc {
        value 1;
        description "LabelXconnect";
      }
      enum pfx {
        value 2;
        description "IPPrefix";
      }
    }
    description "Fibllc entry";
  }
  typedef Fibnh-info-repl {
    type enumeration {
      enum fib-nh-repl-none {
        value 0;
        description "None Replicated NHINFO";
      }
      enum fib-nh-repl-rsvpte {
        value 1;
        description "Replicated NHINFO for TE Accounting";
      }
      enum fib-nh-repl-sr-mpls {
        value 2;
        description "Replicated NHINFO for SR MPLS Accounting";
      }
      enum fib-nh-repl-bm {
        value 3;
        description "Replicated NHINFO for Bundle member";
      }
    }
    description "Fibnh info repl";
  }
  typedef Fibfrr {
    type enumeration {
      enum fib-te-frr-node {
        value 0;
        description "TE FRR";
      }
      enum fib-te-frr-intf {
        value 1;
        description "TE Interface FRR";
      }
      enum fib-te-frr-protected-nh {
        value 2;
        description "TE Protected FRR";
      }
      enum fib-te-frr-backup-nh {
        value 3;
        description "TE Backup FRR";
      }
      enum fib-per-link-frr-protected-nh {
        value 4;
        description "Per Link Protected FRR";
      }
      enum fib-per-link-frr-backup-nh {
        value 5;
        description "Per Link Backup FRR";
      }
      enum fib-prefix-frr-protected-nh {
        value 6;
        description "Per Prefix Protected FRR";
      }
      enum fib-prefix-frr-backup-nh {
        value 7;
        description "Per Prefix Backup FRR";
      }
      enum fib-pic-frr-protected-nh {
        value 8;
        description "BGP PIC Protected FRR";
      }
      enum fib-pic-frr-backup-nh {
        value 9;
        description "BGP PIC Backup FRR";
      }
    }
    description "Fibfrr";
  }
  typedef Hw-ingress-info {
    type enumeration {
      enum hw-ingress-flg-off {
        value 0;
        description "No Hardware Ingress option";
      }
      enum hw-ingress-flg-on {
        value 32768;
        description "Hardware Ingress";
      }
    }
    description "Hw ingress info";
  }
  typedef Fib-link {
    type enumeration {
      enum link-ipv4 {
        value 0;
        description "IPv4 link protocol";
      }
      enum link-ipv6 {
        value 1;
        description "IPv6 link protocol";
      }
      enum link-mpls {
        value 2;
        description "MPLS link protocol";
      }
    }
    description "Fib link";
  }
  typedef Hw-egress-info {
    type enumeration {
      enum hw-egress-flg-off {
        value 0;
        description "No Hardware Egress option";
      }
      enum hw-egress-flg-on {
        value 16384;
        description "Hardware Egress";
      }
    }
    description "Hw egress info";
  }
  typedef Exact-route-ip-protocol {
    type enumeration {
      enum ip-proto-icmp {
        value 1;
        description "icmp";
      }
      enum ip-proto-ggp {
        value 3;
        description "ggp";
      }
      enum ip-proto-ipinip {
        value 4;
        description "ip in ip";
      }
      enum ip-proto-tcp {
        value 6;
        description "tcp";
      }
      enum ip-proto-egp {
        value 8;
        description "egp";
      }
      enum ip-proto-i-grp {
        value 9;
        description "igrp";
      }
      enum ip-proto-pup {
        value 12;
        description "pup";
      }
      enum ip-proto-udp {
        value 17;
        description "udp";
      }
      enum ip-proto-idp {
        value 22;
        description "idp";
      }
      enum ip-proto-tp {
        value 29;
        description "tp";
      }
      enum ip-proto-rsvp {
        value 46;
        description "rsvp";
      }
      enum ip-proto-gre {
        value 47;
        description "gre";
      }
      enum ip-proto-esp {
        value 50;
        description "esp";
      }
      enum ip-proto-ahp {
        value 51;
        description "ahp";
      }
      enum ip-proto-eon {
        value 80;
        description "eon";
      }
      enum ipproto_eigrp: {
        value 88;
        description "eigrp";
      }
      enum ip-proto-ospf {
        value 89;
        description "ospf";
      }
      enum ip-proto-nosip {
        value 94;
        description "no sip";
      }
      enum ip-proto-encap {
        value 98;
        description "encap";
      }
      enum ip-proto-pim {
        value 103;
        description "pim";
      }
      enum ip-proto-pcp {
        value 108;
        description "pcp";
      }
      enum ip-proto-l2tpv3 {
        value 115;
        description "l2tpv3";
      }
      enum ip-proto-uti {
        value 120;
        description "uti";
      }
      enum ip-proto-sctp {
        value 123;
        description "sctp";
      }
      enum ip-proto-raw {
        value 255;
        description "raw";
      }
    }
    description "Exact route ip protocol";
  }
  typedef Fibnh-remote {
    type enumeration {
      enum fib-nh-rx {
        value 1;
        description "NHINFO Remote Type";
      }
    }
    description "Fibnh remote";
  }
  typedef Mpls-label {
    type uint32 {
      range "16..1048575";
    }
    description "Mpls label";
  }
  typedef Mplseos {
    type enumeration {
      enum eos0 {
        value 0;
        description "EOS Disable";
      }
      enum eos1 {
        value 1;
        description "EOS Enable";
      }
    }
    description "Mplseos";
  }
  typedef Fib-afi {
    type enumeration {
      enum ipv4 {
        value 0;
        description "ipv4 family";
      }
      enum ipv6 {
        value 1;
        description "ipv6 family";
      }
      enum mpls {
        value 2;
        description "MPLS family";
      }
    }
    description "Fib afi";
  }
  typedef Prefix-len-range {
    type uint32 {
      range "0..128";
    }
    description "Prefix len range";
  }
  typedef Aft-object {
    type enumeration {
      enum fib-aft-invalid {
        value 0;
        description "Invalid";
      }
      enum fib-aft-next-hop {
        value 1;
        description "nh";
      }
      enum fib-aft-next-hop-group {
        value 2;
        description "nhg";
      }
      enum fib-aft-max {
        value 5;
        description "max";
      }
    }
    description "Aft object";
  }
  typedef Fibnh-local {
    type enumeration {
      enum fib-nh-tx {
        value 0;
        description "NHINFO Local Type";
      }
      enum fib-nh-special {
        value 2;
        description "NHINFO Special Type";
      }
    }
    description "Fibnh local";
  }
  typedef Fibevni-key {
    type enumeration {
      enum rtep-id-key {
        value 0;
        description "RTEP ID Key";
      }
      enum bgp-key {
        value 1;
        description "BGP Key";
      }
      enum tblid-vni-key {
        value 2;
        description "TBLID VNI Key";
      }
    }
    description "Fibevni key";
  }
  typedef Generic-index {
    type uint32 {
      range "0..4294967295";
    }
    description "Generic index";
  }

  grouping NH-INFO-SPECIAL-NULL-HARDWARE-EGRESS {
    description
      "Common node of nh-info-special-hardware-egress,
      nh-info-special-mpls-hardware-egress";

    container nh-info-special-null-hardware-egress {
      description
        "hardware egress info for special-null NHInfo
        entry";
      uses FIB-SH-NHINFO;
    }
  }

  grouping NH-INFO-SPECIAL-PUNT-DETAIL-HARDWARE-INGRESS {
    description
      "Common node of
      nh-info-special-detail-hardware-ingress,
      nh-info-special-mpls-detail-hardware-ingress";

    container nh-info-special-punt-detail-hardware-ingress {
      description
        "Detail hardware ingress info for special-punt
        NHInfo entry";
      uses FIB-SH-NHINFO;
    }
  }

  grouping NH-INFO-SPECIAL-DROP-HARDWARE-EGRESS {
    description
      "Common node of nh-info-special-hardware-egress,
      nh-info-special-mpls-hardware-egress";

    container nh-info-special-drop-hardware-egress {
      description
        "hardware egress info for special-drop NHInfo
        entry";
      uses FIB-SH-NHINFO;
    }
  }

  grouping NH-INFO-SPECIAL-PUNT-DETAIL {
    description
      "Common node of nh-info-special-detail,
      nh-info-special-mpls-detail";

    container nh-info-special-punt-detail {
      description "Detail special NHInfo punt entry";
      uses FIB-SH-NHINFO;
    }
  }

  grouping NH-INFO-SPECIAL-DISCARD-DETAIL {
    description
      "Common node of nh-info-special-detail,
      nh-info-special-mpls-detail";

    container nh-info-special-discard-detail {
      description "Detail special NHInfo discard entry";
      uses FIB-SH-NHINFO;
    }
  }

  grouping NH-INFO-SPECIAL-DROP-DETAIL {
    description
      "Common node of nh-info-special-detail,
      nh-info-special-mpls-detail";

    container nh-info-special-drop-detail {
      description "Detail special NHInfo punt entry";
      uses FIB-SH-NHINFO;
    }
  }

  grouping OBJECT-TABLE {
    description "Common node of summary-protocol, total";

    container objects {
      description "Object Table";

      list object {
        key "object-id";
        description "Object Table entry";
        leaf object-id {
          type uint32;
          description "Object ID";
        }
        uses FIB-BAG-SUM-OBJ;
      }
    }
  }

  grouping NH-INFO-SPECIAL-DISCARD-HARDWARE-EGRESS {
    description
      "Common node of nh-info-special-hardware-egress,
      nh-info-special-mpls-hardware-egress";

    container nh-info-special-discard-hardware-egress {
      description
        "hardware egress info for special-discard NHInfo
        entry";
      uses FIB-SH-NHINFO;
    }
  }

  grouping NH-INFO-SPECIAL-DROP-HARDWARE-INGRESS {
    description
      "Common node of nh-info-special-hardware-egress,
      nh-info-special-mpls-hardware-egressCommon node
      of nh-info-special-hardware-ingress,
      nh-info-special-mpls-hardware-ingress";

    container nh-info-special-drop-hardware-ingress {
      description
        "hardware ingress info for special-drop NHInfo
        entry";
      uses FIB-SH-NHINFO;
    }
  }

  grouping NH-INFO-SPECIAL-DROP-BRIEF {
    description
      "Common node of nh-info-special-brief,
      nh-info-special-mpls-brief";

    container nh-info-special-drop-brief {
      description "Brief special NHInfo drop entry";
      uses FIB-SH-NHINFO;
    }
  }

  grouping NH-INFO-SPECIAL-DISCARD-BRIEF {
    description
      "Common node of nh-info-special-brief,
      nh-info-special-mpls-brief";

    container nh-info-special-discard-brief {
      description "Brief special NHInfo discard entry";
      uses FIB-SH-NHINFO;
    }
  }

  grouping ERRORS-OBJECT-TABLE {
    description "Common node of errors, errors-protocol";

    container objects {
      description "Object Table for Errors";

      list object {
        key "object-id";
        description "Object Table for Errors";
        leaf object-id {
          type uint32;
          description "Object ID";
        }
        uses FIB-BAG-ERROR-OBJ;
      }
    }
  }

  grouping NH-INFO-SPECIAL-PUNT-BRIEF {
    description
      "Common node of nh-info-special-brief,
      nh-info-special-mpls-brief";

    container nh-info-special-punt-brief {
      description "Brief special NHInfo punt entry";
      uses FIB-SH-NHINFO;
    }
  }

  grouping NH-INFO-SPECIAL-DROP-DETAIL-HARDWARE-EGRESS {
    description
      "Common node of
      nh-info-special-detail-hardware-egress,
      nh-info-special-mpls-detail-hardware-egress";

    container nh-info-special-drop-detail-hardware-egress {
      description
        "Detail hardware egress info for special-drop
        NHInfo entry";
      uses FIB-SH-NHINFO;
    }
  }

  grouping ERROR {
    description "Common node of ipv4, ipv6";

    container error {
      description "Error data";

      container state {
        description "Error data";
        uses FIB-OC-AFT-ERROR-STATE;
      }
    }
  }

  grouping INFORMATION {
    description "Common node of vrf, forwarding";

    list information {
      description "MPLS forwarding information";
      leaf label-value {
        type Mpls-label;
        description "Local label value";
      }
      leaf eos {
        type Mplseos;
        description "End of stack flag";
      }
      uses MPLS-SH-LEAF;
    }
  }

  grouping NH-INFO-SPECIAL-DISCARD-HARDWARE-INGRESS {
    description
      "Common node of nh-info-special-hardware-ingress,
      nh-info-special-mpls-hardware-ingress";

    container nh-info-special-discard-hardware-ingress {
      description
        "hardware ingress info for special-discard NHInfo
        entry";
      uses FIB-SH-NHINFO;
    }
  }

  grouping NH-INFO-SPECIAL-NULL-DETAIL-HARDWARE-INGRESS {
    description
      "Common node of
      nh-info-special-detail-hardware-ingress,
      nh-info-special-mpls-detail-hardware-ingress";

    container nh-info-special-null-detail-hardware-ingress {
      description
        "Detail hardware ingress info for special-null
        NHInfo entry";
      uses FIB-SH-NHINFO;
    }
  }

  grouping NH-INFO-SPECIAL-NULL-HARDWARE-INGRESS {
    description
      "Common node of nh-info-special-hardware-ingress,
      nh-info-special-mpls-hardware-ingress";

    container nh-info-special-null-hardware-ingress {
      description
        "hardware ingress info for special-null NHInfo
        entry";
      uses FIB-SH-NHINFO;
    }
  }

  grouping NH-INFO-SPECIAL-DISCARD-DETAIL-HARDWARE-EGRESS {
    description
      "Common node of
      nh-info-special-detail-hardware-egress,
      nh-info-special-mpls-detail-hardware-egress";

    container nh-info-special-discard-detail-hardware-egress {
      description
        "Detail hardware egress info for special-discard
        NHInfo entry";
      uses FIB-SH-NHINFO;
    }
  }

  grouping NH-INFO-SPECIAL-NULL-BRIEF {
    description
      "Common node of nh-info-special-brief,
      nh-info-special-mpls-brief";

    container nh-info-special-null-brief {
      description "Brief special NHInfo null entry";
      uses FIB-SH-NHINFO;
    }
  }

  grouping NH-INFO-SPECIAL-PUNT-HARDWARE-INGRESS {
    description
      "Common node of nh-info-special-hardware-ingress,
      nh-info-special-mpls-hardware-ingress";

    container nh-info-special-punt-hardware-ingress {
      description
        "hardware ingress info for special-punt NHInfo
        entry";
      uses FIB-SH-NHINFO;
    }
  }

  grouping OOR {
    description "Common node of ipv4, ipv6";

    container oor {
      description "OOR data";

      container state {
        description "OOR data";
        uses FIB-OC-AFT-OOR-STATE;
      }
    }
  }

  grouping NH-INFO-SPECIAL-PUNT-HARDWARE-EGRESS {
    description
      "Common node of nh-info-special-hardware-egress,
      nh-info-special-mpls-hardware-egress";

    container nh-info-special-punt-hardware-egress {
      description
        "hardware egress info for special-punt NHInfo
        entry";
      uses FIB-SH-NHINFO;
    }
  }

  grouping NH-INFO-SPECIAL-DISCARD-DETAIL-HARDWARE-INGRESS {
    description
      "Common node of
      nh-info-special-detail-hardware-ingress,
      nh-info-special-mpls-detail-hardware-ingress";

    container nh-info-special-discard-detail-hardware-ingress {
      description
        "Detail hardware ingress info for special-discard
        NHInfo entry";
      uses FIB-SH-NHINFO;
    }
  }

  grouping NH-INFO-SPECIAL-NULL-DETAIL {
    description
      "Common node of nh-info-special-detail,
      nh-info-special-mpls-detail";

    container nh-info-special-null-detail {
      description "Detail special NHInfo null entry";
      uses FIB-SH-NHINFO;
    }
  }

  grouping NH-INFO-SPECIAL-NULL-DETAIL-HARDWARE-EGRESS {
    description
      "Common node of
      nh-info-special-detail-hardware-egress,
      nh-info-special-mpls-detail-hardware-egress";

    container nh-info-special-null-detail-hardware-egress {
      description
        "Detail hardware egress info for special-null
        NHInfo entry";
      uses FIB-SH-NHINFO;
    }
  }

  grouping NH-INFO-SPECIAL-PUNT-DETAIL-HARDWARE-EGRESS {
    description
      "Common node of
      nh-info-special-detail-hardware-egress,
      nh-info-special-mpls-detail-hardware-egress";

    container nh-info-special-punt-detail-hardware-egress {
      description
        "Detail hardware egress info for special-punt
        NHInfo entry";
      uses FIB-SH-NHINFO;
    }
  }

  grouping NH-INFO-SPECIAL-DROP-DETAIL-HARDWARE-INGRESS {
    description
      "Common node of
      nh-info-special-detail-hardware-ingress,
      nh-info-special-mpls-detail-hardware-ingress";

    container nh-info-special-drop-detail-hardware-ingress {
      description
        "Detail hardware ingress info for special-drop
        NHInfo entry";
      uses FIB-SH-NHINFO;
    }
  }

  container fib-statistics {
    config false;
    description "cef interface drops operational data";

    container nodes {
      description "List of nodes";

      list node {
        key "node-name";
        description "Specific node operational data";

        container drops {
          description "Specific node drops";
          uses FIB-STATISTICS-BAG-DROPS;
        }

        container drops-mpls {
          description "Specific node drops";
          uses FIB-STATISTICS-BAG-DROPS;
        }

        container exceptions-mpls {
          description "Specific node exceptions";
          uses FIB-STATISTICS-BAG-EXCEPTIONS;
        }

        container exceptions-v4 {
          description "Specific node exceptions";
          uses FIB-STATISTICS-BAG-EXCEPTIONS;
        }

        container drops-v6 {
          description "Specific node drops";
          uses FIB-STATISTICS-BAG-DROPS;
        }

        container exceptions-v6 {
          description "Specific node exceptions";
          uses FIB-STATISTICS-BAG-EXCEPTIONS;
        }
        leaf node-name {
          type xr:Node-id;
          description "Node name";
        }
      }
    }
  }

  container fib {
    config false;
    description "FIB operational data";

    container nodes {
      description "Table of nodes";

      list node {
        key "node-name";
        description "Operational data for a specific Node";

        container global {
          description "FIB Global info";

          container fib-cofo {
            description "Collapsed Forwarding";

            container fib-cofo-idb {
              description "Collapsed Forwarding IDB Table";

              container fib-cofo-idb-table-entries {
                description
                  "Collapsed Forwarding Idb Table Entries";

                list fib-cofo-idb-table-entry {
                  description
                    "Collapsed Forwarding Idb Table Entries";
                  leaf sdr-id {
                    type uint32;
                    description "SDR ID value";
                  }
                  leaf if-index {
                    type uint32;
                    description "Interface Index";
                  }
                  uses FIB-SH-COFO-IDB-TBL-ENTRY-INFO;
                }
              }
            }

            container fib-cofo-table-id {
              description "Collapsed Forwarding Table Id Table";

              container fib-cofo-table-id-entries {
                description "Collapsed Forwarding Table Id Entries";

                list fib-cofo-table-id-entry {
                  description
                    "Collapsed Forwarding Idb Table Entries";
                  leaf sdr-id {
                    type uint32;
                    description "SDR ID value";
                  }
                  leaf protocol {
                    type Fib-protocol;
                    description "Protocol";
                  }
                  leaf rd {
                    type xr:Cisco-ios-xr-string;
                    description "Route Distinguisher";
                  }
                  leaf table-id-key {
                    type uint32;
                    description "Table Id";
                  }
                  uses FIB-SH-COFO-TBL-ID-ENTRY-INFO;
                }
              }

              container fib-cofo-table-id-summary {
                description "Collapsed Forwarding Table Id Entries";
                uses FIB-SH-COFO-TBL-ID-DB-SUM;
              }
            }
          }

          container summary {
            description "Global Summary";

            container total {
              description "Display total";

              container counters {
                description
                  "Display total counters and common info";
                uses FIB-GLOBAL-SUMMARY-TOTAL;
              }
              uses OBJECT-TABLE;
            }

            container summary-protocols {
              description "Summary Protocol Table";

              list summary-protocol {
                key "protocol-name";
                description "Summary Protocol Table entry";

                container proto-counters {
                  description "Display protocol counters";
                  uses FIB-GLOBAL-SUMMARY-PROTO;
                }
                leaf protocol-name {
                  type Fibafi-proto;
                  description "Protocol Name";
                }
                uses OBJECT-TABLE;
              }
            }
          }

          container errors {
            description "Errors";

            container errors-protocols {
              description "Error Protocol";

              list errors-protocol {
                key "protocol-name";
                description "Errors Protocol Table entry";
                leaf protocol-name {
                  type Fibafi-proto;
                  description "Protocol Name";
                }
                uses ERRORS-OBJECT-TABLE;
              }
            }

            container errors-total {
              description "Aggregate object Table for Errors";
              uses FIB-BAG-ERROR-AGGR-OBJ;
            }
            uses ERRORS-OBJECT-TABLE;
          }

          container encap-id-database {
            description "Encap ID database";

            container summary {
              description "Encap ID DB summary";
              uses FIB-ENCAP-ID-SUMMARY;
            }

            container encap-id-incompletes {
              description "Incomplete Encap ID entry table";

              list encap-id-incomplete {
                key "object-id";
                description "Incomplete Encap ID entry";
                leaf object-id {
                  type xr:Cisco-ios-xr-string;
                  description "Object ID";
                }
                uses FIB-OBJECT-ENCAP-ID-INFO;
              }
            }

            container encap-ids {
              description "Encap ID table";

              list encap-id {
                key "encap-id-key";
                description "Encap ID entry";
                leaf encap-id-key {
                  type xr:Cisco-ios-xr-string;
                  description "Encap ID";
                }
                uses FIB-OBJECT-ENCAP-ID-INFO;
              }
            }
          }

          container object-history {
            description "FIB Global Object History";

            container obj-history-protos {
              description "Proto Table";

              list obj-history-proto {
                key "protocol-name";
                description "Protocol Table entry";
                leaf protocol-name {
                  type Fibafi-proto;
                  description "Protocol Name";
                }
                uses FIB-GLOBAL-SUMMARY-OBJ-HISTORY-PROTO;
              }
            }
          }

          container gribi-database {
            description "GRIBI table database";

            container gribi-table-summary {
              description "GRIBI table summary";
              uses FIB-COMMON-GRIBI-TBL-STATS;
            }

            container gribi-hardware-ingresses {
              description "GRIBI table";

              list gribi-hardware-ingress {
                description "GRIBI table entry";
                leaf vrf-id-key {
                  type xr:Hex-integer;
                  description "VRF ID";
                }
                leaf fib-object-id {
                  type xr:Cisco-ios-xr-string;
                  description "FIB object ID";
                }
                leaf aft-object-typ {
                  type Aft-object;
                  description "AFT object type";
                }
                uses FIB-GLOBAL-GRIBI-ENTRY;
              }
            }

            container gribi-hardware-egresses {
              description "GRIBI table";

              list gribi-hardware-egress {
                description "GRIBI table entry";
                leaf vrf-id-key {
                  type xr:Hex-integer;
                  description "VRF ID";
                }
                leaf fib-object-id {
                  type xr:Cisco-ios-xr-string;
                  description "FIB object ID";
                }
                leaf aft-object-typ {
                  type Aft-object;
                  description "AFT object type";
                }
                uses FIB-GLOBAL-GRIBI-ENTRY;
              }
            }

            container gribis {
              description "GRIBI table";

              list gribi {
                description "GRIBI table entry";
                leaf vrf-id-key {
                  type xr:Hex-integer;
                  description "VRF ID";
                }
                leaf fib-object-id {
                  type xr:Cisco-ios-xr-string;
                  description "FIB object ID";
                }
                leaf aft-object-typ {
                  type Aft-object;
                  description "AFT object type";
                }
                uses FIB-GLOBAL-GRIBI-ENTRY;
              }
            }
          }

          container tunnel-database {
            description "TunnelTable database";

            container vxlan-tep-tunnels {
              description "VXLAN TEP tunnel database";

              list vxlan-tep-tunnel {
                description "VXLAN TEP table entry";
                leaf evni-key-type {
                  type Fibevni-key;
                  description "VXLAN EVNI Table key type";
                }
                leaf evni-tunnel-type {
                  type Ipvpn-tunnel;
                  description "Tunnel type";
                }
                leaf evni-vrf-protocol {
                  type Fib-protocol;
                  description "FIB Protocol Type";
                }
                leaf evni-vrf-name {
                  type string;
                  description "VXLAN EVNI Table vrf name";
                }
                leaf evni-vni-id {
                  type uint32;
                  description "VNI ID";
                }
                leaf evni-underlay-table-id {
                  type xr:Hex-integer;
                  description "Underlay Table Id";
                }
                leaf evni-destination-address-protocol {
                  type Fib-protocol;
                  description "FIB Protocol Type";
                }
                leaf evni-destination-address {
                  type inet:ip-address-no-zone;
                  description "Destination address";
                }
                leaf evni-mac-address {
                  type yang:mac-address;
                  description "MAC Address";
                }
                leaf evni-rtep-id {
                  type xr:Cisco-ios-xr-string;
                  description "RTEP ID";
                }
                leaf rtep-tunnel-type {
                  type Ipvpn-tunnel;
                  description "Tunnel type";
                }
                leaf rtep-destination-address-protocol {
                  type Fib-protocol;
                  description "Destination address proto";
                }
                leaf rtep-destination-address {
                  type inet:ip-address-no-zone;
                  description "Destination address";
                }
                leaf rtep-underlay-table-id {
                  type xr:Hex-integer;
                  description "Underlay Table Id";
                }
                leaf rtep-vxlan-overlay-table-id {
                  type xr:Hex-integer;
                  description "VxLAN Overlay Table Id";
                }
                leaf rtep-vxlan-evni-id {
                  type uint32;
                  description "VxLAN EVNI ID";
                }
                leaf rtep-is-default {
                  type boolean;
                  description "Is Default LTEP NVE";
                }
                leaf rtep-table-id {
                  type xr:Hex-integer;
                  description "LTEP_NVE Table ID";
                }
                leaf rtep-nve-interface-id {
                  type uint32;
                  description "LTEP_NVE NVE ID";
                }
                leaf rtep-vni-id {
                  type uint32;
                  description "LTEP_NVE VNI ID";
                }
                uses FIB-VXLAN-TEP-ENTRY;
              }
            }

            container vxlan-tep-tunnel-hardware-ingresses {
              description "VXLAN TEP Tunnel database, HW Ingress";

              list vxlan-tep-tunnel-hardware-ingress {
                description "VXLAN TEP table entry, HW Ingress";
                leaf evni-key-type {
                  type Fibevni-key;
                  description "VXLAN EVNI Table key type";
                }
                leaf evni-tunnel-type {
                  type Ipvpn-tunnel;
                  description "Tunnel type";
                }
                leaf evni-vrf-protocol {
                  type Fib-protocol;
                  description "FIB Protocol Type";
                }
                leaf evni-vrf-name {
                  type string;
                  description "VXLAN EVNI Table vrf name";
                }
                leaf evni-vni-id {
                  type uint32;
                  description "VNI ID";
                }
                leaf evni-underlay-table-id {
                  type xr:Hex-integer;
                  description "Underlay Table Id";
                }
                leaf evni-destination-address-protocol {
                  type Fib-protocol;
                  description "FIB Protocol Type";
                }
                leaf evni-destination-address {
                  type inet:ip-address-no-zone;
                  description "Destination address";
                }
                leaf evni-mac-address {
                  type yang:mac-address;
                  description "MAC Address";
                }
                leaf evni-rtep-id {
                  type xr:Cisco-ios-xr-string;
                  description "RTEP ID";
                }
                leaf rtep-tunnel-type {
                  type Ipvpn-tunnel;
                  description "Tunnel type";
                }
                leaf rtep-destination-address-protocol {
                  type Fib-protocol;
                  description "Destination address proto";
                }
                leaf rtep-destination-address {
                  type inet:ip-address-no-zone;
                  description "Destination address";
                }
                leaf rtep-underlay-table-id {
                  type xr:Hex-integer;
                  description "Underlay Table Id";
                }
                leaf rtep-vxlan-overlay-table-id {
                  type xr:Hex-integer;
                  description "VxLAN Overlay Table Id";
                }
                leaf rtep-vxlan-evni-id {
                  type uint32;
                  description "VxLAN EVNI ID";
                }
                leaf rtep-is-default {
                  type boolean;
                  description "Is Default LTEP NVE";
                }
                leaf rtep-table-id {
                  type xr:Hex-integer;
                  description "LTEP_NVE Table ID";
                }
                leaf rtep-nve-interface-id {
                  type uint32;
                  description "LTEP_NVE NVE ID";
                }
                leaf rtep-vni-id {
                  type uint32;
                  description "LTEP_NVE VNI ID";
                }
                uses FIB-VXLAN-TEP-ENTRY;
              }
            }

            container evni-tunnel-internals {
              description "EVNI internal tunnel database";

              list evni-tunnel-internal {
                description "EVNI internal table entry";
                leaf vni-into-type-key {
                  type Fibevni-key;
                  description "VXLAN EVNI Table key type";
                }
                leaf tunnel-type-key {
                  type Ipvpn-tunnel;
                  description "Tunnel type";
                }
                leaf vrf-protocol {
                  type Fib-protocol;
                  description "FIB Protocol Type";
                }
                leaf vrf-name {
                  type string;
                  description "VXLAN EVNI Table vrf name";
                }
                leaf vni-id-key {
                  type uint32;
                  description "VNI ID";
                }
                leaf underlay-table-id-key {
                  type xr:Hex-integer;
                  description "Underlay Table Id";
                }
                leaf dest-address-protocol {
                  type Fib-protocol;
                  description "FIB Protocol Type";
                }
                leaf destination-address-key {
                  type inet:ip-address-no-zone;
                  description "Destination address";
                }
                leaf mac-address {
                  type yang:mac-address;
                  description "MAC Address";
                }
                leaf rtep-id-key {
                  type xr:Cisco-ios-xr-string;
                  description "RTEP ID";
                }
                uses FIB-VNI-INFO-ENTRY;
              }
            }

            container ltep-nve-tunnel-hardware-egresses {
              description "Ltep NVE Tunnel table";

              list ltep-nve-tunnel-hardware-egress {
                description "LTEP NVE table entry";
                leaf table-id-key {
                  type xr:Hex-integer;
                  description "Table ID";
                }
                leaf nve-interface-id-key {
                  type uint32;
                  description "NVE interface ID";
                }
                leaf vni-id-key {
                  type uint32;
                  description "VNI ID";
                }
                leaf dest-address-protocol {
                  type Fib-protocol;
                  description "FIB Protocol Type";
                }
                leaf destination-address-key {
                  type inet:ip-address-no-zone;
                  description "Destination address";
                }
                leaf underlay-table-id-key {
                  type xr:Hex-integer;
                  description "Table ID";
                }
                uses FIB-GLOBAL-LTEP-NVE-ENTRY;
              }
            }

            container evni-tunnel-hardware-ingresses {
              description
                "EVNI Tunnel database for BGP based key, HW
                Ingress";

              list evni-tunnel-hardware-ingress {
                description "EVNI table entry, HW Ingress";
                leaf vni-into-type-key {
                  type Fibevni-key;
                  description "VXLAN EVNI Table key type";
                }
                leaf tunnel-type-key {
                  type Ipvpn-tunnel;
                  description "Tunnel type";
                }
                leaf vrf-protocol {
                  type Fib-protocol;
                  description "FIB VRF Protocol Type";
                }
                leaf vrf-name {
                  type string;
                  description "VXLAN EVNI Table vrf name";
                }
                leaf vni-id-key {
                  type uint32;
                  description "VNI ID";
                }
                leaf underlay-table-id-key {
                  type xr:Hex-integer;
                  description "Underlay Table Id";
                }
                leaf dest-address-protocol {
                  type Fib-protocol;
                  description "FIB Protocol Type";
                }
                leaf destination-address-key {
                  type inet:ip-address-no-zone;
                  description "Destination address";
                }
                leaf mac-address {
                  type yang:mac-address;
                  description "MAC Address";
                }
                leaf rtep-id-key {
                  type xr:Cisco-ios-xr-string;
                  description "RTEP ID";
                }
                uses FIB-VNI-INFO-ENTRY;
              }
            }

            container evni-tunnel-hardware-egresses {
              description
                "EVNI Tunnel database for BGP based key, HW
                Egress";

              list evni-tunnel-hardware-egress {
                description "EVNI table entry, HW Ingress";
                leaf vni-into-type-key {
                  type Fibevni-key;
                  description "VXLAN EVNI Table key type";
                }
                leaf tunnel-type-key {
                  type Ipvpn-tunnel;
                  description "Tunnel type";
                }
                leaf vrf-protocol {
                  type Fib-protocol;
                  description "FIB VRF Protocol Type";
                }
                leaf vrf-name {
                  type string;
                  description "VXLAN EVNI Table vrf name";
                }
                leaf vni-id-key {
                  type uint32;
                  description "VNI ID";
                }
                leaf underlay-table-id-key {
                  type xr:Hex-integer;
                  description "Underlay Table Id";
                }
                leaf dest-address-protocol {
                  type Fib-protocol;
                  description "FIB Protocol Type";
                }
                leaf destination-address-key {
                  type inet:ip-address-no-zone;
                  description "Destination address";
                }
                leaf mac-address {
                  type yang:mac-address;
                  description "MAC Address";
                }
                leaf rtep-id-key {
                  type xr:Cisco-ios-xr-string;
                  description "RTEP ID";
                }
                uses FIB-VNI-INFO-ENTRY;
              }
            }

            container evni-tunnels {
              description "EVNI tunnel database";

              list evni-tunnel {
                description "EVNI table entry";
                leaf vni-into-type-key {
                  type Fibevni-key;
                  description "VXLAN EVNI Table key type";
                }
                leaf tunnel-type-key {
                  type Ipvpn-tunnel;
                  description "Tunnel type";
                }
                leaf vrf-protocol {
                  type Fib-protocol;
                  description "FIB VRF Protocol Type";
                }
                leaf vrf-name {
                  type string;
                  description "VXLAN EVNI Table vrf name";
                }
                leaf vni-id-key {
                  type uint32;
                  description "VNI ID";
                }
                leaf underlay-table-id-key {
                  type xr:Hex-integer;
                  description "Underlay Table Id";
                }
                leaf dest-address-protocol {
                  type Fib-protocol;
                  description "FIB Protocol Type";
                }
                leaf destination-address-key {
                  type inet:ip-address-no-zone;
                  description "Destination address";
                }
                leaf mac-address {
                  type yang:mac-address;
                  description "MAC Address";
                }
                leaf rtep-id-key {
                  type xr:Cisco-ios-xr-string;
                  description "RTEP ID";
                }
                uses FIB-VNI-INFO-ENTRY;
              }
            }

            container vxlan-tep-tunnel-internals {
              description "VXLAN TEP internal tunnel database";

              list vxlan-tep-tunnel-internal {
                description "VXLAN TEP internal table entry";
                leaf evni-key-type {
                  type Fibevni-key;
                  description "VXLAN EVNI Table key type";
                }
                leaf evni-tunnel-type {
                  type Ipvpn-tunnel;
                  description "Tunnel type";
                }
                leaf evni-vrf-protocol {
                  type Fib-protocol;
                  description "FIB Protocol Type";
                }
                leaf evni-vrf-name {
                  type string;
                  description "VXLAN EVNI Table vrf name";
                }
                leaf evni-vni-id {
                  type uint32;
                  description "VNI ID";
                }
                leaf evni-underlay-table-id {
                  type xr:Hex-integer;
                  description "Underlay Table Id";
                }
                leaf evni-destination-address-protocol {
                  type Fib-protocol;
                  description "FIB Protocol Type";
                }
                leaf evni-destination-address {
                  type inet:ip-address-no-zone;
                  description "Destination address";
                }
                leaf evni-mac-address {
                  type yang:mac-address;
                  description "MAC Address";
                }
                leaf evni-rtep-id {
                  type xr:Cisco-ios-xr-string;
                  description "RTEP ID";
                }
                leaf rtep-tunnel-type {
                  type Ipvpn-tunnel;
                  description "Tunnel type";
                }
                leaf rtep-destination-address-protocol {
                  type Fib-protocol;
                  description "Destination address proto";
                }
                leaf rtep-destination-address {
                  type inet:ip-address-no-zone;
                  description "Destination address";
                }
                leaf rtep-underlay-table-id {
                  type xr:Hex-integer;
                  description "Underlay Table Id";
                }
                leaf rtep-vxlan-overlay-table-id {
                  type xr:Hex-integer;
                  description "VxLAN Overlay Table Id";
                }
                leaf rtep-vxlan-evni-id {
                  type uint32;
                  description "VxLAN EVNI ID";
                }
                leaf rtep-is-default {
                  type boolean;
                  description "Is Default LTEP NVE";
                }
                leaf rtep-table-id {
                  type xr:Hex-integer;
                  description "LTEP_NVE Table ID";
                }
                leaf rtep-nve-interface-id {
                  type uint32;
                  description "LTEP_NVE NVE ID";
                }
                leaf rtep-vni-id {
                  type uint32;
                  description "LTEP_NVE VNI ID";
                }
                uses FIB-VXLAN-TEP-ENTRY;
              }
            }

            container ltep-nve-tunnel-table-summary {
              description "Ltep NVE Tunnel table summary";
              uses FIB-COMMON-LTEP-NVE-TBL-STATS;
            }

            container ltep-nve-tunnels {
              description "Ltep NVE Tunnel table";

              list ltep-nve-tunnel {
                description "LTEP NVE table entry";
                leaf table-id-key {
                  type xr:Hex-integer;
                  description "Table ID";
                }
                leaf nve-interface-id-key {
                  type uint32;
                  description "NVE interface ID";
                }
                leaf vni-id-key {
                  type uint32;
                  description "VNI ID";
                }
                leaf dest-address-protocol {
                  type Fib-protocol;
                  description "FIB Protocol Type";
                }
                leaf destination-address-key {
                  type inet:ip-address-no-zone;
                  description "Destination address";
                }
                leaf underlay-table-id-key {
                  type xr:Hex-integer;
                  description "Table ID";
                }
                uses FIB-GLOBAL-LTEP-NVE-ENTRY;
              }
            }

            container vxlan-tep-tunnel-hardware-egresses {
              description "VXLAN TEP Tunnel database, HW Egress";

              list vxlan-tep-tunnel-hardware-egress {
                description "VXLAN TEP table entry, HW Ingress";
                leaf evni-key-type {
                  type Fibevni-key;
                  description "VXLAN EVNI Table key type";
                }
                leaf evni-tunnel-type {
                  type Ipvpn-tunnel;
                  description "Tunnel type";
                }
                leaf evni-vrf-protocol {
                  type Fib-protocol;
                  description "FIB Protocol Type";
                }
                leaf evni-vrf-name {
                  type string;
                  description "VXLAN EVNI Table vrf name";
                }
                leaf evni-vni-id {
                  type uint32;
                  description "VNI ID";
                }
                leaf evni-underlay-table-id {
                  type xr:Hex-integer;
                  description "Underlay Table Id";
                }
                leaf evni-destination-address-protocol {
                  type Fib-protocol;
                  description "FIB Protocol Type";
                }
                leaf evni-destination-address {
                  type inet:ip-address-no-zone;
                  description "Destination address";
                }
                leaf evni-mac-address {
                  type yang:mac-address;
                  description "MAC Address";
                }
                leaf evni-rtep-id {
                  type xr:Cisco-ios-xr-string;
                  description "RTEP ID";
                }
                leaf rtep-tunnel-type {
                  type Ipvpn-tunnel;
                  description "Tunnel type";
                }
                leaf rtep-destination-address-protocol {
                  type Fib-protocol;
                  description "Destination address proto";
                }
                leaf rtep-destination-address {
                  type inet:ip-address-no-zone;
                  description "Destination address";
                }
                leaf rtep-underlay-table-id {
                  type xr:Hex-integer;
                  description "Underlay Table Id";
                }
                leaf rtep-vxlan-overlay-table-id {
                  type xr:Hex-integer;
                  description "VxLAN Overlay Table Id";
                }
                leaf rtep-vxlan-evni-id {
                  type uint32;
                  description "VxLAN EVNI ID";
                }
                leaf rtep-is-default {
                  type boolean;
                  description "Is Default LTEP NVE";
                }
                leaf rtep-table-id {
                  type xr:Hex-integer;
                  description "LTEP_NVE Table ID";
                }
                leaf rtep-nve-interface-id {
                  type uint32;
                  description "LTEP_NVE NVE ID";
                }
                leaf rtep-vni-id {
                  type uint32;
                  description "LTEP_NVE VNI ID";
                }
                uses FIB-VXLAN-TEP-ENTRY;
              }
            }

            container ltep-nve-tunnel-hardware-ingresses {
              description "Ltep NVE Tunnel table";

              list ltep-nve-tunnel-hardware-ingress {
                description "LTEP NVE table entry";
                leaf table-id-key {
                  type xr:Hex-integer;
                  description "Table ID";
                }
                leaf nve-interface-id-key {
                  type uint32;
                  description "NVE interface ID";
                }
                leaf vni-id-key {
                  type uint32;
                  description "VNI ID";
                }
                leaf dest-address-protocol {
                  type Fib-protocol;
                  description "FIB Protocol Type";
                }
                leaf destination-address-key {
                  type inet:ip-address-no-zone;
                  description "Destination address";
                }
                leaf underlay-table-id-key {
                  type xr:Hex-integer;
                  description "Table ID";
                }
                uses FIB-GLOBAL-LTEP-NVE-ENTRY;
              }
            }
          }

          container aggregation-db {
            description "Aggregation database";

            container aggregation-entries {
              description "Aggregation table";

              list aggregation-entry {
                description "Aggregation table entry";
                leaf protocol {
                  type Fib-protocol;
                  description "Protocol type";
                }
                leaf object-type {
                  type Fib-object;
                  description "Object Type";
                }
                leaf attribute-type {
                  type Fib-object-attribute;
                  description "Attribute Type";
                }
                leaf is-mpls {
                  type boolean;
                  description "Is MPLS flag?";
                }
                leaf adjacency-interface {
                  type xr:Interface-name;
                  description "Adjacency interface name";
                }
                leaf adjacency-next-hop {
                  type xr:Cisco-ios-xr-string;
                  description "Adjacency next hop address";
                }
                leaf adjacency-application-type {
                  type Fibnh-info-repl;
                  description "Adjacency application type";
                }
                leaf adjacency-type {
                  type Fib-adjacency;
                  description "Adjacency type";
                }
                uses FIB-GLOBAL-AGGREGATION-ENTRY;
              }
            }

            container aggregation-summary {
              description "Aggregation table summary";
              uses FIB-GLOBAL-AGGREGATION-SUMMARY;
            }
          }

          container global-policy-database {
            description "Global policy table database";

            container global-policy-internals {
              description "Global policy internal table";

              list global-policy-internal {
                description "Global policy internal table entry";
                leaf policy-name-key {
                  type xr:Cisco-ios-xr-string;
                  description "Policy name";
                }
                leaf policy-type {
                  type Fib-global-policy;
                  description "Policy type";
                }
                uses FIB-SH-POLICY-ENTRY;
              }
            }

            container global-policies {
              description "Global policy table";

              list global-policy {
                description "Global policy table entry";
                leaf policy-name-key {
                  type xr:Cisco-ios-xr-string;
                  description "Policy name";
                }
                leaf policy-type {
                  type Fib-global-policy;
                  description "Policy type";
                }
                uses FIB-SH-POLICY-ENTRY;
              }
            }
          }
        }

        container global-main {
          description "FIB Global info from the Main thread";

          container global-retry-db-summary {
            description "Retry DB Summary entry";
            uses FIB-RETRY-DB-SUMMARY;
          }

          container global-retry-db-entries {
            description "Details for retry db";

            list global-retry-db-entry {
              description
                "Details for retry_db corresponding to index";
              leaf index {
                type Generic-index;
                description "Index";
              }
              leaf frsc {
                type Generic-index;
                description "Frsc";
              }
              leaf queue-id {
                type Generic-index;
                description "Queue Id";
              }
              uses FIB-RETRY-DB-INFO;
            }
          }

          container clients {
            description "Client table";

            list client {
              key "client-id-key";
              description "FIB Client";
              leaf client-id-key {
                type uint32;
                description "Client ID";
              }
              uses FIB-GLOBAL-CLIENT;
            }
          }
        }

        container protocols {
          description "Protocol table";

          list protocol {
            key "protocol-name";
            description "Protocol table entry";

            container resource-oor {
              description "Resource out of resource information";
              uses FIB-SH-RSRC-AVAIL-OOR-STATE;
            }

            container issu-state {
              description "CEF ISSU State";
              uses FIB-ISSU-STATE;
            }

            container cef-tables {
              description "Details for cef tables db";

              list cef-table {
                description
                  "Details for cef_db corresponding to
                  table_id";
                leaf table-id-key {
                  type xr:Hex-integer;
                  description "Table Id";
                }
                leaf vrf-name {
                  type string;
                  description "VRF Name";
                }
                uses FIB-SH-SUM;
              }
            }

            container interfaces {
              description "Interface list data details";

              list interface {
                description "Details for interface list data";
                leaf protocol-id {
                  type Fib-protocol;
                  description "Protocol ID";
                }
                leaf interface-list-id-key {
                  type uint32 {
                    range "0..4294967295";
                  }
                  description "Interface List ID";
                }
                leaf interface-list-name-key {
                  type xr:Cisco-ios-xr-string;
                  description "Interface List Name";
                }
                uses FIB-GENERIC-INTF-LIST-DATA;
              }
            }

            container external-client-hardware-types {
              description "External client hardware type table";

              list external-client-hardware-type {
                key "hardware-table-type";
                description "External client hardware type";

                container external-clients {
                  description "All external clients";

                  list external-client {
                    description "External client";
                    leaf client-name {
                      type string;
                      description "Hardware Ingress";
                    }
                    leaf protocol-name {
                      type Fib-protocol;
                      description "Protocol Name ";
                    }
                    leaf interest-type {
                      type Fib-interest;
                      description "Interest Type";
                    }
                    leaf prefix {
                      type inet:ip-address-no-zone;
                      description "Destination IP address";
                    }
                    leaf prefix-length {
                      type xr:Ipv6-prefix-length;
                      description "IP FIB prefix length";
                    }
                    leaf tunnel-id {
                      type xr:Hex-integer;
                      description "LSMID or Tunnel ID";
                    }
                    leaf table-id {
                      type xr:Hex-integer;
                      description "Reg Table Id";
                    }
                    uses FIB-SH-TBL-EXT;
                  }
                }
                leaf hardware-table-type {
                  type Prefix-hardware-table;
                  description "Hw table type";
                }
              }
            }

            container resource-summary-infos {
              description "Resource information";

              list resource-summary-info {
                description "Summary info";
                leaf flag-detail {
                  type Resource-summary-info-detail;
                  description "detail or no detail";
                }
                leaf flag-hardware {
                  type Resource-summary-info-hardware;
                  description "hardware or no hardware";
                }
                leaf flag-direction {
                  type Resource-summary-info-dir;
                  description "egress/ingress";
                }
                uses FIB-SH-RSRC-AVAIL-STATE;
              }
            }

            container prefix-linklocal-table-types {
              description "Linklocal Table";

              list prefix-linklocal-table-type {
                key "hardware-table-type";
                description "IP FIB linklocal table type";

                container prefix-linklocal-containers {
                  description "Prefix Linklocal Table";

                  list prefix-linklocal-container {
                    description "Prefix linklocal table details";
                    leaf vrf-name {
                      type xr:Cisco-ios-xr-string;
                      description "VRF Name";
                    }
                    leaf table-id-key {
                      type uint32;
                      description "Table Id";
                    }

                    list prefix-linklocal-bag {
                      description "Prefix linklocal table entry";
                      leaf address {
                        type inet:ip-address-no-zone;
                        description "Destination Address";
                      }
                      leaf interface-name {
                        type xr:Interface-name;
                        description "Interface Name";
                      }
                      uses FIB-SH-TBL-FIB;
                    }
                  }
                }
                leaf hardware-table-type {
                  type Prefix-hardware-table;
                  description "Hw table type";
                }
              }
            }

            container fib-summaries {
              description "Summary for FIB tables";

              list fib-summary {
                description "Summary for the requested fib table";
                leaf vrf-name {
                  type string;
                  description "VRF Name";
                }
                leaf table-id-key {
                  type xr:Hex-integer;
                  description "FIB table id";
                }
                uses FIB-SH-SUM;
              }
            }

            container object-queues {
              description "Object queue details";

              list object-queue {
                key "object-queue-id";
                description
                  "Details for corresponding object queue id";
                leaf object-queue-id {
                  type uint32 {
                    range "0..255";
                  }
                  description "Object Queue ID";
                }
                uses FIB-OBJECT-QUEUE-INFO;
              }
            }

            container external-summary-all {
              description "Summary for all external clients";
              uses FIB-SH-TBL-EXT-SUM-ALL;
            }

            container frr-log {
              description "Table of Fast Reroute activation logs";

              container frr-interfaces {
                description "FRR Interface Table";

                list frr-interface {
                  key "frr-interface-name";
                  description "Specify FRR Interface Name";

                  container logs {
                    description "FRR log table";

                    list log {
                      key "log-index";
                      description
                        "Specify index into frr log table";
                      leaf log-index {
                        type uint32;
                        description "FRR Log Index";
                      }
                      uses FIB-SH-FRR-LOG;
                    }
                  }
                  leaf frr-interface-name {
                    type xr:Interface-name;
                    description "Interface Name";
                  }
                }
              }
            }

            container retry-db-entries {
              description "Details for retry db";

              list retry-db-entry {
                description
                  "Details for retry_db corresponding to index";
                leaf index {
                  type Generic-index;
                  description "Index";
                }
                leaf frsc {
                  type Generic-index;
                  description "Frsc";
                }
                leaf queue-id {
                  type Generic-index;
                  description "Queue Id";
                }
                uses FIB-RETRY-DB-INFO;
              }
            }

            container protocol-tunnel-database {
              description "Protocol tunnel database";

              container ltep-tunnel-table-summary {
                description "LTEP table summary";
                uses FIB-COMMON-LTEP-TBL-STATS;
              }

              container rtep-tunnel-table-summary {
                description "RTEP table summary";
                uses FIB-COMMON-RTEP-TBL-STATS;
              }

              container ltep-tunnel-hardware-egresses {
                description "Ltep Tunnel database, HW Egress";

                list ltep-tunnel-hardware-egress {
                  description "LTEP table entry, HW Egress";
                  leaf tunnel-type-key {
                    type Ipvpn-tunnel;
                    description "Tunnel type";
                  }
                  leaf source-address-key {
                    type inet:ip-address-no-zone;
                    description "Source address";
                  }
                  leaf underlay-table-id-key {
                    type xr:Hex-integer;
                    description "Underlay Table Id";
                  }
                  leaf vxlan-vni-id-key {
                    type uint32;
                    description "VxLAN VNI ID";
                  }
                  leaf destination-address-key {
                    type inet:ip-address-no-zone;
                    description "Destination address";
                  }
                  uses FIB-COMMON-LTEP-ENTRY;
                }
              }

              container rtep-tunnel-hardware-egresses {
                description "Rtep Tunnel database, HW Egress";

                list rtep-tunnel-hardware-egress {
                  description "RTEP table entry, HW Egress";
                  leaf tunnel-type-key {
                    type Ipvpn-tunnel;
                    description "Tunnel type";
                  }
                  leaf destination-address-proto {
                    type Fib-protocol;
                    description "Destination address proto";
                  }
                  leaf destination-address-key {
                    type inet:ip-address-no-zone;
                    description "Destination address";
                  }
                  leaf underlay-table-id-key {
                    type xr:Hex-integer;
                    description "Underlay Table Id";
                  }
                  leaf vxlan-overlay-table-id-key {
                    type xr:Hex-integer;
                    description "VxLAN Overlay Table Id";
                  }
                  leaf vxlan-e-vni-id-key {
                    type uint32;
                    description "VxLAN E-VNI ID";
                  }
                  leaf is-default {
                    type boolean;
                    description "Is Default LTEP NVE";
                  }
                  leaf table-id-key {
                    type xr:Hex-integer;
                    description "LTEP_NVE Table ID";
                  }
                  leaf nve-interface-id {
                    type uint32;
                    description "LTEP_NVE NVE ID";
                  }
                  leaf vni-id-key {
                    type uint32;
                    description "LTEP_NVE VNI ID";
                  }
                  uses FIB-COMMON-RTEP-ENTRY;
                }
              }

              container rtep-tunnel-internals {
                description "Rtep tunnel database";

                list rtep-tunnel-internal {
                  description "RTEP table entry";
                  leaf tunnel-type-key {
                    type Ipvpn-tunnel;
                    description "Tunnel type";
                  }
                  leaf destination-address-proto {
                    type Fib-protocol;
                    description "Destination address proto";
                  }
                  leaf destination-address-key {
                    type inet:ip-address-no-zone;
                    description "Destination address";
                  }
                  leaf underlay-table-id-key {
                    type xr:Hex-integer;
                    description "Underlay Table Id";
                  }
                  leaf vxlan-overlay-table-id-key {
                    type xr:Hex-integer;
                    description "VxLAN Overlay Table Id";
                  }
                  leaf vxlan-e-vni-id-key {
                    type uint32;
                    description "VxLAN E-VNI ID";
                  }
                  leaf is-default {
                    type boolean;
                    description "Is Default LTEP NVE";
                  }
                  leaf table-id-key {
                    type xr:Hex-integer;
                    description "LTEP_NVE Table ID";
                  }
                  leaf nve-interface-id {
                    type uint32;
                    description "LTEP_NVE NVE ID";
                  }
                  leaf vni-id-key {
                    type uint32;
                    description "LTEP_NVE VNI ID";
                  }
                  uses FIB-COMMON-RTEP-ENTRY;
                }
              }

              container rtep-tunnels {
                description "Rtep tunnel database";

                list rtep-tunnel {
                  description "RTEP table entry";
                  leaf tunnel-type-key {
                    type Ipvpn-tunnel;
                    description "Tunnel type";
                  }
                  leaf destination-address-proto {
                    type Fib-protocol;
                    description "Destination address proto";
                  }
                  leaf destination-address-key {
                    type inet:ip-address-no-zone;
                    description "Destination address";
                  }
                  leaf underlay-table-id-key {
                    type xr:Hex-integer;
                    description "Underlay Table Id";
                  }
                  leaf vxlan-overlay-table-id-key {
                    type xr:Hex-integer;
                    description "VxLAN Overlay Table Id";
                  }
                  leaf vxlan-e-vni-id-key {
                    type uint32;
                    description "VxLAN E-VNI ID";
                  }
                  leaf is-default {
                    type boolean;
                    description "Is Default LTEP NVE";
                  }
                  leaf table-id-key {
                    type xr:Hex-integer;
                    description "LTEP_NVE Table ID";
                  }
                  leaf nve-interface-id {
                    type uint32;
                    description "LTEP_NVE NVE ID";
                  }
                  leaf vni-id-key {
                    type uint32;
                    description "LTEP_NVE VNI ID";
                  }
                  uses FIB-COMMON-RTEP-ENTRY;
                }
              }

              container ltep-tunnel-hardware-ingresses {
                description "Ltep Tunnel database, HW Ingress";

                list ltep-tunnel-hardware-ingress {
                  description "LTEP table entry, HW Ingress";
                  leaf tunnel-type-key {
                    type Ipvpn-tunnel;
                    description "Tunnel type";
                  }
                  leaf source-address-key {
                    type inet:ip-address-no-zone;
                    description "Source address";
                  }
                  leaf underlay-table-id-key {
                    type xr:Hex-integer;
                    description "Underlay Table Id";
                  }
                  leaf vxlan-e-vni-id-key {
                    type uint32;
                    description "VxLAN VNI ID";
                  }
                  leaf destination-address-key {
                    type inet:ip-address-no-zone;
                    description "Destination address";
                  }
                  uses FIB-COMMON-LTEP-ENTRY;
                }
              }

              container ltep-tunnel-internals {
                description "Ltep tunnel database";

                list ltep-tunnel-internal {
                  description "LTEP table entry";
                  leaf tunnel-type-key {
                    type Ipvpn-tunnel;
                    description "Tunnel type";
                  }
                  leaf source-address-key {
                    type inet:ip-address-no-zone;
                    description "Source address";
                  }
                  leaf underlay-table-id-key {
                    type xr:Hex-integer;
                    description "Underlay Table Id";
                  }
                  leaf vxlan-vni-id-key {
                    type uint32;
                    description "VxLAN VNI ID";
                  }
                  leaf destination-address-key {
                    type inet:ip-address-no-zone;
                    description "Destination address";
                  }
                  uses FIB-COMMON-LTEP-ENTRY;
                }
              }

              container rtep-tunnel-hardware-ingresses {
                description "Rtep Tunnel database, HW Ingress";

                list rtep-tunnel-hardware-ingress {
                  description "RTEP table entry, HW Ingress";
                  leaf tunnel-type-key {
                    type Ipvpn-tunnel;
                    description "Tunnel type";
                  }
                  leaf destination-address-proto {
                    type Fib-protocol;
                    description "Destination address proto";
                  }
                  leaf destination-address-key {
                    type inet:ip-address-no-zone;
                    description "Destination address";
                  }
                  leaf underlay-table-id-key {
                    type xr:Hex-integer;
                    description "Underlay Table Id";
                  }
                  leaf vxlan-overlay-table-id-key {
                    type xr:Hex-integer;
                    description "VxLAN Overlay Table Id";
                  }
                  leaf vxlan-e-vni-id-key {
                    type uint32;
                    description "VxLAN E-VNI ID";
                  }
                  leaf is-default {
                    type boolean;
                    description "Is Default LTEP NVE";
                  }
                  leaf table-id-key {
                    type xr:Hex-integer;
                    description "LTEP_NVE Table ID";
                  }
                  leaf nve-interface-id {
                    type uint32;
                    description "LTEP_NVE NVE ID";
                  }
                  leaf vni-id-key {
                    type uint32;
                    description "LTEP_NVE VNI ID";
                  }
                  uses FIB-COMMON-RTEP-ENTRY;
                }
              }

              container ltep-tunnels {
                description "Ltep tunnel database";

                list ltep-tunnel {
                  description "LTEP table entry";
                  leaf tunnel-type-key {
                    type Ipvpn-tunnel;
                    description "Tunnel type";
                  }
                  leaf source-address-key {
                    type inet:ip-address-no-zone;
                    description "Source address";
                  }
                  leaf underlay-table-id-key {
                    type xr:Hex-integer;
                    description "Underlay Table Id";
                  }
                  leaf vxlan-vni-id-key {
                    type uint32;
                    description "VxLAN VNI ID";
                  }
                  leaf destination-address-key {
                    type inet:ip-address-no-zone;
                    description "Destination address";
                  }
                  uses FIB-COMMON-LTEP-ENTRY;
                }
              }
            }

            container vrfs {
              description "VRF table";

              list vrf {
                key "vrf-name";
                description "VRF table entry";

                container ip-prefix-detail-table {
                  description "IP FIB prefix detail table";

                  container ip-prefix-hardware-detail-types {
                    description "IP FIB prefix detail table entry";

                    list ip-prefix-hardware-detail-type {
                      key "hardware-table-type";
                      description
                        "IP FIB prefix detail table entry";

                      container ip-prefix-hardware-details {
                        description
                          "IP FIB prefix detail table entry";

                        list ip-prefix-hardware-detail {
                          description
                            "IP FIB prefix detail table entry";
                          leaf prefix {
                            type inet:ip-address-no-zone;
                            description "Destination IP address";
                          }
                          leaf prefix-length {
                            type xr:Ipv6-prefix-length;
                            description "IP FIB prefix length";
                          }
                          uses FIB-SH-TBL-FIB;
                        }
                      }
                      leaf hardware-table-type {
                        type Prefix-hardware-table;
                        description "Hw table type";
                      }
                    }
                  }

                  container ip-prefix-software-details {
                    description "IP FIB prefix detail table entry";

                    list ip-prefix-software-detail {
                      description
                        "IP FIB prefix detail table entry";
                      leaf prefix {
                        type inet:ip-address-no-zone;
                        description "Destination IP address";
                      }
                      leaf prefix-length {
                        type xr:Ipv6-prefix-length;
                        description "IP FIB prefix length";
                      }
                      uses FIB-SH-TBL-FIB;
                    }
                  }
                }

                container summary {
                  description "Operational data for FIB Tablee";
                  uses FIB-SH-SUM;
                }

                container attributes {
                  description "Information on attribute data";

                  list attribute {
                    description "Attribute Data";
                    leaf attribute-index {
                      type uint32 {
                        range "0..4294967295";
                      }
                      description "Attribute Index";
                    }
                    leaf attribute-local-index {
                      type uint32 {
                        range "0..4294967295";
                      }
                      description "Attribute Local Index";
                    }
                    uses FIB-ATTRIBUTE-DET;
                  }
                }

                container ipv6-d-var-details {
                  description "IPv6 FIB prefix DVAR table";

                  list ipv6-d-var-detail {
                    description "IPv6 FIB prefix dvar entry";
                    leaf table-id-key {
                      type xr:Hex-integer;
                      description "Table Id";
                    }
                    leaf prefix {
                      type inet:ip-address-no-zone;
                      description "IPv6 address";
                    }
                    leaf prefix-length-key {
                      type xr:Ipv6-prefix-length;
                      description "IPv6 prefix length";
                    }
                    uses FIB-SH-TBL-FIB-DVARS;
                  }
                }

                container interface-infos {
                  description "Table of InterfaceInfo";

                  list interface-info {
                    description
                      "InterfaceInfo container has 3 leaves.
                      HwIng ( HWIngressInfo ),HwEgress (
                      HWEgressInfo ),LinkType( FIBLinkType )";

                    container interfaces {
                      description "Table of interfaces";

                      list interface {
                        key "interface-name";
                        description "Specify Interface name";
                        leaf interface-name {
                          type xr:Interface-name;
                          description "Interface Name";
                        }
                        uses FIB-SH-INT;
                      }
                    }
                    leaf hw-ing {
                      type Hw-ingress-info;
                      description "Hardware Ingress";
                    }
                    leaf hw-egress {
                      type Hw-egress-info;
                      description "Hardware Egress";
                    }
                    leaf link-type {
                      type Fib-link;
                      description "Link type";
                    }
                  }
                }

                container recursive-nexthops {
                  description "Information on Recursive Nexthop";

                  list recursive-nexthop {
                    description
                      "IPv4/IPv6 Route address, IPv4/IPv6 Prefix
                      length";
                    leaf address {
                      type inet:ip-address-no-zone;
                      description "IPv4/IPv6 Route Address ";
                    }
                    leaf prefix-length-key {
                      type Prefix-len-range;
                      description "IPv4/IPv6 Prefix Length";
                    }
                    uses FIB-SH-REC-NH;
                  }
                }

                container ip-prefix-brief-table {
                  description "IP FIB prefix brief table";

                  container ip-prefix-software-briefs {
                    description "IP FIB prefix detail table";

                    list ip-prefix-software-brief {
                      description
                        "IP FIB prefix brief software table entry";
                      leaf prefix {
                        type inet:ip-address-no-zone;
                        description "Destination IP address";
                      }
                      leaf prefix-length {
                        type xr:Ipv6-prefix-length;
                        description "IP FIB prefix length";
                      }
                      uses FIB-SH-TBL-FIB;
                    }
                  }

                  container ip-prefix-hardware-brief-types {
                    description "IP FIB prefix brief table entry";

                    list ip-prefix-hardware-brief-type {
                      key "hardware-table-type";
                      description "IP FIB prefix brief table entry";

                      container ip-prefix-hardware-briefs {
                        description
                          "IP FIB prefix brief info table";

                        list ip-prefix-hardware-brief {
                          description
                            "IP FIB prefix brief table entry";
                          leaf prefix {
                            type inet:ip-address-no-zone;
                            description "Destination IP address";
                          }
                          leaf prefix-length {
                            type xr:Ipv6-prefix-length;
                            description "IP FIB prefix length";
                          }
                          uses FIB-SH-TBL-FIB;
                        }
                      }
                      leaf hardware-table-type {
                        type Prefix-hardware-table;
                        description "Hw table type";
                      }
                    }
                  }
                }

                container ipv4-d-var-details {
                  description "IPv4 FIB prefix DVAR table";

                  list ipv4-d-var-detail {
                    description "IPv4 FIB prefix dvar entry";
                    leaf table-id-key {
                      type xr:Hex-integer;
                      description "Table Id";
                    }
                    leaf prefix {
                      type inet:ipv4-address-no-zone;
                      description "IPv4 address";
                    }
                    leaf prefix-length-key {
                      type xr:Ipv4-prefix-length;
                      description "IPv4 prefix length";
                    }
                    uses FIB-SH-TBL-FIB-DVARS;
                  }
                }

                container attribute-summary {
                  description "Information on attribute summary";
                  uses FIB-ATTRIBUTE-SUMMARY;
                }

                container policy-database {
                  description "Database of Policies";

                  container policy-hardware-egresses {
                    description "Policy Table";

                    list policy-hardware-egress {
                      key "policy-name-key";
                      description "Policy Entry";
                      leaf policy-name-key {
                        type xr:Cisco-ios-xr-string {
                          length "1..64";
                        }
                        description "Policy Name";
                      }
                      uses FIB-SH-POLICY-ENTRY;
                    }
                  }

                  container policies {
                    description "Policy Table";

                    list policy {
                      key "policy-name-key";
                      description "Policy Entry";
                      leaf policy-name-key {
                        type xr:Cisco-ios-xr-string {
                          length "1..64";
                        }
                        description "Policy Name";
                      }
                      uses FIB-SH-POLICY-ENTRY;
                    }
                  }

                  container policy-hardware-ingresses {
                    description "Policy Table";

                    list policy-hardware-ingress {
                      key "policy-name-key";
                      description "Policy Entry";
                      leaf policy-name-key {
                        type xr:Cisco-ios-xr-string {
                          length "1..64";
                        }
                        description "Policy Name";
                      }
                      uses FIB-SH-POLICY-ENTRY;
                    }
                  }
                }

                container nh-info {
                  description "FIB NHInfo table";

                  container nh-info-detail-hardware-egress {
                    description
                      "NHInfoTable is accessed by two keys;
                      {NHInterface,NHAddress}";

                    container "nh-info-local-mpls-detail-hardware"+
                      "-egresses" {
                      description "Local (non-remote) nhinfo";

                      list "nh-info-local-mpls-detail-hardware"+
                        "-egress" {
                        description
                          "MPLS Detail-Hardware-Egress NHinfo
                          entry";
                        leaf nh-local-type {
                          type Fibnh-local;
                          description "Next-hop Type";
                        }
                        leaf parent-nh-interface-name {
                          type xr:Interface-name;
                          description "Parent Interface Name";
                        }
                        leaf nh-interface-name {
                          type xr:Interface-name;
                          description "Interface Name";
                        }
                        leaf nh-proto {
                          type Fib-protocol;
                          description "Next-hop proto";
                        }
                        leaf nh-pfx-length {
                          type uint32;
                          description "Next-hop prefix length";
                        }
                        leaf nh-address {
                          type xr:Cisco-ios-xr-string;
                          description
                            "Next-hop address in string format";
                        }
                        uses FIB-SH-NHINFO;
                      }
                    }

                    container "nh-info-special-detail-hardware"+
                      "-egress" {
                      description
                        "Detail hardware egress info for Special
                        nhinfo";
                      uses "NH-INFO-SPECIAL-NULL"+
                        "-DETAIL-HARDWARE-EGRESS";
                      uses "NH-INFO-SPECIAL-PUNT"+
                        "-DETAIL-HARDWARE-EGRESS";
                      uses "NH-INFO-SPECIAL-DISCARD"+
                        "-DETAIL-HARDWARE-EGRESS";
                      uses "NH-INFO-SPECIAL-DROP"+
                        "-DETAIL-HARDWARE-EGRESS";
                    }

                    container "nh-info-local-detail-hardware"+
                      "-egresses" {
                      description "Local (non-remote) nhinfo";

                      list nh-info-local-detail-hardware-egress {
                        description
                          "Detail-Hardware-Egress NHinfo entry";
                        leaf nh-local-type {
                          type Fibnh-local;
                          description "Next-hop Type";
                        }
                        leaf parent-nh-interface-name {
                          type xr:Interface-name;
                          description "Parent Interface Name";
                        }
                        leaf nh-interface-name {
                          type xr:Interface-name;
                          description "Interface Name";
                        }
                        leaf nh-proto {
                          type Fib-protocol;
                          description "Next-hop proto";
                        }
                        leaf nh-pfx-length {
                          type uint32;
                          description "Next-hop prefix length";
                        }
                        leaf nh-address {
                          type xr:Cisco-ios-xr-string;
                          description
                            "Next-hop address in string format";
                        }
                        uses FIB-SH-NHINFO;
                      }
                    }

                    container "nh-info-remote-mpls-detail-hardware"+
                      "-egresses" {
                      description
                        "Detail hardware egress info for remote
                        NHInfo table";

                      list "nh-info-remote-mpls-detail-hardware"+
                        "-egress" {
                        description
                          "MPLS Detail-Hardware-Egress NHinfo
                          entry";
                        leaf nh-remote-type {
                          type Fibnh-remote;
                          description "Next-hop Type";
                        }
                        leaf parent-nh-interface-name {
                          type xr:Interface-name;
                          description "Parent Interface Name";
                        }
                        leaf nh-interface-name {
                          type xr:Interface-name;
                          description "Interface Name";
                        }
                        leaf nh-proto {
                          type Fib-protocol;
                          description "Next-hop proto";
                        }
                        leaf nh-pfx-length {
                          type uint32;
                          description "Next-hop prefix length";
                        }
                        leaf nh-address {
                          type xr:Cisco-ios-xr-string;
                          description
                            "Next-hop address in string format";
                        }
                        uses FIB-SH-NHINFO;
                      }
                    }

                    container "nh-info-special-mpls-detail-hardware"+
                      "-egress" {
                      description
                        "Detail hardware egress info for Special
                        nhinfo";
                      uses "NH-INFO-SPECIAL-NULL"+
                        "-DETAIL-HARDWARE-EGRESS";
                      uses "NH-INFO-SPECIAL-PUNT"+
                        "-DETAIL-HARDWARE-EGRESS";
                      uses "NH-INFO-SPECIAL-DISCARD"+
                        "-DETAIL-HARDWARE-EGRESS";
                      uses "NH-INFO-SPECIAL-DROP"+
                        "-DETAIL-HARDWARE-EGRESS";
                    }

                    container "nh-info-remote-detail-hardware"+
                      "-egresses" {
                      description
                        "Detail hardware egress info for remote
                        NHInfo table";

                      list nh-info-remote-detail-hardware-egress {
                        description
                          "Detail-Hardware-Egress NHinfo entry";
                        leaf nh-remote-type {
                          type Fibnh-remote;
                          description "Next-hop Type";
                        }
                        leaf parent-nh-interface-name {
                          type xr:Interface-name;
                          description "Parent Interface Name";
                        }
                        leaf nh-interface-name {
                          type xr:Interface-name;
                          description "Interface Name";
                        }
                        leaf nh-proto {
                          type Fib-protocol;
                          description "Next-hop proto";
                        }
                        leaf nh-pfx-length {
                          type uint32;
                          description "Next-hop prefix length";
                        }
                        leaf nh-address {
                          type xr:Cisco-ios-xr-string;
                          description
                            "Next-hop address in string format";
                        }
                        uses FIB-SH-NHINFO;
                      }
                    }
                  }

                  container nh-info-detail {
                    description
                      "NHInfoTable is accessed by two keys;
                      {NHInterface,NHAddress}";

                    container nh-info-local-details {
                      description "Local (non-remote) nhinfo";

                      list nh-info-local-detail {
                        description "Detail NHinfo entry";
                        leaf nh-local-type {
                          type Fibnh-local;
                          description "Next-hop Type";
                        }
                        leaf parent-nh-interface-name {
                          type xr:Interface-name;
                          description "Parent Interface Name";
                        }
                        leaf nh-interface-name {
                          type xr:Interface-name;
                          description "Interface Name";
                        }
                        leaf nh-proto {
                          type Fib-protocol;
                          description "Next-hop proto";
                        }
                        leaf nh-pfx-length {
                          type uint32;
                          description "Next-hop prefix length";
                        }
                        leaf nh-address {
                          type xr:Cisco-ios-xr-string;
                          description
                            "Next-hop address in string format";
                        }
                        uses FIB-SH-NHINFO;
                      }
                    }

                    container nh-info-remote-mpls-details {
                      description "Detailed Remote NHInfo table";

                      list nh-info-remote-mpls-detail {
                        description "MPLS Detail NHinfo entry";
                        leaf nh-remote-type {
                          type Fibnh-remote;
                          description "Next-hop Type";
                        }
                        leaf parent-nh-interface-name {
                          type xr:Interface-name;
                          description "Parent Interface Name";
                        }
                        leaf nh-interface-name {
                          type xr:Interface-name;
                          description "Interface Name";
                        }
                        leaf nh-proto {
                          type Fib-protocol;
                          description "Next-hop proto";
                        }
                        leaf nh-pfx-length {
                          type uint32;
                          description "Next-hop prefix length";
                        }
                        leaf nh-address {
                          type xr:Cisco-ios-xr-string;
                          description
                            "Next-hop address in string format";
                        }
                        uses FIB-SH-NHINFO;
                      }
                    }

                    container nh-info-local-mpls-details {
                      description "Local (non-remote) nhinfo";

                      list nh-info-local-mpls-detail {
                        description "MPLS Detail NHinfo entry";
                        leaf nh-local-type {
                          type Fibnh-local;
                          description "Next-hop Type";
                        }
                        leaf parent-nh-interface-name {
                          type xr:Interface-name;
                          description "Parent Interface Name";
                        }
                        leaf nh-interface-name {
                          type xr:Interface-name;
                          description "Interface Name";
                        }
                        leaf nh-proto {
                          type Fib-protocol;
                          description "Next-hop proto";
                        }
                        leaf nh-pfx-length {
                          type uint32;
                          description "Next-hop prefix length";
                        }
                        leaf nh-address {
                          type xr:Cisco-ios-xr-string;
                          description
                            "Next-hop address in string format";
                        }
                        uses FIB-SH-NHINFO;
                      }
                    }

                    container nh-info-special-detail {
                      description "Special nhinfo";
                      uses NH-INFO-SPECIAL-PUNT-DETAIL;
                      uses NH-INFO-SPECIAL-DROP-DETAIL;
                      uses NH-INFO-SPECIAL-NULL-DETAIL;
                      uses NH-INFO-SPECIAL-DISCARD-DETAIL;
                    }

                    container nh-info-special-mpls-detail {
                      description "Special nhinfo";
                      uses NH-INFO-SPECIAL-PUNT-DETAIL;
                      uses NH-INFO-SPECIAL-DROP-DETAIL;
                      uses NH-INFO-SPECIAL-NULL-DETAIL;
                      uses NH-INFO-SPECIAL-DISCARD-DETAIL;
                    }

                    container nh-info-remote-details {
                      description "Detailed Remote NHInfo table";

                      list nh-info-remote-detail {
                        description "Detail NHinfo entry";
                        leaf nh-remote-type {
                          type Fibnh-remote;
                          description "Next-hop Type";
                        }
                        leaf parent-nh-interface-name {
                          type xr:Interface-name;
                          description "Parent Interface Name";
                        }
                        leaf nh-interface-name {
                          type xr:Interface-name;
                          description "Interface Name";
                        }
                        leaf nh-proto {
                          type Fib-protocol;
                          description "Next-hop proto";
                        }
                        leaf nh-pfx-length {
                          type uint32;
                          description "Next-hop prefix length";
                        }
                        leaf nh-address {
                          type xr:Cisco-ios-xr-string;
                          description
                            "Next-hop address in string format";
                        }
                        uses FIB-SH-NHINFO;
                      }
                    }
                  }

                  container nh-info-hardware-ingress {
                    description
                      "NHInfoTable is accessed by two keys;
                      {NHInterface,NHAddress}";

                    container nh-info-local-hardware-ingresses {
                      description "Local (non-remote) nhinfo";

                      list nh-info-local-hardware-ingress {
                        description "Hardware-Ingress NHinfo entry";
                        leaf nh-local-type {
                          type Fibnh-local;
                          description "Next-hop Type";
                        }
                        leaf parent-nh-interface-name {
                          type xr:Interface-name;
                          description "Parent Interface Name";
                        }
                        leaf nh-interface-name {
                          type xr:Interface-name;
                          description "Interface Name";
                        }
                        leaf nh-proto {
                          type Fib-protocol;
                          description "Next-hop proto";
                        }
                        leaf nh-pfx-length {
                          type uint32;
                          description "Next-hop prefix length";
                        }
                        leaf nh-address {
                          type xr:Cisco-ios-xr-string;
                          description
                            "Next-hop address in string format";
                        }
                        uses FIB-SH-NHINFO;
                      }
                    }

                    container nh-info-special-hardware-ingress {
                      description "Special nhinfo";
                      uses NH-INFO-SPECIAL-DISCARD-HARDWARE-INGRESS;
                      uses NH-INFO-SPECIAL-PUNT-HARDWARE-INGRESS;
                      uses NH-INFO-SPECIAL-DROP-HARDWARE-INGRESS;
                      uses NH-INFO-SPECIAL-NULL-HARDWARE-INGRESS;
                    }

                    container "nh-info-special-mpls-hardware"+
                      "-ingress" {
                      description "Special nhinfo";
                      uses NH-INFO-SPECIAL-DISCARD-HARDWARE-INGRESS;
                      uses NH-INFO-SPECIAL-PUNT-HARDWARE-INGRESS;
                      uses NH-INFO-SPECIAL-DROP-HARDWARE-INGRESS;
                      uses NH-INFO-SPECIAL-NULL-HARDWARE-INGRESS;
                    }

                    container nh-info-remote-hardware-ingresses {
                      description
                        "hardware ingress info for remote NHInfo
                        table";

                      list nh-info-remote-hardware-ingress {
                        description
                          "Detail-Hardware-Ingress NHinfo entry";
                        leaf nh-remote-type {
                          type Fibnh-remote;
                          description "Next-hop Type";
                        }
                        leaf parent-nh-interface-name {
                          type xr:Interface-name;
                          description "Parent Interface Name";
                        }
                        leaf nh-interface-name {
                          type xr:Interface-name;
                          description "Interface Name";
                        }
                        leaf nh-proto {
                          type Fib-protocol;
                          description "Next-hop proto";
                        }
                        leaf nh-pfx-length {
                          type uint32;
                          description "Next-hop prefix length";
                        }
                        leaf nh-address {
                          type xr:Cisco-ios-xr-string;
                          description
                            "Next-hop address in string format";
                        }
                        uses FIB-SH-NHINFO;
                      }
                    }

                    container "nh-info-local-mpls-hardware"+
                      "-ingresses" {
                      description "Local (non-remote) nhinfo";

                      list nh-info-local-mpls-hardware-ingress {
                        description
                          "MPLS Hardware-Ingress NHinfo entry";
                        leaf nh-local-type {
                          type Fibnh-local;
                          description "Next-hop Type";
                        }
                        leaf parent-nh-interface-name {
                          type xr:Interface-name;
                          description "Parent Interface Name";
                        }
                        leaf nh-interface-name {
                          type xr:Interface-name;
                          description "Interface Name";
                        }
                        leaf nh-proto {
                          type Fib-protocol;
                          description "Next-hop proto";
                        }
                        leaf nh-pfx-length {
                          type uint32;
                          description "Next-hop prefix length";
                        }
                        leaf nh-address {
                          type xr:Cisco-ios-xr-string;
                          description
                            "Next-hop address in string format";
                        }
                        uses FIB-SH-NHINFO;
                      }
                    }

                    container "nh-info-remote-mpls-hardware"+
                      "-ingresses" {
                      description
                        "hardware ingress info for remote NHInfo
                        table";

                      list nh-info-remote-mpls-hardware-ingress {
                        description
                          "MPLS Hardware-Ingress NHinfo entry";
                        leaf nh-remote-type {
                          type Fibnh-remote;
                          description "Next-hop Type";
                        }
                        leaf parent-nh-interface-name {
                          type xr:Interface-name;
                          description "Parent Interface Name";
                        }
                        leaf nh-interface-name {
                          type xr:Interface-name;
                          description "Interface Name";
                        }
                        leaf nh-proto {
                          type Fib-protocol;
                          description "Next-hop proto";
                        }
                        leaf nh-pfx-length {
                          type uint32;
                          description "Next-hop prefix length";
                        }
                        leaf nh-address {
                          type xr:Cisco-ios-xr-string;
                          description
                            "Next-hop address in string format";
                        }
                        uses FIB-SH-NHINFO;
                      }
                    }
                  }

                  container nh-info-detail-hardware-ingress {
                    description
                      "NHInfoTable is accessed by two keys;
                      {NHInterface,NHAddress}";

                    container "nh-info-special-mpls-detail-hardware"+
                      "-ingress" {
                      description "Special nhinfo";
                      uses "NH-INFO-SPECIAL-PUNT"+
                        "-DETAIL-HARDWARE-INGRESS";
                      uses "NH-INFO-SPECIAL-NULL"+
                        "-DETAIL-HARDWARE-INGRESS";
                      uses "NH-INFO-SPECIAL-DROP"+
                        "-DETAIL-HARDWARE-INGRESS";
                      uses "NH-INFO-SPECIAL-DISCARD"+
                        "-DETAIL-HARDWARE-INGRESS";
                    }

                    container "nh-info-remote-detail-hardware"+
                      "-ingresses" {
                      description
                        "Detailed hardware ingress info for
                        remote NHInfo table";

                      list nh-info-remote-detail-hardware-ingress {
                        description
                          "Detail-Hardware-Ingress NHinfo entry";
                        leaf nh-remote-type {
                          type Fibnh-remote;
                          description "Next-hop Type";
                        }
                        leaf parent-nh-interface-name {
                          type xr:Interface-name;
                          description "Parent Interface Name";
                        }
                        leaf nh-interface-name {
                          type xr:Interface-name;
                          description "Interface Name";
                        }
                        leaf nh-proto {
                          type Fib-protocol;
                          description "Next-hop proto";
                        }
                        leaf nh-pfx-length {
                          type uint32;
                          description "Next-hop prefix length";
                        }
                        leaf nh-address {
                          type xr:Cisco-ios-xr-string;
                          description
                            "Next-hop address in string format";
                        }
                        uses FIB-SH-NHINFO;
                      }
                    }

                    container "nh-info-remote-mpls-detail-hardware"+
                      "-ingresses" {
                      description
                        "Detailed hardware ingress info for
                        remote NHInfo table";

                      list "nh-info-remote-mpls-detail-hardware"+
                        "-ingress" {
                        description
                          "MPLS Detail-Hardware-Ingress NHinfo
                          entry";
                        leaf nh-remote-type {
                          type Fibnh-remote;
                          description "Next-hop Type";
                        }
                        leaf parent-nh-interface-name {
                          type xr:Interface-name;
                          description "Parent Interface Name";
                        }
                        leaf nh-interface-name {
                          type xr:Interface-name;
                          description "Interface Name";
                        }
                        leaf nh-proto {
                          type Fib-protocol;
                          description "Next-hop proto";
                        }
                        leaf nh-pfx-length {
                          type uint32;
                          description "Next-hop prefix length";
                        }
                        leaf nh-address {
                          type xr:Cisco-ios-xr-string;
                          description
                            "Next-hop address in string format";
                        }
                        uses FIB-SH-NHINFO;
                      }
                    }

                    container "nh-info-local-detail-hardware"+
                      "-ingresses" {
                      description "Local (non-remote) nhinfo";

                      list nh-info-local-detail-hardware-ingress {
                        description
                          "Detail-Hardware-Ingress NHinfo entry";
                        leaf nh-local-type {
                          type Fibnh-local;
                          description "Next-hop Type";
                        }
                        leaf parent-nh-interface-name {
                          type xr:Interface-name;
                          description "Parent Interface Name";
                        }
                        leaf nh-interface-name {
                          type xr:Interface-name;
                          description "Interface Name";
                        }
                        leaf nh-proto {
                          type Fib-protocol;
                          description "Next-hop proto";
                        }
                        leaf nh-pfx-length {
                          type uint32;
                          description "Next-hop prefix length";
                        }
                        leaf nh-address {
                          type xr:Cisco-ios-xr-string;
                          description
                            "Next-hop address in string format";
                        }
                        uses FIB-SH-NHINFO;
                      }
                    }

                    container "nh-info-special-detail-hardware"+
                      "-ingress" {
                      description "Special nhinfo";
                      uses "NH-INFO-SPECIAL-PUNT"+
                        "-DETAIL-HARDWARE-INGRESS";
                      uses "NH-INFO-SPECIAL-NULL"+
                        "-DETAIL-HARDWARE-INGRESS";
                      uses "NH-INFO-SPECIAL-DROP"+
                        "-DETAIL-HARDWARE-INGRESS";
                      uses "NH-INFO-SPECIAL-DISCARD"+
                        "-DETAIL-HARDWARE-INGRESS";
                    }

                    container "nh-info-local-mpls-detail-hardware"+
                      "-ingresses" {
                      description "Local (non-remote) nhinfo";

                      list "nh-info-local-mpls-detail-hardware"+
                        "-ingress" {
                        description
                          "MPLS Detail-Hardware-Ingress NHinfo
                          entry";
                        leaf nh-local-type {
                          type Fibnh-local;
                          description "Next-hop Type";
                        }
                        leaf parent-nh-interface-name {
                          type xr:Interface-name;
                          description "Parent Interface Name";
                        }
                        leaf nh-interface-name {
                          type xr:Interface-name;
                          description "Interface Name";
                        }
                        leaf nh-proto {
                          type Fib-protocol;
                          description "Next-hop proto";
                        }
                        leaf nh-pfx-length {
                          type uint32;
                          description "Next-hop prefix length";
                        }
                        leaf nh-address {
                          type xr:Cisco-ios-xr-string;
                          description
                            "Next-hop address in string format";
                        }
                        uses FIB-SH-NHINFO;
                      }
                    }
                  }

                  container nh-info-hardware-egress {
                    description
                      "NHInfoTable is accessed by two keys;
                      {NHInterface,NHAddress}";

                    container nh-info-local-hardware-egresses {
                      description "Local (non-remote) nhinfo";

                      list nh-info-local-hardware-egress {
                        description "Hardware-Egress NHinfo entry";
                        leaf nh-local-type {
                          type Fibnh-local;
                          description "Next-hop Type";
                        }
                        leaf parent-nh-interface-name {
                          type xr:Interface-name;
                          description "Parent Interface Name";
                        }
                        leaf nh-interface-name {
                          type xr:Interface-name;
                          description "Interface Name";
                        }
                        leaf nh-proto {
                          type Fib-protocol;
                          description "Next-hop proto";
                        }
                        leaf nh-pfx-length {
                          type uint32;
                          description "Next-hop prefix length";
                        }
                        leaf nh-address {
                          type xr:Cisco-ios-xr-string;
                          description
                            "Next-hop address in string format";
                        }
                        uses FIB-SH-NHINFO;
                      }
                    }

                    container nh-info-remote-hardware-egresses {
                      description
                        "hardware egress info for remote NHInfo
                        table";

                      list nh-info-remote-hardware-egress {
                        description "Hardware-Egress NHinfo entry";
                        leaf nh-remote-type {
                          type Fibnh-remote;
                          description "Next-hop Type";
                        }
                        leaf parent-nh-interface-name {
                          type xr:Interface-name;
                          description "Parent Interface Name";
                        }
                        leaf nh-interface-name {
                          type xr:Interface-name;
                          description "Interface Name";
                        }
                        leaf nh-proto {
                          type Fib-protocol;
                          description "Next-hop proto";
                        }
                        leaf nh-pfx-length {
                          type uint32;
                          description "Next-hop prefix length";
                        }
                        leaf nh-address {
                          type xr:Cisco-ios-xr-string;
                          description
                            "Next-hop address in string format";
                        }
                        uses FIB-SH-NHINFO;
                      }
                    }

                    container nh-info-special-mpls-hardware-egress {
                      description
                        "hardware egress info for Special nhinfo";
                      uses NH-INFO-SPECIAL-DISCARD-HARDWARE-EGRESS;
                      uses NH-INFO-SPECIAL-PUNT-HARDWARE-EGRESS;
                      uses NH-INFO-SPECIAL-DROP-HARDWARE-EGRESS;
                      uses NH-INFO-SPECIAL-NULL-HARDWARE-EGRESS;
                    }

                    container nh-info-local-mpls-hardware-egresses {
                      description "Local (non-remote) nhinfo";

                      list nh-info-local-mpls-hardware-egress {
                        description
                          "MPLS Hardware-Egress NHinfo entry";
                        leaf nh-local-type {
                          type Fibnh-local;
                          description "Next-hop Type";
                        }
                        leaf parent-nh-interface-name {
                          type xr:Interface-name;
                          description "Parent Interface Name";
                        }
                        leaf nh-interface-name {
                          type xr:Interface-name;
                          description "Interface Name";
                        }
                        leaf nh-proto {
                          type Fib-protocol;
                          description "Next-hop proto";
                        }
                        leaf nh-pfx-length {
                          type uint32;
                          description "Next-hop prefix length";
                        }
                        leaf nh-address {
                          type xr:Cisco-ios-xr-string;
                          description
                            "Next-hop address in string format";
                        }
                        uses FIB-SH-NHINFO;
                      }
                    }

                    container "nh-info-remote-mpls-hardware"+
                      "-egresses" {
                      description
                        "hardware egress info for remote NHInfo
                        table";

                      list nh-info-remote-mpls-hardware-egress {
                        description
                          "MPLS Hardware-Egress NHinfo entry";
                        leaf nh-remote-type {
                          type Fibnh-remote;
                          description "Next-hop Type";
                        }
                        leaf parent-nh-interface-name {
                          type xr:Interface-name;
                          description "Parent Interface Name";
                        }
                        leaf nh-interface-name {
                          type xr:Interface-name;
                          description "Interface Name";
                        }
                        leaf nh-proto {
                          type Fib-protocol;
                          description "Next-hop proto";
                        }
                        leaf nh-pfx-length {
                          type uint32;
                          description "Next-hop prefix length";
                        }
                        leaf nh-address {
                          type xr:Cisco-ios-xr-string;
                          description
                            "Next-hop address in string format";
                        }
                        uses FIB-SH-NHINFO;
                      }
                    }

                    container nh-info-special-hardware-egress {
                      description
                        "hardware egress info for Special nhinfo";
                      uses NH-INFO-SPECIAL-DISCARD-HARDWARE-EGRESS;
                      uses NH-INFO-SPECIAL-PUNT-HARDWARE-EGRESS;
                      uses NH-INFO-SPECIAL-DROP-HARDWARE-EGRESS;
                      uses NH-INFO-SPECIAL-NULL-HARDWARE-EGRESS;
                    }
                  }

                  container nh-info-brief {
                    description
                      "NHInfoTable is accessed by two keys;
                      {NHInterface,NHAddress}";

                    container nh-info-special-mpls-brief {
                      description "Special nhinfo";
                      uses NH-INFO-SPECIAL-DISCARD-BRIEF;
                      uses NH-INFO-SPECIAL-NULL-BRIEF;
                      uses NH-INFO-SPECIAL-PUNT-BRIEF;
                      uses NH-INFO-SPECIAL-DROP-BRIEF;
                    }

                    container nh-info-special-brief {
                      description "Special nhinfo";
                      uses NH-INFO-SPECIAL-DISCARD-BRIEF;
                      uses NH-INFO-SPECIAL-NULL-BRIEF;
                      uses NH-INFO-SPECIAL-PUNT-BRIEF;
                      uses NH-INFO-SPECIAL-DROP-BRIEF;
                    }

                    container nh-info-local-mpls-briefs {
                      description "Local (non-remote) nhinfo";

                      list nh-info-local-mpls-brief {
                        description "MPLS Brief NHinfo entry";
                        leaf nh-local-type {
                          type Fibnh-local;
                          description "Next-hop Type";
                        }
                        leaf parent-nh-interface-name {
                          type xr:Interface-name;
                          description "Parent Interface Name";
                        }
                        leaf nh-interface-name {
                          type xr:Interface-name;
                          description "Interface Name";
                        }
                        leaf nh-proto {
                          type Fib-protocol;
                          description "Next-hop proto";
                        }
                        leaf nh-pfx-length {
                          type uint32;
                          description "Next-hop prefix length";
                        }
                        leaf nh-address {
                          type xr:Cisco-ios-xr-string;
                          description
                            "Next-hop address in string format";
                        }
                        uses FIB-SH-NHINFO;
                      }
                    }

                    container nh-info-remote-briefs {
                      description "remote nhinfo";

                      list nh-info-remote-brief {
                        description "Brief NHinfo entry";
                        leaf nh-remote-type {
                          type Fibnh-remote;
                          description "Next-hop Type";
                        }
                        leaf parent-nh-interface-name {
                          type xr:Interface-name;
                          description "Parent Interface Name";
                        }
                        leaf nh-interface-name {
                          type xr:Interface-name;
                          description "Interface Name";
                        }
                        leaf nh-proto {
                          type Fib-protocol;
                          description "Next-hop proto";
                        }
                        leaf nh-pfx-length {
                          type uint32;
                          description "Next-hop prefix length";
                        }
                        leaf nh-address {
                          type xr:Cisco-ios-xr-string;
                          description
                            "Next-hop address in string format";
                        }
                        uses FIB-SH-NHINFO;
                      }
                    }

                    container nh-info-local-briefs {
                      description "Local (non-remote) nhinfo";

                      list nh-info-local-brief {
                        description "Brief NHinfo entry";
                        leaf nh-local-type {
                          type Fibnh-local;
                          description "Next-hop Type";
                        }
                        leaf parent-nh-interface-name {
                          type xr:Interface-name;
                          description "Parent Interface Name";
                        }
                        leaf nh-interface-name {
                          type xr:Interface-name;
                          description "Interface Name";
                        }
                        leaf nh-proto {
                          type Fib-protocol;
                          description "Next-hop proto";
                        }
                        leaf nh-pfx-length {
                          type uint32;
                          description "Next-hop prefix length";
                        }
                        leaf nh-address {
                          type xr:Cisco-ios-xr-string;
                          description
                            "Next-hop address in string format";
                        }
                        uses FIB-SH-NHINFO;
                      }
                    }

                    container nh-info-remote-mpls-briefs {
                      description "remote nhinfo";

                      list nh-info-remote-mpls-brief {
                        description "MPLS Brief NHinfo entry";
                        leaf nh-remote-type {
                          type Fibnh-remote;
                          description "Next-hop Type";
                        }
                        leaf parent-nh-interface-name {
                          type xr:Interface-name;
                          description "Parent Interface Name";
                        }
                        leaf nh-interface-name {
                          type xr:Interface-name;
                          description "Interface Name";
                        }
                        leaf nh-proto {
                          type Fib-protocol;
                          description "Next-hop proto";
                        }
                        leaf nh-pfx-length {
                          type uint32;
                          description "Next-hop prefix length";
                        }
                        leaf nh-address {
                          type xr:Cisco-ios-xr-string;
                          description
                            "Next-hop address in string format";
                        }
                        uses FIB-SH-NHINFO;
                      }
                    }
                  }
                }

                container srv6-accountings {
                  description "SRV6 accounting table";

                  list srv6-accounting {
                    description "SRV6 accounting table entry";
                    leaf prefix {
                      type inet:ip-address-no-zone;
                      description "SRV6 address";
                    }
                    leaf prefix-length-key {
                      type xr:Ipv6-prefix-length;
                      description "Prefix Length";
                    }
                    uses FIB-SRV6-SH;
                  }
                }
                leaf vrf-name {
                  type string;
                  description "VRF Name";
                }
              }
            }

            container exact-routes {
              description "Exact Route Table";

              list exact-route {
                description
                  "Exact route for the given source and
                  destination addresses";
                leaf protocol-name {
                  type Fib-protocol;
                  description "Fib Protocol Name";
                }
                leaf interface-name {
                  type xr:Interface-name;
                  description "Interface Name";
                }
                leaf source {
                  type inet:ip-address-no-zone;
                  description "Source address";
                }
                leaf vrf-name {
                  type xr:Cisco-ios-xr-string;
                  description "VRF Name";
                }
                leaf class-id {
                  type uint32 {
                    range "0..7";
                  }
                  description "Class ID";
                }
                leaf ipv6-flow-label {
                  type Fibipv6-flow-label;
                  description
                    "IPv6 flow label (applies only to and used
                    only for IPv6)";
                }
                leaf ip-protocol {
                  type Exact-route-ip-protocol;
                  description "IP Protocol";
                }
                leaf src-port {
                  type uint32;
                  description "Source Port";
                }
                leaf dest-port {
                  type uint32;
                  description "Destination Port";
                }
                leaf address {
                  type inet:ip-address-no-zone;
                  description "Destination Address";
                }
                leaf has-user-data {
                  type boolean;
                  description "Has User Data";
                }
                leaf user-data {
                  type uint32;
                  description "User Data";
                }
                uses FIB-SH-TBL-FIB;
              }
            }

            container protocol-global {
              description "FIB SRV6 global information";

              container segment-routing {
                description
                  "FIB SRV6 global segment routing information";

                container srv6-hardware-ingress {
                  description
                    "FIB ipv6 global segment routing srv6
                    hardware ingress information";
                  uses FIB-SRV6-GBL-UPD;
                }

                container srv6-hardware-egress {
                  description
                    "FIB ipv6 global segment routing srv6
                    hardware egress information";
                  uses FIB-SRV6-GBL-UPD;
                }

                container srv6 {
                  description
                    "FIB ipv6 global segment routing srv6
                    information";
                  uses FIB-SRV6-GBL-UPD;
                }
              }
            }

            container nh-ids {
              description
                "NHIdTable is accessed by two keys; {NHId}
                and/or {NHInterface,NHAddress";

              list nh-id {
                description "NextHopId table entry";
                leaf nh-id {
                  type uint32;
                  description "NexthopId Value";
                }
                leaf nh-interface-name-key {
                  type xr:Interface-name;
                  description "Interface Name";
                }
                leaf nh-address-key {
                  type xr:Cisco-ios-xr-string;
                  description
                    "Next-hop address in string format (e.g., 1
                    .2.3.4)";
                }
                uses FIB-SH-NHID-ENTRY;
              }
            }

            container frr-nhinfo-pendings {
              description "FIB FRR NHINFO pending information";

              list frr-nhinfo-pending {
                description "FIB FRR Nhinfo pending information";
                leaf queue-index {
                  type Generic-index;
                  description "FIB FRR Queue Index";
                }
                leaf frr-type {
                  type Fibfrr;
                  description "FRR Type";
                }
                leaf link-type-key {
                  type Fib-link;
                  description "Link Type";
                }
                leaf prefix-length-key {
                  type Prefix-len-range;
                  description "Prefix Length";
                }
                leaf interface-name {
                  type xr:Interface-name;
                  description "Interface Name";
                }
                leaf main-interface-name-key {
                  type xr:Interface-name;
                  description "Main Interface Name";
                }
                leaf next-hop-prefix {
                  type inet:ip-address-no-zone;
                  description "NextHop Address";
                }
                leaf replicated-nh-type {
                  type Fibnh-info-repl;
                  description "Replicated NextHop Type";
                }
                uses FIB-SH-FRR-NHINFO;
              }
            }

            container external-client-summaries {
              description "External Client Summary Table";

              list external-client-summary {
                description "Summary of the external clients";
                leaf ecd-ver {
                  type uint32;
                  description "Ecd Version";
                }
                leaf id {
                  type uint32;
                  description
                    "ID of the client: ECDv1 is component id,
                    ECDv2 is client id";
                }
                uses FIB-SH-TBL-EXT-CLIENT-SUM;
              }
            }

            container cef-table-summary {
              description "Tables summary";
              uses FIB-SH-SUM;
            }

            container misc {
              description "CEF misc hidden data";
              uses FIB-SH-MISC;
            }

            container object-queue-entries {
              description "Object queue entry details";

              list object-queue-entry {
                key "object-queue-id";
                description "Object queue id";

                container object-queue-entry-infos {
                  description
                    "Details for corresponding object queue
                    entry";

                  list object-queue-entry-info {
                    key "item-index";
                    description
                      "Details for corresponding object queue
                      entry";
                    leaf item-index {
                      type uint32 {
                        range "0..4294967295";
                      }
                      description "Item Index";
                    }
                    uses FIB-OBJECT-QUEUE-ITEM-INFO;
                  }
                }
                leaf object-queue-id {
                  type uint32 {
                    range "0..255";
                  }
                  description "Object Queue ID";
                }
              }
            }

            container retry-db-summary {
              description "Retry DB Summary entry";
              uses FIB-RETRY-DB-SUMMARY;
            }

            container local-label {
              description "Fib Local label";

              container conflicts {
                description "FIB Local-label conflicts database";

                list conflict {
                  description "CEF Local-label conflicts entry";
                  leaf label {
                    type Fib-label;
                    description "Local label";
                  }
                  leaf source-key {
                    type Fib-route-source;
                    description "Route source";
                  }
                  leaf ll-ctype {
                    type Fibllc-entry;
                    description "Type of entry";
                  }
                  leaf pfx-tbl-id {
                    type uint32;
                    description "Table ID of IP prefix";
                  }
                  leaf prefix {
                    type xr:Cisco-ios-xr-string;
                    description "IP Prefix";
                  }
                  leaf prefix-length-key {
                    type uint32;
                    description "Length of IP Prefix";
                  }
                  uses FIB-MPLS-LLC;
                }
              }
            }
            leaf protocol-name {
              type Fib-protocol;
              description "Protocol Name ";
            }
          }
        }
        leaf node-name {
          type xr:Node-id;
          description "Node name";
        }
      }
    }
  }

  container oc-aft-l3 {
    config false;
    description "Openconfig L3 abstract forwarding table data";

    container protocol {
      description "Abstract forwarding table per FIB protocol";

      container ipv6 {
        description "IPv6 abstract forwarding table";
        uses OOR;
        uses ERROR;
      }

      container ipv4 {
        description "IPv4 abstract forwarding table";
        uses OOR;
        uses ERROR;
      }
    }
  }

  container mpls-forwarding {
    config false;
    description "MPLS forwarding operational data";

    container nodes {
      description "Table of Nodes";

      list node {
        key "node-name";
        description "Operational data for a specific Node";

        container forwarding-summary {
          description "MPLS forwarding summary";
          uses MPLS-FWDING-SUMMARY;
        }

        container frr-logs {
          description "FRR Log Table";

          list frr-log {
            key "event-id";
            description "FRR Log information";
            leaf event-id {
              type uint32;
              description "Event ID";
            }
            uses FIB-MPLS-FRR-EVENT;
          }
        }

        container label-fib {
          description "Labels For FIB";

          container vrfs {
            description "Table of VRFs";

            list vrf {
              key "vrf-name";
              description "VRF table";
              leaf vrf-name {
                type xr:Cisco-ios-xr-string;
                description "VRF Name";
              }
              uses INFORMATION;
            }
          }

          container forwarding-details {
            description "MPLS Forwarding Detail table";

            list forwarding-detail {
              description "MPLS forwarding details";
              leaf label-value {
                type Mpls-label;
                description "Local label value";
              }
              leaf eos {
                type Mplseos;
                description "End of stack flag";
              }
              uses MPLS-SH-LEAF;
            }
          }

          container forwarding {
            description "Forwarding filtering details";
            uses INFORMATION;
          }

          container label-security {
            description "MPLS label security";

            container interfaces {
              description "MPLS label security interface table";

              list interface {
                key "interface-name";
                description "Specify interface Name";
                leaf interface-name {
                  type xr:Interface-name;
                  description "Interface Name";
                }
                uses MPLS-LABEL-SECURITY-INTF;
              }
            }

            container summary {
              description "MPLS label security summary";
              uses MPLS-LABEL-SECURITY-SUMMARY;
            }
          }
        }

        container tunnel {
          description "TE Tunnel information";

          container forwarding-tunnels {
            description "Forwarding details for TE tunnels";

            list forwarding-tunnel {
              key "interface-name";
              description
                "Forwarding information for the TE tunnel";
              leaf interface-name {
                type xr:Interface-name;
                description "Interface Name";
              }
              uses MPLS-SH-TEHEAD;
            }
          }
        }

        container frr-database {
          description "MPLS forwarding FRR Database";

          container frrdb-summary {
            description "MPLS forwarding FRR Database Summary";
            uses FIB-MPLS-FRR-DB-SUM;
          }

          container frrdb-protected-interface-table-summaries {
            description
              "MPLS forwarding FRR Database Protected
              Interface Summary Table";

            list frrdb-protected-interface-table-summary {
              key "interface-name";
              description
                "MPLS forwarding FRR Database Protected
                Interface Summary";
              leaf interface-name {
                type xr:Interface-name;
                description "Interface Name";
              }
              uses FIB-MPLS-FRR-DB-SUM;
            }
          }

          container frrdb-tunnel-midpoint-summary {
            description
              "MPLS forwarding FRR Database Tunnel Midpoint
              Summary";
            uses FIB-MPLS-FRR-DB-SUM;
          }

          container frrdb-tunnel-midpoints {
            description
              "MPLS forwarding FRR Database Tunnel Midpoint
              Table";

            list frrdb-tunnel-midpoint {
              key "local-label";
              description
                "MPLS forwarding FRR Database Tunnel Midpoint
                Entry";
              leaf local-label {
                type Mpls-label;
                description "Local label value";
              }
              uses MPLS-FRR-DB-ENTRY;
            }
          }

          container frrdb-tunnel-heads {
            description
              "MPLS forwarding FRR Database Tunnel Head
              Table";

            list frrdb-tunnel-head {
              key "interface-name";
              description
                "MPLS forwarding FRR Database Tunnel Head
                Entry";
              leaf interface-name {
                type xr:Interface-name;
                description "Interface Name";
              }
              uses MPLS-FRR-DB-ENTRY;
            }
          }

          container frrdb-tunnel-head-summary {
            description
              "MPLS forwarding FRR Database Tunnel Head
              Summary";
            uses FIB-MPLS-FRR-DB-SUM;
          }

          container frrdb-backup-interface-summaries {
            description
              "MPLS forwarding FRR Database Backup Interface
              Summary Table";

            list frrdb-backup-interface-summary {
              key "interface-name";
              description
                "MPLS forwarding FRR Database Backup
                Interface Summary";
              leaf interface-name {
                type xr:Interface-name;
                description "Interface Name";
              }
              uses FIB-MPLS-FRR-DB-SUM;
            }
          }
        }
        leaf node-name {
          type xr:Node-id;
          description "Node ID";
        }
      }
    }
  }

  container cef-accounting {
    config false;
    description "CEF accounting operational data";

    container vrfs {
      description "VRF table";

      list vrf {
        key "vrf-name";
        description "VRF table entry";

        container afis {
          description "AFI table";

          list afi {
            key "afi-type";
            description "AFI table entry";

            container pfx {
              description "prefix accounting";

              container srv6locs {
                description "SRv6 locators";

                list srv6loc {
                  description "SRV6 accounting details";
                  leaf ipv6-address {
                    type inet:ip-address-no-zone;
                    description "IPv6 Prefix";
                  }
                  leaf prefix-length {
                    type xr:Ipv6-prefix-length;
                    description "IPv6 Prefix Length";
                  }
                  uses SRV6-ACCT-PFX-INFO;
                }
              }
            }
            leaf afi-type {
              type Fib-afi;
              description "Address family Name ";
            }
          }
        }
        leaf vrf-name {
          type string;
          description "VRF Name";
        }
      }
    }
  }
}
