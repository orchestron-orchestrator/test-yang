module Cisco-IOS-XR-um-rcc-cfg {

  /*** NAMESPACE / PREFIX DEFINITION ***/

  namespace "http://cisco.com/ns/yang/Cisco-IOS-XR-um-rcc-cfg";
  prefix um-rcc-cfg;

  /*** LINKAGE (IMPORTS / INCLUDES) ***/
  import cisco-semver { prefix "semver"; }

  /*** META INFORMATION ***/

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR rcc package configuration.

     This YANG module augments the
     modules with configuration data.

     Copyright (c) 2020, 2022 by Cisco Systems, Inc.
     All rights reserved.";

  revision 2020-09-09 {
    description
      "Initial release";
    semver:module-version "1.0.0";
  }


  container lcc {
    description
      "Label Consistency Checker";
    container ipv6 {
      description
        "IPv6 Configuration";
      container unicast {
        description
          "Unicast table";
        container enable {
          presence "Indicates a enable node is configured.";
          description
            "Enable background scan";
        }
        leaf period {
          type uint32 {
            range "100..600000" {
              description
                "Period between buffers in scans in milliseconds";
            }
          }
          description
            "Period of checks in milliseconds";
        }
      }
    }
    container ipv4 {
      description
        "IPv4 Configuration";
      container unicast {
        description
          "Unicast table";
        container enable {
          presence "Indicates a enable node is configured.";
          description
            "Enable background scan";
        }
        leaf period {
          type uint32 {
            range "100..600000" {
              description
                "Period between buffers in scans in milliseconds";
            }
          }
          description
            "Period of checks in milliseconds";
        }
      }
    }
  }
  container rcc {
    description
      "Route Consistency Checker";
    container ipv6 {
      description
        "IPv6 Configuration";
      container unicast {
        description
          "Unicast tables";
        container enable {
          presence "Indicates a enable node is configured.";
          description
            "Enable background scan";
        }
        leaf period {
          type uint32 {
            range "100..600000" {
              description
                "Period between buffers in scans in milliseconds";
            }
          }
          description
            "Period of checks in milliseconds";
        }
      }
    }
    container ipv4 {
      description
        "IPv4 Configuration";
      container unicast {
        description
          "Unicast tables";
        container enable {
          presence "Indicates a enable node is configured.";
          description
            "Enable background scan";
        }
        leaf period {
          type uint32 {
            range "100..600000" {
              description
                "Period between buffers in scans in milliseconds";
            }
          }
          description
            "Period of checks in milliseconds";
        }
      }
    }
  }
}
