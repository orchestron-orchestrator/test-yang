module Cisco-IOS-XR-um-statistics-cfg {

  /*** NAMESPACE / PREFIX DEFINITION ***/

  namespace "http://cisco.com/ns/yang/Cisco-IOS-XR-um-statistics-cfg";
  prefix um-statistics-cfg;

  /*** LINKAGE (IMPORTS / INCLUDES) ***/

  import Cisco-IOS-XR-um-interface-cfg {
    prefix a1;
  }

  import cisco-semver { prefix "semver"; }

  /*** META INFORMATION ***/

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR statistics package configuration.

     This YANG module augments the
     modules with configuration data.

     Copyright (c) 2019-2022 by Cisco Systems, Inc.
     All rights reserved.";

  revision 2022-07-11 {
    description
      "Added missing description statement to nodes";
    semver:module-version "1.1.0";
  }

  revision "2020-02-20" {
    description
      "Initial draft";
    semver:module-version "1.0.0";
  }

  grouping IF-BODY {
    description
      "Grouping for interface";
    leaf load-interval {
      type uint32 {
        range "0|30|60|90|120|150|180|210|240|270|300|330|360|390|420|450|480|510|540|570|600" {
          description
            "Number of seconds. 0 disables load calculation.";
        }
      }
      default "300";
      description
        "Specify interval for load calculation for an interface";
    }
  }

  augment "/a1:interfaces/a1:interface" {
    description
      "This augment extends active nodes configuration";
    uses IF-BODY;
  }

  augment "/a1:interfaces/a1:interface-preconfigure" {
    description
      "This augment extends preconfigured nodes
       configuration";
    uses IF-BODY;
  }

  container statistics {
    description
      "Statistics configuration commands";
    container period {
      description
        "Set collection period for statistics collectors";
      container service-accounting {
        description
          "Collectors for the service accounting feature";
        leaf collection-period {
          type uint32 {
            range "30..3600" {
              description
                "Collection period in seconds";
            }
          }
          must 'not(../disable)';
          description
            "Collection period in seconds";
        }
        container disable {
          must 'not(../collection-period)';
          presence "Indicates a disable node is configured.";
          description
            "Disable periodic statistics collection";
        }
      }
    }
  }
}
