submodule Cisco-IOS-XR-aaa-protocol-radius-oper-sub1 {

  belongs-to Cisco-IOS-XR-aaa-protocol-radius-oper {
    prefix Cisco-IOS-XR-aaa-protocol-radius-oper;
  }

  /*** LINKAGE (IMPORTS / INCLUDES) ***/

  import ietf-inet-types { prefix "inet"; }

  import cisco-semver { prefix "semver"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR aaa-protocol-radius package operational data.

     Copyright (c) 2013-2021 by Cisco Systems, Inc.
     All rights reserved.";

  revision "2021-02-23" {
    description
      "Adding yang support for coa";
    semver:module-version "1.1.0";
  }

  revision "2019-04-05" {
    description
      "Establish semantic version baseline.";
    semver:module-version "1.0.1";
  }

  revision "2017-11-13" {
    description
      "Adding yang support for new cli.";
  }

  revision "2017-05-01" {
    description
      "Fixing backward compatibility error in module.";
  }

  revision "2015-11-09" {
    description
      "IOS XR 6.0 revision.";
  }

  grouping RADIUS-CLIENTBAG {
    description "RADIUS CLIENTBAG";
    leaf unknown-authentication-response {
      type uint32;
      description
        "Number of RADIUS Access-Response packets
        received from unknown addresses";
    }
    leaf authentication-nas-id {
      type string;
      description
        "NAS-Identifier of the RADIUS authentication
        client";
    }
    leaf unknown-accounting-response {
      type uint32;
      description
        "Number of RADIUS Accounting-Response packets
        received from unknown addresses";
    }
    leaf accounting-nas-id {
      type string;
      description "NAS-Identifier of the RADIUS accounting client";
    }
  }

  grouping SRC-INTF {
    description "SRC INTF";
    leaf interface-name {
      type string;
      description "Name of the source interface";
    }
    leaf ipaddrv4 {
      type string;
      description "IP address buffer";
    }
    leaf ipaddrv6 {
      type string;
      description "IP address buffer";
    }
    leaf vrfid {
      type uint32;
      description "VRF Id";
    }
  }

  grouping SOURCE-INTERFACES {
    description "SOURCE INTERFACES";

    list list-of-source-interface {
      description "List of source interfaces";
      uses SRC-INTF;
    }
  }

  grouping RADIUS-SERVERBAG {
    description "RADIUS SERVERBAG";
    leaf ipv4-address {
      type inet:ipv4-address;
      description "IP address of RADIUS server";
    }
    leaf priority {
      type uint32;
      description
        "A number that indicates the priority of the
        server";
    }
    leaf timeout-xr {
      type uint32;
      units "second";
      description "Per-server timeout in seconds";
    }
    leaf retransmit {
      type uint32;
      description "Per-server retransmit";
    }
    leaf dead-time {
      type uint32;
      units "minute";
      description "Per-server deadtime in minutes";
    }
    leaf dead-detect-time {
      type uint32;
      units "second";
      description "Per-server dead-detect time in  seconds";
    }
    leaf dead-detect-tries {
      type uint32;
      description "Per-server dead-detect tries";
    }
    leaf authentication-port {
      type uint32;
      description "Authentication port";
    }
    leaf accounting-port {
      type uint32;
      description "Accounting port";
    }
    leaf state {
      type string;
      description "State of the server UP/DOWN";
    }
    leaf current-state-duration {
      type uint32;
      description
        "Elapsed time the server has been in current
        state";
    }
    leaf previous-state-duration {
      type uint32;
      description
        "Elapsed time the server was been in previous
        state";
    }
    leaf packets-in {
      type uint32;
      description "Total number of incoming packets read";
    }
    leaf packets-out {
      type uint32;
      description "Total number of outgoing packets sent";
    }
    leaf timeouts {
      type uint32;
      description "Total number of packets timed-out";
    }
    leaf aborts {
      type uint32;
      description "Total number of requests aborted";
    }
    leaf replies-expected {
      type uint32;
      description "Number of replies expected to arrive";
    }
    leaf redirected-requests {
      type uint32;
      description "Number of requests redirected";
    }
    leaf authentication-rtt {
      type uint32;
      units "millisecond";
      description
        "Round-trip time for authentication in
        milliseconds";
    }
    leaf access-requests {
      type uint32;
      description "Number of access requests";
    }
    leaf access-request-retransmits {
      type uint32;
      description "Number of retransmitted access requests";
    }
    leaf access-accepts {
      type uint32;
      description "Number of access accepts";
    }
    leaf access-rejects {
      type uint32;
      description "Number of access rejects";
    }
    leaf access-challenges {
      type uint32;
      description "Number of access challenges";
    }
    leaf bad-access-responses {
      type uint32;
      description "Number of bad access responses";
    }
    leaf bad-access-authenticators {
      type uint32;
      description "Number of bad access authenticators";
    }
    leaf pending-access-requests {
      type uint32;
      description "Number of pending access requests";
    }
    leaf access-timeouts {
      type uint32;
      description "Number of access packets timed-out";
    }
    leaf unknown-access-types {
      type uint32;
      description
        "Number of packets received with unknown type
        from authentication server";
    }
    leaf dropped-access-responses {
      type uint32;
      description "Number of access responses dropped";
    }
    leaf throttled-access-reqs {
      type uint32;
      description "No of throttled access reqs stats";
    }
    leaf throttled-timed-out-reqs {
      type uint32;
      description "No of access reqs that is throttled is timedout";
    }
    leaf throttled-dropped-reqs {
      type uint32;
      description "No of discarded access reqs";
    }
    leaf max-throttled-access-reqs {
      type uint32;
      description "Max throttled access reqs";
    }
    leaf currently-throttled-access-reqs {
      type uint32;
      description "No of currently throttled access reqs";
    }
    leaf authen-response-time {
      type uint32;
      description
        "Average response time for authentication
        requests";
    }
    leaf authen-transaction-successess {
      type uint32;
      description "Number of succeeded authentication transactions";
    }
    leaf authen-transaction-failure {
      type uint32;
      description "Number of failed authentication transactions";
    }
    leaf authen-unexpected-responses {
      type uint32;
      description "Number of unexpected authentication responses";
    }
    leaf authen-server-error-responses {
      type uint32;
      description "Number of server error authentication responses";
    }
    leaf authen-incorrect-responses {
      type uint32;
      description "Number of incorrect authentication responses";
    }
    leaf author-requests {
      type uint32;
      description "Number of access requests";
    }
    leaf author-request-timeouts {
      type uint32;
      description "Number of access packets timed out";
    }
    leaf author-response-time {
      type uint32;
      description
        "Average response time for authorization requests";
    }
    leaf author-transaction-successess {
      type uint32;
      description "Number of succeeded authorization transactions";
    }
    leaf author-transaction-failure {
      type uint32;
      description "Number of failed authorization transactions";
    }
    leaf author-unexpected-responses {
      type uint32;
      description "Number of unexpected authorization responses";
    }
    leaf author-server-error-responses {
      type uint32;
      description "Number of server error authorization responses";
    }
    leaf author-incorrect-responses {
      type uint32;
      description "Number of incorrect authorization responses";
    }
    leaf accounting-rtt {
      type uint32;
      units "millisecond";
      description "Round-trip time for accounting in milliseconds";
    }
    leaf accounting-requests {
      type uint32;
      description "Number of accounting requests";
    }
    leaf accounting-retransmits {
      type uint32;
      description "Number of retransmitted accounting requests";
    }
    leaf accounting-responses {
      type uint32;
      description "Number of accounting responses";
    }
    leaf bad-accounting-responses {
      type uint32;
      description "Number of bad accounting responses";
    }
    leaf bad-accounting-authenticators {
      type uint32;
      description "Number of bad accounting authenticators";
    }
    leaf pending-accounting-requets {
      type uint32;
      description "Number of pending accounting requests";
    }
    leaf accounting-timeouts {
      type uint32;
      description "Number of accounting packets timed-out";
    }
    leaf unknown-accounting-types {
      type uint32;
      description
        "Number of packets received with unknown type
        from accounting server";
    }
    leaf dropped-accounting-responses {
      type uint32;
      description "Number of accounting responses dropped";
    }
    leaf is-a-private-server {
      type boolean;
      description "Is a private server";
    }
    leaf total-test-auth-reqs {
      type uint32;
      description "Total auth test request";
    }
    leaf total-test-auth-timeouts {
      type uint32;
      description "Total auth test timeouts";
    }
    leaf total-test-auth-response {
      type uint32;
      description "Total auth test response";
    }
    leaf total-test-auth-pending {
      type uint32;
      description "Total auth test pending";
    }
    leaf total-test-acct-reqs {
      type uint32;
      description " Total acct test req";
    }
    leaf total-test-acct-timeouts {
      type uint32;
      description "Total acct test timeouts";
    }
    leaf total-test-acct-response {
      type uint32;
      description "Total acct test response";
    }
    leaf total-test-acct-pending {
      type uint32;
      description "Total acct test pending";
    }
    leaf throttled-acct-transactions {
      type uint32;
      description "No of throttled acct transactions stats";
    }
    leaf throttled-acct-timed-out-stats {
      type uint32;
      description
        "No of acct transaction that is throttled is
        timedout";
    }
    leaf throttled-acct-failures-stats {
      type uint32;
      description "No of acct discarded transaction";
    }
    leaf max-acct-throttled {
      type uint32;
      description "Max throttled acct transactions";
    }
    leaf throttleda-acct-transactions {
      type uint32;
      description "No of currently throttled acct transactions";
    }
    leaf acct-unexpected-responses {
      type uint32;
      description "Number of unexpected accounting responses";
    }
    leaf acct-server-error-responses {
      type uint32;
      description "Number of server error accounting responses";
    }
    leaf acct-incorrect-responses {
      type uint32;
      description "Number of incorrect accounting responses";
    }
    leaf acct-response-time {
      type uint32;
      description
        "Average response time for authentication
        requests";
    }
    leaf acct-transaction-successess {
      type uint32;
      description "Number of succeeded authentication transactions";
    }
    leaf acct-transaction-failure {
      type uint32;
      description "Number of failed authentication transactions";
    }
    leaf total-deadtime {
      type uint32;
      description "Total time of Server being in DEAD state";
    }
    leaf last-deadtime {
      type uint32;
      description
        "Time of Server being in DEAD state, after last
        UP";
    }
    leaf is-quarantined {
      type boolean;
      description
        "flag to indicate Server is quarantined or not
        (Automated TEST in progress)";
    }
    leaf group-name {
      type string;
      description "Server group name for private server";
    }
    leaf ip-address-xr {
      type string;
      description "IP address buffer";
    }
    leaf family {
      type string;
      description "IP address Family";
    }
  }
}
