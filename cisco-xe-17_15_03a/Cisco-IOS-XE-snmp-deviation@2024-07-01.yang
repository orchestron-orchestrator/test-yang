module Cisco-IOS-XE-snmp-deviation {
  yang-version 1.1;
  namespace "http://cisco.com/ns/yang/Cisco-IOS-XE-snmp-deviation";
  prefix ios-snmp-d;

  import Cisco-IOS-XE-native {
    prefix ios;
  }
  import Cisco-IOS-XE-snmp {
    prefix ios-snmp;
  }
  import cisco-semver {
    prefix cisco-semver;
  }

  organization
    "Cisco Systems";
  description
    "Cisco XE Native Deviation YANG module for IOS
     Copyright (c) 2020 by Cisco Systems, Inc.
     All rights reserved.";

  revision 2024-07-01 {
    description
      "Added SNMP trap-source Vlan range deviation";
    cisco-semver:module-version "1.0.0";
  }

  deviation "/ios:native/ios:snmp-server/ios-snmp:trap-source/ios-snmp:interface-choice/ios-snmp:Vlan/ios-snmp:Vlan" {
    deviate replace {
      type uint16 {
        range "1..4094";
      }
    }
  }
}
