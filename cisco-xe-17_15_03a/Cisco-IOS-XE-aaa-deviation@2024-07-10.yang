module Cisco-IOS-XE-aaa-deviation {
  yang-version 1.1;
  namespace "http://cisco.com/ns/yang/Cisco-IOS-XE-aaa-deviation";
  prefix ios-aaa-d;

  import Cisco-IOS-XE-native {
    prefix ios;
  }
  import Cisco-IOS-XE-aaa {
    prefix ios-aaa;
  }
  import cisco-semver {
    prefix cisco-semver;
  }

  organization
    "Cisco Systems";
  description
    "Cisco XE Native AAA Deviation YANG module for IOS
     Copyright (c) 2024 by Cisco Systems, Inc.
     All rights reserved.";

  revision 2024-07-10 {
    description
      "Added ip radius source-interface Vlan range deviation";
    cisco-semver:module-version "1.0.0";
  }

  deviation "/ios:native/ios:aaa/ios-aaa:group/ios-aaa:server/ios-aaa:radius/ios-aaa:ip/ios-aaa:radius/ios-aaa:source-interface/ios-aaa:interface-choice/ios-aaa:Vlan/ios-aaa:Vlan" {
    deviate replace {
      type uint16 {
        range "1..4094";
      }
    }
  }
}
