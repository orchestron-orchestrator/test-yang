module Cisco-IOS-XE-snmp {
  yang-version 1.1;
  namespace "http://cisco.com/ns/yang/Cisco-IOS-XE-snmp";
  prefix ios-snmp;

  import cisco-semver {
    prefix cisco-semver;
  }
  import Cisco-IOS-XE-types {
    prefix ios-types;
  }
  import Cisco-IOS-XE-interface-common {
    prefix ios-ifc;
  }
  import Cisco-IOS-XE-native {
    prefix ios;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Simple Network Management Protocol (SNMP) Yang model.
     Copyright (c) 2016-2020 by Cisco Systems, Inc.
     All rights reserved.";

  revision 2024-07-10 {
    description
      "- Added new encryption type leaf for the SNMP v3 users passwords
       - Added new privacy protocol grouping which supports encryption(0,6,7) type";
    cisco-semver:module-version "9.1.0";
  }
  revision 2024-07-01 {
    description
      "- Added support for snmp traps for mpls rfc ldp and traffic-eng
       - Changed deprecated nodes in or before 17.6 to obsolete
       - Added support for flow monitor configuration data
       - Added support for snmp and snmp-server commands
       - Added support for snmp MIB expression commands
       - Added model support for snmp-server trap authentication access-list failure
       - Added model support for snmp monitor response
       - Deprecated security-level-list and added security-level-list-config and security-level-list-context
       - Added model support for snmp-server subagent datastage timeout
       - Added model support for snmp MIB expression owner commands
       - Obsolete bgp traps that were deprecated before 17.9
       - Deprecated persist container and added persist-config container under snmp mib
       - Deprecated persist-enum leaf and introduced new leaves under persist-config
       - Added model support for snmp-server file-transfer access-group <> protocol <>
       - Added model support for snmp MIB expression owner value type";
    cisco-semver:module-version "9.0.0";
  }
  revision 2024-03-01 {
    description
      "- Added default exact value for match-node
       - Added default v1-default value for read-node
       - Added invalid value RO and RW for access-list-name node in community-config
       - Added leaf nhrp under mib container
       - Changed deprecated nodes in or before 17.6 to obsolete, removed relevant entries
       - Added support for snmp-server enable trap for LISP";
    cisco-semver:module-version "8.0.0";
  }
  revision 2022-11-01 {
    description
      "- changed the order of engineId and community config node
       - added support for SHA-2 snmp v3 user
       - Added support for snmp-server sub agent
       - Update yang-version to 1.1";
    cisco-semver:module-version "7.2.0";
  }
  revision 2022-07-01 {
    description
      "- Added support snmp-server frame relay trap";
    cisco-semver:module-version "7.1.0";
  }
  revision 2022-03-01 {
    description
      "- Added length constraint for leaf ipv6-acl in access-config
       - Added length constraint for leaf view in config-snmp-server-grouping
       - Added support snmp-server enable trap for tunnel
       - Deprecated snmp-bgp related configurations, now present in bgp yang model. obsolete invalid bgp-conf container";
    cisco-semver:module-version "7.0.0";
  }
  revision 2021-11-01 {
    description
      "- Added length constraint for leaf ipv6 in community-config
       - Added tailf:cli-flatten-container and tailf:cli-compact-syntax under flash container
       - Added leaf lowspace under flash container
       - Added leaf c3g under traps container
       - Added leaf LTE under traps container
       - Added leaf entity-sensor under traps container
       - Added leaf pfr under traps container
       - Added leaf count under subif container
       - Added leaf interval under subif container
       - Added container ip under traps container
       - Added container entity-perf under traps container
       - Added container entity-qfp under traps container
       - Added container diameter under traps container
       - Added container sdwan under traps container
       - Added container pimstdmib under traps container";
    cisco-semver:module-version "6.2.0";
  }
  revision 2021-07-01 {
    description
      "- Deprecated ospf and ospfv3 under SNMP traps configuration
       - Added support for bgp trap state-changes
       - Added support for bgp trap cbgp2
       - Added support for bgp trap threshold";
    cisco-semver:module-version "6.1.0";
  }
  revision 2021-03-01 {
    description
      "- moving version and security-level from annotation to yang file.
       - Added support for snmp link-status for ATM sub interface
       - Added interface Serial to use snmp grouping";
    cisco-semver:module-version "6.0.0";
  }
  revision 2020-11-01 {
    description
      "- Added support for community string encryption.
       - Marked existing wireless traps configuration containers as obsolete and introduced new leaves
       - Introduced new container for wired guest traps";
    cisco-semver:module-version "5.0.0";
  }
  revision 2020-07-01 {
    description
      "- Corrected range on packet size
       - Reapplied the change in key fields of snmp-server/host";
    cisco-semver:module-version "3.0.0";
  }
  revision 2020-03-01 {
    description
      "- Deprecated informs-traps-choice
       - Added support for IPV6 ACL in snmp group node
       - Deprecated access-node used in snmp group node
       - Deprecated ipv6 choice in config-access-grouping
       - Reverted the change in key fields of snmp-server/host";
    cisco-semver:module-version "2.0.0";
  }
  revision 2019-11-01 {
    description
      "- Fixed key fields of snmp-server/host
       - Added authentication and privacy config for snmp user and isis
       - Added smart licensing config";
    cisco-semver:module-version "1.1.0";
  }
  revision 2019-07-01 {
    description
      "Establish semantic version baseline";
    cisco-semver:module-version "1.0.0";
  }
  revision 2019-01-22 {
    description
      "Added leaf for App-hosting Gigabit Ethernet interface";
  }
  revision 2018-12-03 {
    description
      "Added pki option under snmp-server enable traps";
  }
  revision 2018-11-07 {
    description
      "Cleanup spelling errors in description statements";
  }
  revision 2018-11-06 {
    description
      "Added encrypted to snmp-server user";
  }
  revision 2018-09-04 {
    description
      "Added snmp traps enable for vdsl and adsl";
  }
  revision 2018-06-28 {
    description
      "Added must constraints for deleting vrf";
  }
  revision 2018-05-09 {
    description
      "Added auth md5 to snmp-server user";
  }
  revision 2017-11-27 {
    description
      "Added Change 25GE name";
  }
  revision 2017-11-14 {
    description
      "This revision has changes for new 40 and 100GE interface addition";
  }
  revision 2017-10-15 {
    description
      "This revision has changes for new 2gig interface addition";
  }
  revision 2017-10-06 {
    description
      "Move udp-port out of container trap-enable";
  }
  revision 2017-08-11 {
    description
      "This revision has changes for new 5gig and 25gig interfaces addition";
  }
  revision 2017-02-07 {
    description
      "Initial revision";
  }

  grouping config-priv-encryption-type-grouping {
    container priv-config {
      description
        "encryption parameters for the user";
      choice priv-option {
        description
          "encryption choice for the user";
        container aes {
          description
            "Use AES algorithm for encryption";
          presence "true";
          leaf algorithm {
            mandatory true;
            type enumeration {
              enum 128;
              enum 192;
              enum 256;
            }
          }
          uses config-encryption-type-grouping;
          leaf password {
            description
              "Authentication password for user";
            mandatory true;
            type string;
          }
          uses config-access-grouping;
        }
        container des {
          description
            "Use 56 bit DES algorithm for encryption";
          presence "true";
          uses config-encryption-type-grouping;
          leaf password {
            description
              "Authentication password for user";
            mandatory true;
            type string;
          }
          uses config-access-grouping;
        }
        container des3 {
          description
            "Use 168 bit 3DES algorithm for encryption";
          presence "true";
          uses config-encryption-type-grouping;
          leaf password {
            description
              "Authentication password for user";
            mandatory true;
            type string;
          }
          uses config-access-grouping;
        }
      }
    }
  }

  grouping config-encryption-type-grouping {
    leaf encryption {
      description
        "Encryption method of password";
      type enumeration {
        enum 0;
        enum 6;
        enum 7;
      }
    }
  }

  grouping config-access-grouping {
    container access-config {
      description
        "specify an access-list associated with this group";
      leaf ipv6-acl {
        description
          "Specify IPv6 Named Access-List";
        type string {
          length "1..194";
        }
      }
      choice access-option {
        description
          "access-list associated with this group";
        leaf standard-acl {
          description
            "Standard IP Access-list allowing access with this community string";
          type uint32 {
            range "1..99";
          }
        }
        leaf acl-name {
          description
            "Access-list name";
          type string {
            length "1..183";
          }
        }
        leaf ipv6 {
          description
            "OBSOLETE Specify IPv6 Named Access-List";
          status obsolete;
          type string;
        }
      }
    }
  }

  grouping config-priv-grouping {
    container priv-config {
      description
        "encryption parameters for the user";
      choice priv-option {
        description
          "encryption choice for the user";
        container aes {
          description
            "Use AES algorithm for encryption";
          presence "true";
          leaf algorithm {
            mandatory true;
            type enumeration {
              enum 128;
              enum 192;
              enum 256;
            }
          }
          leaf password {
            description
              "Authentication password for user";
            mandatory true;
            type string;
          }
          uses config-access-grouping;
        }
        container des {
          description
            "Use 56 bit DES algorithm for encryption";
          presence "true";
          leaf password {
            description
              "Authentication password for user";
            mandatory true;
            type string;
          }
          uses config-access-grouping;
        }
        container des3 {
          description
            "Use 168 bit 3DES algorithm for encryption";
          presence "true";
          leaf password {
            description
              "Authentication password for user";
            mandatory true;
            type string;
          }
          uses config-access-grouping;
        }
      }
    }
  }

  grouping config-auth-grouping {
    container auth {
      status obsolete;
      leaf authpass {
        status obsolete;
        description
          "OBSOLETE authentication password for user";
        type string;
      }
      container priv {
        description
          "encryption parameters for the user";
        status obsolete;
        container aes {
          description
            "Use AES algorithm for encryption";
          status obsolete;
          container algo128 {
            description
              "Use 128 bit AES algorithm for encryption";
            status obsolete;
            container privpass {
              status obsolete;
              leaf privpass {
                status obsolete;
                description
                  "OBSOLETE privacy password for user";
                type string;
              }
              leaf access {
                description
                  "OBSOLETE Access-list name";
                status obsolete;
                type string;
              }
            }
          }
        }
      }
    }
  }

  grouping config-host-attribute-grouping {
    container trap-enable {
      leaf aaa_server {
        description
          "Allow SNMP AAA traps";
        type empty;
      }
      leaf alarms {
        description
          "Allow SNMP alarms traps";
        type empty;
      }
      leaf atm {
        description
          "Allow SNMP atm traps";
        type empty;
      }
      leaf bfd {
        description
          "Allow SNMP BFD traps";
        type empty;
      }
      leaf bgp {
        description
          "Allow BGP state change traps";
        type empty;
      }
      leaf bstun {
        description
          "Allow bstun event traps";
        type empty;
      }
      leaf bulkstat {
        description
          "Allow Data-Collection-MIB traps";
        type empty;
      }
      leaf call-home {
        description
          "Allow SNMP CISCO-CALLHOME-MIB traps";
        type empty;
      }
      leaf casa {
        description
          "Allow casa event traps";
        type empty;
      }
      leaf cef {
        description
          "Allows cef traps";
        type empty;
      }
      leaf cnpd {
        description
          "Allow NBAR Protocol Discovery traps";
        type empty;
      }
      leaf config {
        description
          "Allow SNMP config traps";
        type empty;
      }
      leaf config-copy {
        description
          "Allow SNMP config-copy traps";
        type empty;
      }
      leaf config-ctid {
        description
          "Allow SNMP config-ctid traps";
        type empty;
      }
      leaf cpu {
        description
          "Allow cpu related traps";
        type empty;
      }
      leaf dhcp {
        description
          "Allow dhcp traps";
        type empty;
      }
      leaf dlsw {
        description
          "Allow dlsw traps";
        type empty;
      }
      leaf ds1 {
        description
          "Allow SNMP ds1 traps";
        type empty;
      }
      leaf dsp {
        description
          "Allow SNMP DSP traps";
        type empty;
      }
      leaf dspu {
        description
          "Allow dspu event traps";
        type empty;
      }
      leaf eigrp {
        description
          "Allow SNMP EIGRP traps";
        type empty;
      }
      leaf entity {
        description
          "Allow SNMP entity traps";
        type empty;
      }
      leaf entity-diag {
        description
          "Allow SNMP CISCO-ENTITY-DIAG-MIB traps";
        type empty;
      }
      leaf entity-qfp {
        description
          "Allow SNMP CISCO-ENTITY-QFP-MIB traps";
        type empty;
      }
      leaf entity-state {
        description
          "Allow ENTITY-STATE-MIB traps";
        type empty;
      }
      leaf ethernet-cfm {
        description
          "Allow SNMP Ethernet CFM traps";
        type empty;
      }
      leaf evc {
        description
          "Allow SNMP EVC traps";
        type empty;
      }
      leaf event-manager {
        description
          "Allow SNMP Embedded Event Manager traps";
        type empty;
      }
      leaf firewall {
        description
          "Allow SNMP Firewall traps";
        type empty;
      }
      leaf flash {
        description
          "Allow SNMP FLASH traps";
        type empty;
      }
      leaf flowmon {
        description
          "Allow SNMP flow monitor notifications";
        type empty;
      }
      leaf frame-relay {
        description
          "Allow SNMP frame-relay traps";
        type empty;
      }
      leaf fru-ctrl {
        description
          "Allow entity FRU control traps";
        type empty;
      }
      leaf gdoi {
        description
          "Allows gdoi traps";
        type empty;
      }
      leaf hsrp {
        description
          "Allow SNMP HSRP traps";
        type empty;
      }
      leaf iplocalpool {
        description
          "Allow SNMP IP Local Pool traps";
        type empty;
      }
      leaf ipmulticast {
        description
          "Allow SNMP ipmulticast traps";
        type empty;
      }
      leaf ipsec {
        description
          "Allow SNMP IPsec traps";
        type empty;
      }
      leaf ipsla {
        description
          "Allow SNMP Host IP SLA traps";
        type empty;
      }
      leaf isakmp {
        description
          "Allow SNMP ISAKMP traps";
        type empty;
      }
      leaf isg-mib {
        description
          "Allow SNMP isgmib traps";
        type empty;
      }
      leaf isis {
        description
          "Allow IS-IS traps";
        type empty;
      }
      leaf l2tun-pseudowire-status {
        description
          "Allow SNMP L2 pseudowire status traps";
        type empty;
      }
      leaf l2tun-session {
        description
          "Allow SNMP L2 session traps";
        type empty;
      }
      leaf license {
        description
          "Allow license traps";
        type empty;
      }
      leaf memory {
        description
          "Allow SNMP Mempool traps";
        type empty;
      }
      leaf mpls-fast-reroute {
        description
          "Allow SNMP MPLS traffic engineering fast reroute traps";
        type empty;
      }
      leaf mpls-ldp {
        description
          "Allow SNMP MPLS label distribution protocol traps";
        type empty;
      }
      leaf mpls-traffic-eng {
        description
          "Allow SNMP MPLS traffic engineering traps";
        type empty;
      }
      leaf mpls-vpn {
        description
          "Allow SNMP MPLS Virtual Private Network traps";
        type empty;
      }
      leaf msdp {
        description
          "Allow SNMP MSDP traps";
        type empty;
      }
      leaf mvpn {
        description
          "Allow Multicast Virtual Private Network traps";
        type empty;
      }
      leaf nhrp {
        description
          "Allow SNMP NHRP traps";
        type empty;
      }
      leaf ospf {
        description
          "Allow OSPF traps";
        type empty;
      }
      leaf ospfv3 {
        description
          "Allow OSPFv3 traps";
        type empty;
      }
      leaf pfr {
        description
          "Allow SNMP PfR traps";
        type empty;
      }
      leaf pim {
        description
          "Allow SNMP PIM traps";
        type empty;
      }
      leaf pw-vc {
        description
          "Allow SNMP Pseudowire VC traps";
        type empty;
      }
      leaf resource-policy {
        description
          "Enable CISCO-ERM-MIB notifications";
        type empty;
      }
      leaf rf {
        description
          "Allow all SNMP traps defined in CISCO-RF-MIB";
        type empty;
      }
      leaf rsrb {
        description
          "Allow rsrb event traps";
        type empty;
      }
      leaf rsvp {
        description
          "Allow RSVP flow change traps";
        type empty;
      }
      leaf sdlc {
        description
          "Allow sdlc event traps";
        type empty;
      }
      leaf sdllc {
        description
          "Allow sdllc event traps";
        type empty;
      }
      leaf snmp {
        description
          "Allow SNMP-type notifications";
        type empty;
      }
      leaf sonet {
        description
          "Allow SNMP SONET traps";
        type empty;
      }
      leaf srp {
        description
          "Allow SRP protocol traps";
        type empty;
      }
      leaf stun {
        description
          "Allow stun event traps";
        type empty;
      }
      leaf syslog {
        description
          "Allow SNMP syslog traps";
        type empty;
      }
      leaf trustsec-sxp {
        description
          "Allow SNMP CISCO-TRUSTSEC-SXP-MIB traps";
        type empty;
      }
      leaf tty {
        description
          "Allow TCP connection traps";
        type empty;
      }
      leaf voice {
        description
          "Allow SNMP Voice traps";
        type empty;
      }
      leaf vrfmib {
        description
          "Allow SNMP vrfmib traps";
        type empty;
      }
      leaf vrrp {
        description
          "Allow SNMP vrrp traps";
        type empty;
      }
      leaf x25 {
        description
          "Allow x25 event traps";
        type empty;
      }
    }
  }

  grouping snmp-server-trap-bgp-grouping {
    container state-changes {
      status obsolete;
      description
        "State change traps (OBSOLETE - please use snmp configuration in Cisco-IOS-XE-bgp.yang)";
      leaf-list suboptions {
        status obsolete;
        max-elements 3;
        type enumeration {
          enum all {
            description
              "CISCO specific trap for all fsm state changes (OBSOLETE - please use snmp configuration in Cisco-IOS-XE-bgp.yang)";
          }
          enum backward-trans {
            description
              "CISCO specific trap for backward transition (OBSOLETE - please use snmp configuration in Cisco-IOS-XE-bgp.yang)";
          }
          enum limited {
            description
              "Trap for standard backward transition and established (OBSOLETE - please use snmp configuration in Cisco-IOS-XE-bgp.yang)";
          }
          enum updown-limited {
            description
              "Like limited, but only session goes to Established or comes from Established state (OBSOLETE - please use snmp configuration in Cisco-IOS-XE-bgp.yang)";
          }
        }
      }
      leaf enable-all-traps {
        status obsolete;
        description
          "Traps for FSM state changes (OBSOLETE - please use snmp configuration in Cisco-IOS-XE-bgp.yang)";
        type empty;
      }
      must '(enable-all-traps and not (suboptions)) or (not (enable-all-traps) and not (suboptions)) or (not (enable-all-traps) and suboptions)' {
        error-message "Cannot configure enable-all-traps and a specific trap. In order to enable a specific trap, delete enable-all-traps. Likewise, in order to configure enable-all-traps, delete all specific traps";
      }
    }
    leaf cbgp2 {
      status obsolete;
      description
        "Enable BGP MIBv2 traps (OBSOLETE - please use snmp configuration in Cisco-IOS-XE-bgp.yang)";
      type empty;
    }
    container threshold {
      status obsolete;
      description
        "Traps for threshold events (OBSOLETE - please use snmp configuration in Cisco-IOS-XE-bgp.yang)";
      leaf prefix {
        status obsolete;
        description
          "CISCO specific trap for prefix threshold events (OBSOLETE - please use snmp configuration in Cisco-IOS-XE-bgp.yang)";
        type empty;
      }
    }
  }

  grouping config-snmp-server-grouping {
    leaf chassis-id {
      description
        "String to uniquely identify this chassis";
      type string;
    }
    container engineID {
      description
        "Configure a local or remote SNMPv3 engineID";
      leaf local {
        description
          "engineID of the local agent";
        type string {
          length "10..64";
          pattern '[0-9a-fA-F]*';
        }
      }
      container remote-conf {
        description
          "engineID of the remote agent";
        list host-list {
          key "ip-address";
          leaf ip-address {
            description
              "Hostname or IP/IPv6 address of SNMP notification host";
            type ios-types:host-type;
          }
          uses engine-id-group;
        }
        list host-vrf-list {
          key "ip-address";
          leaf ip-address {
            description
              "Hostname or IP/IPv6 address of SNMP notification host";
            type ios-types:host-type;
          }
          uses vrf-engine-id;
        }
        list host-udp-list {
          key "ip-address";
          leaf ip-address {
            description
              "Hostname or IP/IPv6 address of SNMP notification host";
            type ios-types:host-type;
          }
          uses udp-port-engine;
        }
        list host-udp-vrf-list {
          key "ip-address";
          leaf ip-address {
            description
              "Hostname or IP/IPv6 address of SNMP notification host";
            type ios-types:host-type;
          }
          uses udp-port-vrf-engine;
        }
      }
      container remote {
        status obsolete;
      }
    }
    list community-config {
      description
        "Enable SNMP; set community string and access privs";
      key "name";
      leaf name {
        type string;
      }
      leaf encryption {
        description
          "Specifies an encryption type";
        type enumeration {
          enum 0;
          enum 6;
          enum 7;
        }
      }
      leaf view {
        description
          "Restrict this community to a named MIB view";
        type string {
          length "1..214";
        }
      }
      leaf permission {
        when '../name';
        type enumeration {
          enum ro;
          enum rw;
        }
        default "ro";
      }
      leaf ipv6 {
        description
          "Specify IPv6 Named Access-List";
        type string {
          length "1..219";
        }
      }
      leaf access-list-name {
        description
          "Access-list name";
        type ios-types:std-acl-type;
      }
    }
    list community {
      status obsolete;
      description
        "Enable SNMP; set community string and access privs";
      key "name";
      leaf name {
        status obsolete;
        type string;
      }
      leaf view {
        status obsolete;
        description
          "OBSOLETE Restrict this community to a named MIB view";
        type string;
      }
      choice access-choice {
        leaf RO {
          status obsolete;
          description
            "OBSOLETE Read-only access with this community string";
          type empty;
        }
        leaf RW {
          status obsolete;
          description
            "OBSOLETE Read-write access with this community string";
          type empty;
        }
      }
      leaf ipv6 {
        status obsolete;
        description
          "OBSOLETE Specify IPv6 Named Access-List";
        type string;
      }
      leaf access-list-name {
        status obsolete;
        description
          "OBSOLETE Access-list name";
        type ios-types:std-acl-type;
      }
    }
    leaf contact {
      description
        "Text for mib object sysContact";
      type string;
    }
    list context {
      description
        "Create/Delete a context apart from default";
      key "name";
      leaf name {
        type string;
      }
    }
    container dbal {
      description
        "SNMP database access layer";
      leaf cache {
        description
          "SNMP DBAL cache";
        type boolean;
        default "false";
      }
    }
    container enable {
      description
        "Enable SNMP Traps or Informs";
      container enable-choice {
        container logging {
          description
            "Enable SNMP logging";
          leaf getop {
            description
              "Enable SNMP GET Operation logging";
            type boolean;
            default "false";
          }
          leaf setop {
            description
              "Enable SNMP SET Operation logging";
            type boolean;
            default "true";
          }
        }
        leaf informs {
          description
            "Enable SNMP Informs";
          type empty;
        }
        container traps {
          description
            "Enable SNMP Traps";
          presence "true";
          leaf aaa_server {
            description
              "Enable SNMP AAA Server traps";
            type empty;
          }
          leaf vdsl2line {
            description
              "Enable VDSL2 Line-MIB traps";
            type empty;
          }
          leaf adslline {
            description
              "Enable ADSL Line-MIB traps";
            type empty;
          }
          container trustsec-sxp {
            description
              "Enable SNMP CISCO-TRUSTSEC-SXP-MIB traps";
            presence "true";
            leaf binding-conflict {
              type empty;
            }
            leaf binding-err {
              type empty;
            }
            leaf binding-expn-fail {
              type empty;
            }
            leaf conn-config-err {
              type empty;
            }
            leaf conn-down {
              type empty;
            }
            leaf conn-srcaddr-err {
              type empty;
            }
            leaf conn-up {
              type empty;
            }
            leaf msg-parse-err {
              type empty;
            }
            leaf oper-nodeid-change {
              type empty;
            }
          }
          container vswitch {
            description
              "Enable SNMP Virtual Switch notifications";
            presence "true";
            container dual-active {
              description
                "Enable SNMP Virtual Switch (Dual Active) notification";
              presence "true";
              leaf vsl {
                description
                  "Enable SNMP Virtual Switch Link (VSL) notification";
                type empty;
              }
            }
          }
          container trustsec-server {
            description
              "Enable SNMP CISCO-TRUSTSEC-SERVER-MIB traps";
            presence "true";
            container radius-server {
              description
                "Enable ctsvNoRadiusServerNotif notification";
              presence "true";
              leaf provision-secret {
                description
                  "Enable ctsvNoProvisionSecretNotif notification";
                type empty;
              }
            }
          }
          container trustsec {
            description
              "Enable SNMP CISCO-TRUSTSEC-MIB traps";
            presence "true";
            container authz-file-error {
              description
                "Enable ctsAuthzCacheFileErrNotif notifications";
              presence "true";
              container cache-file-error {
                description
                  "Enable ctsCacheFileAccessErrNotif notifications";
                presence "true";
                container keystore-file-error {
                  description
                    "Enable ctsSwKeystoreFileErrNotif notifications";
                  presence "true";
                  container keystore-sync-fail {
                    description
                      "Enable ctsSwKeystoreSyncFailNotif notifications";
                    presence "true";
                    container random-number-fail {
                      description
                        "Enable ctsSapRandonNumberFailNotif notifications";
                      presence "true";
                      leaf src-entropy-fail {
                        description
                          "Enable ctsSrcEntropyFailNotif notifications";
                        type empty;
                      }
                    }
                  }
                }
              }
            }
          }
          container trustsec-interface {
            description
              "Enable SNMP CISCO-TRUSTSEC-INTERFACE-MIB traps";
            presence "true";
            container unauthorized {
              description
                "Enable ctsiIfUnauthorizedNotifEnable trap";
              presence "true";
              container sap-fail {
                description
                  "Enable ctsiIfSapNegotiationFailNotif trap";
                presence "true";
                container authc-fail {
                  description
                    "Enable ctsiIfAuthenticationFailNotif trap";
                  presence "true";
                  container supplicant-fail {
                    description
                      "Enable ctsiIfAddSupplicantFailNotif trap";
                    presence "true";
                    leaf authz-fail {
                      description
                        "Enable ctsiAuthorizationFailNotif trap";
                      type empty;
                    }
                  }
                }
              }
            }
          }
          container trustsec-policy {
            description
              "Enable SNMP CISCO-TRUSTSEC-POLICY-MIB traps";
            presence "true";
            container peer-policy-updated {
              description
                "Enable ctspPeerPolicyUpdatedNotif notifications";
              presence "true";
              leaf authz-sgacl-fail {
                description
                  "Enable ctspAuthorizationSgaclFailNotif notifications";
                type empty;
              }
            }
          }
          container ospfv3 {
            status deprecated;
            description
              "Enable OSPFv3 traps";
            leaf state-change {
              status deprecated;
              description
                "State change traps";
              type empty;
            }
            leaf errors {
              status deprecated;
              description
                "Error traps";
              type empty;
            }
          }
          container ike {
            description
              "Enable IKE traps";
            container policy {
              description
                "Enable IKE Policy traps";
              leaf add {
                description
                  "Enable IKE Policy add trap";
                type empty;
              }
              leaf delete {
                description
                  "Enable IKE Policy delete trap";
                type empty;
              }
            }
            container tunnel {
              description
                "Enable IKE Tunnel traps";
              leaf start {
                description
                  "Enable IKE Tunnel start trap";
                type empty;
              }
              leaf stop {
                description
                  "Enable IKE Tunnel stop trap";
                type empty;
              }
            }
          }
          leaf pki {
            description
              "Enable SNMP PKI Traps";
            type empty;
          }
          leaf local-auth {
            description
              "Enable SNMP local auth traps";
            type empty;
          }
          container alarms {
            description
              "Enable SNMP alarms traps";
            presence "true";
            leaf alarm-type {
              type union {
                type uint8 {
                  range "1..4";
                }
                type enumeration {
                  enum critical;
                  enum informational;
                  enum major;
                  enum minor;
                }
              }
            }
          }
          container atm {
            description
              "Enable SNMP atm traps";
            container pvc {
              description
                "Enable SNMP atm pvc traps";
              presence "true";
              container extension {
                description
                  "Enable SNMP atm pvc extension traps";
                leaf down {
                  description
                    "Enable SNMP atm pvc extended down trap";
                  type empty;
                }
                leaf up {
                  description
                    "Enable SNMP atm pvc extended up traps";
                  type empty;
                }
                leaf mibversion {
                  description
                    "Extension MIB version to be used";
                  type enumeration {
                    enum 1;
                    enum 2;
                  }
                }
                container oam {
                  description
                    "Enable SNMP atm pvc extended oam trap";
                  container failure {
                    description
                      "Enable SNMP atm pvc extended any oam failure trap";
                    leaf loopback {
                      description
                        "Enable SNMP atm pvc extended oam loopback failure trap";
                      type empty;
                    }
                  }
                }
              }
              leaf interval {
                description
                  "minimum period between successive traps";
                type uint16 {
                  range "1..3600";
                }
              }
              leaf fail-interval {
                description
                  "minimum period for storing the failed timestamp";
                type uint16 {
                  range "0..3600";
                }
              }
            }
            container subif {
              description
                "Enable SNMP atm subinterface traps";
              presence "true";
              leaf interval {
                description
                  "Interval duration in which to limit the number of traps sent";
                type uint16 {
                  range "0..3600";
                }
              }
              leaf count {
                description
                  "Maximum number of traps sent per interval";
                type uint16 {
                  range "1..1000";
                }
              }
            }
          }
          leaf authenticate-fail {
            description
              "Enable SNMP 802.11 Authentication Fail Trap";
            type empty;
          }
          container auth-framework {
            presence "true";
            leaf sec-violation {
              type empty;
            }
          }
          leaf bfd {
            type empty;
          }
          container bgp-conf {
            status obsolete;
            leaf cbgp2 {
              status obsolete;
              description
                "Enable BGP MIBv2 traps";
              type empty;
            }
          }
          container bgp-traps {
            status obsolete;
            description
              "Enable BGP traps (OBSOLETE - please use snmp configuration in Cisco-IOS-XE-bgp.yang)";
            presence "true";
            uses snmp-server-trap-bgp-grouping;
          }
          leaf bgp {
            status obsolete;
            description
              "Allow BGP state change traps (OBSOLETE)";
            type empty;
          }
          container bridge {
            presence "true";
            leaf newroot {
              type empty;
            }
            leaf topologychange {
              type empty;
            }
          }
          leaf bstun {
            description
              "Enable SNMP BSTUN traps";
            type empty;
          }
          container bulkstat {
            description
              "Enable Data-Collection-MIB Collection notifications";
            presence "true";
            leaf collection {
              description
                "Enable Data-Collection-MIB Collection notifications";
              type empty;
            }
            leaf transfer {
              description
                "Enable Data-Collection-MIB Transfer notifications";
              type empty;
            }
          }
          container call-home {
            description
              "Enable CISCO-CALLHOME-MIB traps";
            presence "true";
            leaf message-send-fail {
              type empty;
            }
            leaf server-fail {
              type empty;
            }
          }
          leaf c2900 {
            description
              "Enable SNMP c2900 traps";
            type empty;
          }
          leaf c3g {
            description
              "Allow SNMP c3g traps";
            type empty;
          }
          container c6kxbar {
            description
              "Enable SNMP CISCO-CAT6K-CROSSBAR-MIB traps";
            presence "true";
            leaf intbus-crcexcd {
              description
                "Enable SNMP cc6kxbarIntBusCRCErrExcdNotif notification";
              type empty;
            }
            leaf intbus-crcrcvrd {
              description
                "Enable SNMP cc6kxbarIntBusCRCErrRcvrdNotif notification";
              type empty;
            }
            leaf swbus {
              description
                "Enable SNMP cc6kxbarSwBusStatusChangeNotif notification";
              type empty;
            }
          }
          leaf casa {
            description
              "Enable SNMP casa traps";
            type empty;
          }
          leaf ccme {
            type empty;
          }
          container cef {
            leaf resource-failure {
              type empty;
            }
            leaf peer-state-change {
              type empty;
            }
            leaf peer-fib-state-change {
              type empty;
            }
            leaf inconsistency {
              type empty;
            }
          }
          leaf cluster {
            description
              "Enable Cluster traps";
            type empty;
          }
          leaf channel {
            description
              "Enable SNMP channel traps";
            type empty;
          }
          leaf chassis {
            description
              "Enable SNMP chassis traps";
            type empty;
          }
          leaf cnpd {
            description
              "Enable NBAR Protocol Discovery traps";
            type empty;
          }
          leaf config {
            description
              "Enable SNMP config traps";
            type empty;
          }
          leaf copy-config {
            description
              "Enable SNMP copy-config traps";
            type empty;
          }
          leaf config-copy {
            description
              "Enable SNMP config-copy traps";
            type empty;
          }
          leaf config-ctid {
            type empty;
          }
          container cpu {
            description
              "Allow cpu related traps";
            presence "true";
            leaf threshold {
              description
                "Allow CPU utilization threshold violation traps";
              type empty;
            }
          }
          leaf cpu_threshold {
            description
              "Enables CPU threshold notifications";
            type empty;
          }
          container csg {
            description
              "Enable SNMP CSG traps";
            presence "true";
            leaf agent {
              description
                "Enable SNMP Agent Server traps";
              type empty;
            }
            leaf database {
              description
                "Enable SNMP CSG database traps";
              type empty;
            }
            leaf quota-server {
              description
                "Enable SNMP Quota Server traps";
              type empty;
            }
          }
          leaf dial {
            description
              "Enable SNMP dial control traps";
            type empty;
          }
          leaf director {
            description
              "Enable SNMP Distributed Director traps";
            type empty;
          }
          leaf dlsw {
            description
              "Enable SNMP dlsw traps";
            type empty;
          }
          leaf deauthenticate {
            description
              "Enable SNMP 802.11 Deauthentication Trap";
            type empty;
          }
          leaf disassociate {
            description
              "Enable SNMP 802.11 Disassociation Trap";
            type empty;
          }
          leaf dnis {
            description
              "Enable SNMP DNIS traps";
            type empty;
          }
          leaf dot11-qos {
            description
              "Enable SNMP 802.11 QoS Change Trap";
            type empty;
          }
          container diameter {
            description
              "Enable DIAMETER notifications";
            presence "true";
            leaf peer-down {
              description
                "Allow Diameter peer-down traps";
              type empty;
            }
            leaf peer-up {
              description
                "Allow Diameter peer-up traps";
              type empty;
            }
            leaf permanent-failure {
              description
                "Allow Diameter Permanent Failure traps";
              type empty;
            }
            leaf protocol-error {
              description
                "Allow Diameter Protocol Error traps";
              type empty;
            }
            leaf transient-failure {
              description
                "Allow Diameter Transient Failure traps";
              type empty;
            }
          }
          container dot1x {
            leaf auth-fail-vlan {
              type empty;
            }
            leaf guest-vlan {
              type empty;
            }
            leaf no-auth-fail-vlan {
              type empty;
            }
            leaf no-guest-vlan {
              type empty;
            }
          }
          leaf ds0-busyout {
            description
              "Enable ds0-busyout traps";
            type empty;
          }
          leaf ds1 {
            description
              "Enable SNMP DS1 traps";
            type empty;
          }
          leaf ds1-loopback {
            description
              "Enable ds1-loopback traps";
            type empty;
          }
          leaf ds3 {
            description
              "Enable SNMP DS3 traps";
            type empty;
          }
          container dsp {
            description
              "Enable SNMP dsp traps";
            presence "true";
            leaf card-status {
              description
                "Enable SNMP card status of dsp traps";
              type empty;
            }
            leaf oper-state {
              type empty;
            }
          }
          leaf dhcp {
            description
              "Enable SNMP dhcp traps";
            type empty;
          }
          leaf eigrp {
            description
              "Enable SNMP EIGRP traps";
            type empty;
          }
          container energywise {
            presence "true";
            leaf event-occured {
              type empty;
            }
            leaf level-change {
              type empty;
            }
            leaf neighbor-added {
              type empty;
            }
            leaf neighbor-deleted {
              type empty;
            }
          }
          leaf entity {
            description
              "Enable SNMP entity traps";
            type empty;
          }
          container entity-diag {
            description
              "Enable SNMP CISCO-ENTITY-DIAG-MIB traps";
            presence "true";
            leaf boot-up-fail {
              description
                "Enable SNMP ceDiagBootUpFailedNotif traps";
              type empty;
            }
            leaf hm-test-recover {
              description
                "Enable SNMP ceDiagHMTestRecoverNotif traps";
              type empty;
            }
            leaf hm-thresh-reached {
              description
                "Enable SNMP ceDiagHMThresholdReachedNotif traps";
              type empty;
            }
            leaf scheduled-test-fail {
              description
                "Enable SNMP ceDiagScheduledTestFailedNotif traps";
              type empty;
            }
          }
          leaf entity-sensor {
            description
              "Enable SNMP entity-sensor traps";
            type empty;
          }
          leaf entity-state {
            description
              "Allow SNMP entity-state traps";
            type empty;
          }
          container entity-perf {
            description
              "Enable SNMP ENTITY-PERF traps";
            presence "true";
            leaf throughput-notif {
              description
                "Enable ENTITY PERFORMANCE MIB throughput traps";
              type empty;
            }
          }
          container entity-qfp {
            description
              "Enable SNMP ENTITY-QFP notifications";
            presence "true";
            leaf mem-res-thresh {
              description
                "Enable SNMP ENTITY-QFP MEM-RES-THRESH notifications";
              type empty;
            }
            leaf throughput-notif {
              description
                "Enable SNMP ENTITY-QFP THROUGHPUT-NOTIF notifications";
              type empty;
            }
          }
          container envmon {
            description
              "Enable SNMP environmental monitor traps";
            presence "true";
            leaf fan {
              type empty;
            }
            leaf shutdown {
              type empty;
            }
            leaf supply {
              type empty;
            }
            leaf temperature {
              type empty;
            }
            leaf status {
              type empty;
            }
          }
          container errdisable {
            description
              "Enable SNMP errdisable notifications";
            presence "true";
            leaf notification-rate {
              description
                "Number of notifications per minute";
              type uint16 {
                range "0..10000";
              }
            }
          }
          leaf ether-oam {
            type empty;
          }
          container ethernet {
            container cfm {
              leaf alarm {
                description
                  "Enable SNMP Ethernet CFM fault alarm trap";
                type empty;
              }
              container cc {
                presence "true";
                leaf config {
                  type empty;
                }
                leaf cross-connect {
                  type empty;
                }
                leaf loop {
                  type empty;
                }
                leaf mep-down {
                  type empty;
                }
                leaf mep-up {
                  type empty;
                }
              }
              container crosscheck {
                presence "true";
                leaf mep-missing {
                  type empty;
                }
                leaf mep-unknown {
                  type empty;
                }
                leaf service-up {
                  type empty;
                }
              }
            }
            container evc {
              description
                "Enable SNMP Ethernet EVC traps";
              presence "true";
              leaf create {
                description
                  "Enable SNMP Ethernet EVC create traps";
                type empty;
              }
              leaf delete {
                description
                  "Enable SNMP Ethernet EVC delete traps";
                type empty;
              }
              leaf status {
                description
                  "Enable SNMP Ethernet EVC status traps";
                type empty;
              }
            }
          }
          leaf event-manager {
            description
              "Enable SNMP Embedded Event Manager traps";
            type empty;
          }
          container firewall {
            presence "true";
            leaf serverstatus {
              type empty;
            }
          }
          container flash {
            description
              "Enable SNMP FLASH notifications";
            presence "true";
            leaf insertion {
              description
                "Enable SNMP Flash Insertion notifications";
              type empty;
            }
            leaf removal {
              description
                "Enable SNMP Flash Removal notifications";
              type empty;
            }
            leaf lowspace {
              description
                "Enable SNMP Flash Lowspace notifications";
              type empty;
            }
          }
          leaf flowmon {
            description
              "Enable SNMP flowmon notifications";
            type empty;
          }
          container flex-links {
            description
              "Enable SNMP FLEX Links traps";
            presence "true";
            leaf status {
              description
                "Enable SNMP FLEX Links status change traps";
              type empty;
            }
          }
          container frame-relay-config {
            container only-frame-relay {
              leaf frame-relay {
                type empty;
              }
            }
            container frame-relay-options {
              container frame-relay {
                container multilink {
                  description
                    "Enable MFR traps";
                  leaf bundle-mismatch {
                    description
                      "Enable MFR trap for inconsistent bundle event";
                    type empty;
                  }
                }
                container subif-configs {
                  description
                    "Enable SNMP frame-relay subinterface traps";
                  leaf subif {
                    type empty;
                  }
                  leaf interval {
                    description
                      "Interval duration in which to limit the number of traps sent";
                    when '../subif';
                    type uint16 {
                      range "1..3600";
                    }
                    default "10";
                  }
                  leaf count {
                    description
                      "Maximum number of traps sent per interval";
                    when '../subif';
                    type uint16 {
                      range "1..1000";
                    }
                    default "10";
                  }
                }
              }
            }
          }
          container frame-relay {
            status deprecated;
            description
              "Enable SNMP frame-relay traps";
            presence "true";
            container multilink {
              status deprecated;
              description
                "Enable MFR traps";
              leaf bundle-mismatch {
                status deprecated;
                description
                  "Enable MFR trap for inconsistent bundle event";
                type empty;
              }
            }
            container subif {
              status deprecated;
              description
                "Enable SNMP frame-relay subinterface traps";
              presence "true";
              leaf count {
                status deprecated;
                description
                  "Maximum number of traps sent per interval";
                type uint16 {
                  range "1..1000";
                }
                default "10";
              }
              leaf interval {
                status deprecated;
                description
                  "Interval duration in which to limit the number of traps sent";
                type uint16 {
                  range "1..3600";
                }
                default "10";
              }
            }
          }
          leaf fru-ctrl {
            description
              "Enable SNMP entity FRU control traps";
            type empty;
          }
          leaf gatekeeper {
            description
              "Enable SNMP gatekeeper traps";
            type empty;
          }
          leaf hsrp {
            description
              "Enable SNMP HSRP traps";
            type empty;
          }
          leaf icsudsu {
            description
              "Enable SNMP ICSUDSU traps";
            type empty;
          }
          leaf ima {
            description
              "Enable SNMP ATM IMA traps";
            type empty;
          }
          container ip {
            description
              "Enable SNMP IP traps";
            container local {
              description
                "Enable SNMP IP LOCAL traps";
              leaf pool {
                description
                  "Enable SNMP IP LOCAL POOL traps";
                type empty;
              }
            }
          }
          leaf ipmobile {
            description
              "Enable SNMP ipmobile traps";
            type empty;
          }
          leaf ipmulticast {
            description
              "Enable SNMP ipmulticast traps";
            type empty;
          }
          container ipsec {
            description
              "Enable IPsec traps";
            container cryptomap {
              leaf add {
                description
                  "Enable IPsec Cryptomap add trap";
                type empty;
              }
              leaf attach {
                description
                  "Enable IPsec Cryptomap Attach trap";
                type empty;
              }
              leaf delete {
                description
                  "Enable IPsec Cryptomap delete trap";
                type empty;
              }
              leaf detach {
                description
                  "Enable IPsec Cryptomap Detach trap";
                type empty;
              }
            }
            container tunnel {
              description
                "Enable IPsec Tunnel traps";
              leaf start {
                description
                  "Enable IPsec Tunnel Start trap";
                type empty;
              }
              leaf stop {
                description
                  "Enable IPsec Tunnel Stop trap";
                type empty;
              }
            }
            leaf too-many-sas {
              description
                "Enable IPsec Tunnel Start trap";
              type empty;
            }
          }
          container isakmp {
            description
              "Enable ISAKMP traps traps";
            container policy {
              description
                "Enable ISAKMP traps";
              leaf add {
                description
                  "Enable ISAKMP Policy add trap";
                type empty;
              }
              leaf delete {
                description
                  "Enable ISAKMP Policy delete trap";
                type empty;
              }
            }
            container tunnel {
              description
                "Enable ISAKMP Tunnel traps";
              leaf start {
                description
                  "Enable ISAKMP Tunnel start trap";
                type empty;
              }
              leaf stop {
                description
                  "Enable ISAKMP Tunnel stop trap";
                type empty;
              }
            }
          }
          container isdn {
            description
              "Enable SNMP isdn traps";
            presence "true";
            leaf call-information {
              description
                "Enable SNMP isdn call information traps";
              type empty;
            }
            leaf chan-not-avail {
              description
                "Enable SNMP isdn channel not avail traps";
              type empty;
            }
            leaf ietf {
              description
                "Enable SNMP isdn ietf traps";
              type empty;
            }
            leaf layer2 {
              description
                "Enable SNMP isdn layer2 transition traps";
              type empty;
            }
          }
          leaf ipsla {
            description
              "Enable IPSLA traps traps";
            type empty;
          }
          leaf isis {
            description
              "Enable ISIS traps traps";
            type empty;
          }
          container l2tc {
            description
              "Enable SNMP L2 Tunnel Config traps";
            presence "true";
            leaf sys-threshold {
              description
                "Enable SNMP L2TC System threshold traps";
              type empty;
            }
            leaf threshold {
              description
                "Enable SNMP L2 Tunnel Config threshold traps";
              type empty;
            }
          }
          container l2tun {
            description
              "Enable SNMP L2 tunnel protocol traps";
            leaf session {
              description
                "Enable SNMP l2tun session traps";
              type empty;
            }
            leaf tunnel {
              description
                "Enable SNMP l2tun tunnel traps";
              type empty;
            }
            container pseudowire {
              leaf status {
                type empty;
              }
            }
          }
          leaf LTE {
            description
              "Allow SNMP LTE traps";
            type empty;
          }
          container license {
            description
              "Enable license traps";
            presence "true";
            leaf deploy {
              description
                "Enable license deployment traps";
              type empty;
            }
            leaf error {
              description
                "Enable license error traps";
              type empty;
            }
            leaf usage {
              description
                "Enable license usage traps";
              type empty;
            }
          }
          leaf lisp {
            description
              "Allow SNMP LISP MIB traps";
            type empty;
          }
          container mac-notification {
            description
              "Enable SNMP MAC Notification traps";
            presence "true";
            leaf change {
              description
                "Enable SNMP Change traps";
              type empty;
            }
            leaf move {
              description
                "Enable SNMP Move traps";
              type empty;
            }
            leaf threshold {
              description
                "Enable SNMP Threshold traps";
              type empty;
            }
          }
          container mac-notification2 {
            description
              "Enable SNMP MAC Notification traps";
            presence "true";
            leaf change {
              description
                "Enable SNMP Change traps";
              type empty;
            }
            leaf move {
              description
                "Enable SNMP Move traps";
              type empty;
            }
            leaf threshold {
              description
                "Enable SNMP Threshold traps";
              type empty;
            }
          }
          container memory {
            description
              "Enable SNMP Memory traps";
            presence "true";
            leaf bufferpeak {
              description
                "Enable SNMP Memory Bufferpeak traps";
              type empty;
            }
          }
          leaf module {
            description
              "Enable SNMP module traps";
            type empty;
          }
          container mpls {
            description
              "Enable SNMP MPLS traps";
            presence "true";
            container traffic-eng {
              description
                "Allow SNMP MPLS traffic engineering traps";
              presence "true";
              leaf up {
                description
                  "Enable MPLS TE tunnel up traps";
                type empty;
              }
              leaf down {
                description
                  "Enable MPLS TE tunnel down traps";
                type empty;
              }
              leaf reroute {
                description
                  "Enable MPLS TE tunnel reroute traps";
                type empty;
              }
            }
            container fast-reroute {
              description
                "Allow SNMP MPLS fast reroute traps";
              presence "true";
              leaf protected {
                description
                  "Enable MPLS fast reroute protection traps";
                type empty;
              }
            }
            container rfc {
              description
                "Enable SNMP MPLS RFC traps";
              presence "true";
              leaf ldp {
                description
                  "Allow SNMP MPLS label distribution protocol RFC traps";
                type empty;
              }
              leaf traffic-eng {
                description
                  "Allow SNMP MPLS traffic engineering traps";
                type empty;
              }
            }
            container ldp {
              description
                "Allow SNMP MPLS label distribution protocol traps";
              presence "true";
              leaf pv-limit {
                description
                  "Enable MPLS LDP path vector limit mismatch traps";
                type empty;
              }
              leaf session-down {
                description
                  "Enable MPLS LDP session down traps";
                type empty;
              }
              leaf session-up {
                description
                  "Enable MPLS LDP session up traps";
                type empty;
              }
              leaf threshold {
                description
                  "Enable MPLS LDP threshold exceeded traps";
                type empty;
              }
            }
            leaf vpn {
              description
                "Allow SNMP MPLS Virtual Private Network traps";
              type empty;
            }
          }
          leaf msdp {
            description
              "Enable SNMP MSDP traps";
            type empty;
          }
          leaf mvpn {
            description
              "Enable Multicast Virtual Private Networks traps";
            type empty;
          }
          container nhrp {
            status deprecated;
            presence "true";
            container nhs {
              status deprecated;
              presence "true";
            }
            container nhc {
              status deprecated;
              presence "true";
            }
            container nhp {
              status deprecated;
              presence "true";
            }
            container quota-exceeded {
              status deprecated;
              presence "true";
            }
          }
          container ospf {
            status deprecated;
            description
              "Enable OSPF traps";
            container state-change {
              status deprecated;
              description
                "State change traps";
              presence "true";
              leaf if-state-change {
                status deprecated;
                description
                  "Non-virtual interface state changes";
                type empty;
              }
              leaf neighbor-state-change {
                status deprecated;
                description
                  "Non-virtual neighbor state changes";
                type empty;
              }
              leaf virtif-state-change {
                status deprecated;
                description
                  "Virtual interface state changes";
                type empty;
              }
              leaf virtneighbor-state-change {
                status deprecated;
                description
                  "Non-virtual neighbor state changes";
                type empty;
              }
            }
            container errors {
              description
                "Error traps";
              status deprecated;
              presence "true";
            }
            container retransmit {
              description
                "Packet retransmit traps";
              status deprecated;
              presence "true";
              leaf packets {
                status deprecated;
                description
                  "Packet retransmission on non-virtual interfaces";
                type empty;
              }
              leaf virt-packets {
                status deprecated;
                description
                  "Packet retransmission on virtual interfaces";
                type empty;
              }
            }
            container lsa {
              status deprecated;
              description
                "Lsa related traps";
              presence "true";
              leaf lsa-maxage {
                status deprecated;
                description
                  "Lsa aged to maxage";
                type empty;
              }
              leaf lsa-originate {
                status deprecated;
                description
                  "New lsa originated";
                type empty;
              }
            }
            container cisco-specific {
              status deprecated;
              description
                "Cisco specific traps";
              presence "true";
              container state-change {
                status deprecated;
                description
                  "State change traps";
                presence "true";
                leaf nssa-trans-change {
                  status deprecated;
                  description
                    "Nssa translator state changes";
                  type empty;
                }
                container shamlink {
                  status deprecated;
                  description
                    "Sham link state change traps";
                  presence "true";
                  leaf interface {
                    status deprecated;
                    description
                      "Sham link interface state changes";
                    type empty;
                  }
                  leaf interface-old {
                    status deprecated;
                    description
                      "Sham link interface state changes (deprecated)";
                    type empty;
                  }
                  leaf neighbor {
                    status deprecated;
                    description
                      "Sham link neighbor state changes";
                    type empty;
                  }
                }
              }
              container errors {
                status deprecated;
                description
                  "Error traps";
                presence "true";
              }
              container errdisable {
                status deprecated;
                description
                  "Enable SNMP errdisable notifications";
                presence "true";
                leaf notification-rate {
                  status deprecated;
                  description
                    "Number of notifications per minute";
                  type uint16 {
                    range "0..10000";
                  }
                }
              }
              container retransmit {
                status deprecated;
                description
                  "Packet retransmit traps";
                presence "true";
              }
              container lsa {
                status deprecated;
                description
                  "Lsa related traps";
                presence "true";
                leaf lsa-maxage {
                  status deprecated;
                  description
                    "Lsa aged to maxage";
                  type empty;
                }
                leaf lsa-originate {
                  status deprecated;
                  description
                    "New lsa originated";
                  type empty;
                }
              }
            }
          }
          container pim {
            description
              "Enable SNMP PIM traps";
            presence "true";
            leaf invalid-pim-message {
              description
                "Enable invalid pim message trap";
              type empty;
            }
            leaf neighbor-change {
              description
                "Enable neighbor change trap";
              type empty;
            }
            leaf rp-mapping-change {
              description
                "Enable rp mapping change trap";
              type empty;
            }
          }
          container pimstdmib {
            description
              "Enable SNMP PIMSTDMIB notifications";
            presence "true";
            leaf neighbor-loss {
              description
                "Enable neighbor-loss traps";
              type empty;
            }
            leaf invalid-register {
              description
                "Enable invalid-register traps";
              type empty;
            }
            leaf invalid-join-prune {
              description
                "Enable invalid-join-prune traps";
              type empty;
            }
            leaf rp-mapping-change {
              description
                "Enable invalid rp-mapping-change";
              type empty;
            }
            leaf interface-election {
              description
                "Enable interface-election traps";
              type empty;
            }
          }
          container plogd {
            description
              "Enable SNMP plogd traps";
            presence "true";
          }
          container port-security {
            description
              "Enable SNMP port security traps";
            presence "true";
            leaf trap-rate {
              description
                "Number of traps per second";
              type uint16 {
                range "0..1000";
              }
            }
          }
          container power-ethernet {
            description
              "Enable SNMP power ethernet traps";
            leaf group {
              description
                "Enable SNMP inline power group based traps";
              type string;
            }
            leaf police {
              description
                "Enable Policing Trap";
              type empty;
            }
          }
          leaf pfr {
            description
              "Allow SNMP PFR traps";
            type empty;
          }
          leaf pppoe {
            description
              "Enable SNMP pppoe traps";
            type empty;
          }
          container pw {
            presence "true";
            leaf vc {
              type empty;
            }
          }
          leaf rep {
            type empty;
          }
          leaf resource-policy {
            type empty;
          }
          leaf rf {
            description
              "Enable all SNMP traps defined in CISCO-RF-MIB";
            type empty;
          }
          leaf rogue-ap {
            description
              "Enable SNMP 802.11 Rogue AP Trap";
            type empty;
          }
          leaf rsvp {
            description
              "Enable RSVP flow change traps";
            type empty;
          }
          leaf rtr {
            description
              "Enable SNMP Response Time Reporter traps";
            type empty;
          }
          container sdwan {
            description
              "Enable SNMP SDWAN notifications";
            presence "true";
            leaf security {
              description
                "Enable SNMP SDWAN SECURITY notifications";
              type empty;
            }
            leaf policy {
              description
                "Enable SNMP SDWAN POLICY notifications";
              type empty;
            }
            leaf system {
              description
                "Enable SNMP SDWAN SYSTEM notifications";
              type empty;
            }
            leaf omp {
              description
                "Enable SNMP SDWAN OMP notifications";
              type empty;
            }
          }
          container slb {
            description
              "Enable SNMP SLB traps";
            presence "true";
            leaf csrp {
              description
                "Enable SNMP SLB Fault Tolerance Replication Protocol traps";
              type empty;
            }
            leaf real {
              description
                "Enable SNMP SLB Real Server traps";
              type empty;
            }
            leaf virtual {
              description
                "Enable SNMP SLB Virtual Server traps";
              type empty;
            }
          }
          container smart-licenseing {
            description
              "Enable smart license traps";
            leaf smart-license {
              description
                "Enable smart license traps";
              type empty;
            }
            leaf entitlement {
              description
                "Enable Entitlement Notification trap";
              type empty;
            }
            leaf global {
              description
                "Enable Global Notification traps";
              type empty;
            }
          }
          container snmp {
            description
              "Enable SNMP traps";
            leaf authentication {
              description
                "Enable authentication trap";
              type empty;
            }
            leaf coldstart {
              description
                "Enable coldStart trap";
              type empty;
            }
            leaf linkdown {
              description
                "Enable linkDown trap";
              type empty;
            }
            leaf linkup {
              description
                "Enable linkUp trap";
              type empty;
            }
            leaf warmstart {
              description
                "Enable warmStart trap";
              type empty;
            }
          }
          leaf sonet {
            description
              "Enable SNMP SONET traps";
            type empty;
          }
          leaf srst {
            type empty;
          }
          leaf srp {
            description
              "Enable SRP protocol traps";
            type empty;
          }
          container stackwise {
            description
              "Enable SNMP stackwise traps";
            presence "true";
            leaf GLS {
              description
                "Enable STACKWISE stack power GLS trap";
              type empty;
            }
            leaf ILS {
              description
                "Enable STACKWISE stack power ILS trap";
              type empty;
            }
            leaf SRLS {
              description
                "Enable STACKWISE stack power SRLS trap";
              type empty;
            }
            leaf insufficient-power {
              description
                "Enable STACKWISE stack power unbalanced power supplies trap";
              type empty;
            }
            leaf invalid-input-current {
              description
                "Enable STACKWISE stack power invalid input current trap";
              type empty;
            }
            leaf invalid-output-current {
              description
                "Enable STACKWISE stack power invalid output current trap";
              type empty;
            }
            leaf member-removed {
              description
                "Enable STACKWISE stack member removed trap";
              type empty;
            }
            leaf member-upgrade-notification {
              description
                "Enable STACKWISE member to be reloaded for upgrade trap";
              type empty;
            }
            leaf new-master {
              description
                "Enable STACKWISE new master trap";
              type empty;
            }
            leaf new-member {
              description
                "Enable STACKWISE stack new member trap";
              type empty;
            }
            leaf port-change {
              description
                "Enable STACKWISE port change trap";
              type empty;
            }
            leaf power-budget-warning {
              description
                "Enable STACKWISE stack power budget warning trap";
              type empty;
            }
            leaf power-invalid-topology {
              description
                "Enable STACKWISE stack power invalid topology trap";
              type empty;
            }
            leaf power-link-status-changed {
              description
                "Enable STACKWISE stack power link status changed trap";
              type empty;
            }
            leaf power-oper-status-changed {
              description
                "Enable STACKWISE stack power port oper status changed trap";
              type empty;
            }
            leaf power-priority-conflict {
              description
                "Enable STACKWISE stack power priority conflict trap";
              type empty;
            }
            leaf power-version-mismatch {
              description
                "Enable STACKWISE stack power version mismatch discovered trap";
              type empty;
            }
            leaf ring-redundant {
              description
                "Enable STACKWISE stack ring redundant trap";
              type empty;
            }
            leaf stack-mismatch {
              description
                "Enable STACKWISE stack mismatch trap";
              type empty;
            }
            leaf unbalanced-power-supplies {
              description
                "Enable STACKWISE stack power unbalanced power supplies trap";
              type empty;
            }
            leaf under-budget {
              description
                "Enable STACKWISE stack power under budget trap";
              type empty;
            }
            leaf under-voltage {
              description
                "Enable STACKWISE stack power under voltage trap";
              type empty;
            }
          }
          container stpx {
            presence "true";
            leaf inconsistency {
              type empty;
            }
            leaf root-inconsistency {
              type empty;
            }
            leaf loop-inconsistency {
              type empty;
            }
          }
          leaf stun {
            description
              "Enable SNMP STUN traps";
            type empty;
          }
          leaf switch-over {
            description
              "Enable SNMP 802.11 Standby Switch-over Trap";
            type empty;
          }
          leaf syslog {
            description
              "Enable SNMP syslog traps";
            type empty;
          }
          container transceiver {
            leaf all {
              type empty;
            }
          }
          leaf tty {
            description
              "Enable TCP connection traps";
            type empty;
          }
          container udld {
            description
              "Enable SNMP CISCO-UDLDP-MIB traps";
            presence "true";
            leaf link-fail-rpt {
              description
                "Enable SNMP cudldpFastHelloLinkFailRptNotification traps";
              type empty;
            }
            leaf status-change {
              description
                "Enable SNMP cudldpFastHelloStatusChangeNotification traps";
              type empty;
            }
          }
          leaf vlancreate {
            type empty;
          }
          leaf vlandelete {
            type empty;
          }
          leaf vlan-mac-limit {
            description
              "Enable SNMP L2 Control VLAN MAC Limit notifications";
            type empty;
          }
          leaf vlan-membership {
            type empty;
          }
          leaf voice {
            description
              "Enable SNMP voice traps";
            type empty;
          }
          container vrfmib {
            leaf vrf-up {
              type empty;
            }
            leaf vrf-down {
              type empty;
            }
            leaf vnet-trunk-up {
              type empty;
            }
            leaf vnet-trunk-down {
              type empty;
            }
          }
          leaf vrrp {
            description
              "Enable SNMP vrrp traps";
            type empty;
          }
          leaf vsimaster {
            description
              "Allow SNMP vsimaster traps";
            type empty;
          }
          container vstack {
            description
              "Enable SNMP Smart Install traps";
            presence "true";
            leaf addition {
              description
                "Enable client added trap";
              type empty;
            }
            leaf failure {
              description
                "Enable file upload/download failure trap";
              type empty;
            }
            leaf lost {
              description
                "Enable client lost trap";
              type empty;
            }
            leaf operation {
              description
                "Enable operation mode change trap";
              type empty;
            }
          }
          leaf vtp {
            type empty;
          }
          leaf wlan-wep {
            description
              "Enable SNMP 802.11 WLAN WEP Trap";
            type empty;
          }
          leaf xgcp {
            description
              "Enable XGCP protocol traps";
            type empty;
          }
          container wiredguest {
            description
              "Enable wired guest traps";
            presence "true";
            leaf wired_guest {
              description
                "Wired guest related traps";
              type empty;
            }
          }
          container wireless {
            description
              "wireless";
            presence "true";
            leaf AP {
              description
                "Access Point traps";
              type empty;
            }
            leaf bsn80211Security {
              description
                "Security related traps";
              type empty;
            }
            leaf bsnAutoRF {
              description
                "RF related traps";
              type empty;
            }
            leaf bsnGeneral {
              description
                "General Controller traps";
              type empty;
            }
            leaf Client {
              description
                "Controls wireless client traps";
              type empty;
            }
            leaf MESH {
              description
                "Mesh traps";
              type empty;
            }
            leaf rogue {
              description
                "Rogue related traps";
              type empty;
            }
            leaf RRM {
              description
                "Radio Resource Management (RRM) traps";
              type empty;
            }
            leaf SI {
              description
                "Spectrum Intelligence (SI) traps";
              type empty;
            }
            leaf tunnel {
              description
                "Tunnel related traps";
              type empty;
            }
            leaf wireless_mobility {
              description
                "Wireless mobility traps";
              type empty;
            }
            container bsnMobileStation {
              status obsolete;
              description
                "Controls wireless client traps. Obsolete. Please use 'Client' leaf instead";
              presence "true";
              container bsnAccessPoint {
                status obsolete;
                description
                  "Access Point traps. Obsolete. Please use 'AP' leaf instead";
                presence "true";
                leaf bsnRogue {
                  status obsolete;
                  description
                    "Rogue related traps. Obsolete. Please use 'rogue' leaf instead";
                  type empty;
                }
              }
            }
          }
          leaf netsync {
            description
              "Enable SNMP netsync traps";
            type empty;
          }
          leaf ptp {
            description
              "Enable SNMP PTP traps";
            type empty;
          }
          leaf lost-ptp-slave {
            description
              "Notification generated when the Master does not receive PTP message from Slave";
            type empty;
          }
          leaf breach-ptp-offset-threshold {
            description
              "Notification generated when current offset value exceeds configured severity threshold level";
            type empty;
          }
        }
      }
    }
    grouping engine-id-group {
      leaf engine-id {
        description
          "engine ID octet string";
        type string {
          length "10..64";
          pattern '[0-9a-fA-F]*';
        }
      }
    }

    grouping udp-port-engine {
      list udp-port {
        description
          "The remote notification host's UDP port number";
        key "port-number";
        leaf port-number {
          type uint16;
        }
        uses engine-id-group;
      }
    }

    grouping udp-port-vrf-engine {
      list udp-port {
        description
          "The remote notification host's UDP port number";
        key "port-number";
        leaf port-number {
          type uint16;
        }
        uses vrf-engine-id;
      }
    }

    grouping vrf-engine-id {
      list vrf {
        description
          "The remote notification host's VPN routing instance";
        key "vrf-name";
        leaf vrf-name {
          description
            "VPN Routing/Forwarding instance name";
          must '/ios:native/ios:vrf/ios:definition[ios:name=current()] or /ios:native/ios:ip/ios:vrf[ios:name=current()]' {
            error-message "VRF must be created 1st, deleted last";
          }
          type string;
        }
        uses engine-id-group;
      }
    }

    container file-transfer {
      description
        "File transfer related commands";
      list access-group-with-protocol {
        key "protocol";
        leaf protocol {
          type enumeration {
            enum tftp;
            enum rcp;
            enum scp;
            enum ftp;
            enum sftp;
          }
        }
        leaf access-group {
          type union {
            type uint8 {
              range "1..99";
            }
            type string;
          }
        }
      }
      container access-group {
        description
          "Access control for file transfers";
        status obsolete;
        leaf access-group-name {
          status obsolete;
          type union {
            type uint8 {
              range "1..99";
            }
            type string;
          }
        }
      }
    }
    list group {
      description
        "Define a User Security Model group";
      key "id";
      leaf id {
        type string;
      }
      choice security-model {
        container v1;
        container v2c;
        container v3 {
          description
            "group using the User Security Model (SNMPv3)";
          list security-level-list-config {
            description
              "group using security Level";
            key "security-level";
            leaf security-level {
              description
                "security level type";
              type enumeration {
                enum auth;
                enum noauth;
                enum priv;
              }
            }
            leaf match {
              description
                "context name match criteria";
              type enumeration {
                enum exact;
                enum prefix;
              }
              default "exact";
            }
            leaf read {
              description
                "specify a read view for the group";
              type string;
              default "v1default";
            }
            leaf write {
              description
                "specify a write view for the group";
              type string;
            }
            leaf notify {
              description
                "specify a notify view for the group";
              type string;
            }
            uses config-access-grouping;
          }
          list security-level-list-context {
            description
              "group using security Level";
            key "security-level context";
            leaf security-level {
              description
                "security level type";
              type enumeration {
                enum auth;
                enum noauth;
                enum priv;
              }
            }
            leaf context {
              description
                "specify a context to associate these views for the group";
              type string;
            }
            leaf match {
              description
                "context name match criteria";
              type enumeration {
                enum exact;
                enum prefix;
              }
              default "exact";
            }
            leaf read {
              description
                "specify a read view for the group";
              type string;
              default "v1default";
            }
            leaf write {
              description
                "specify a write view for the group";
              type string;
            }
            leaf notify {
              description
                "specify a notify view for the group";
              type string;
            }
            uses config-access-grouping;
          }
          list security-level-list {
            description
              "DEPRECATED group using security Level";
            status deprecated;
            key "security-level";
            leaf security-level {
              description
                "DEPRECATED security level type";
              status deprecated;
              type enumeration {
                enum auth;
                enum noauth;
                enum priv;
              }
            }
            leaf context-node {
              description
                "DEPRECATED specify a context to associate these views for the group";
              status deprecated;
              type string;
            }
            leaf match-node {
              description
                "DEPRECATED context name match criteria";
              status deprecated;
              type enumeration {
                enum exact;
                enum prefix;
              }
              default "exact";
            }
            leaf read-node {
              description
                "DEPRECATED specify a read view for the group";
              status deprecated;
              type string;
              default "v1default";
            }
            leaf write-node {
              description
                "DEPRECATED specify a write view for the group";
              status deprecated;
              type string;
            }
            leaf notify-node {
              description
                "DEPRECATED specify a notify view for the group";
              status deprecated;
              type string;
            }
            leaf access-node {
              status obsolete;
              description
                "OBSOLETE specify an access-list associated with this group";
              type union {
                type uint8 {
                  range "1..99";
                }
                type string;
              }
            }
            uses config-access-grouping;
          }
          leaf security-level {
            status obsolete;
            type enumeration {
              enum auth;
              enum noauth;
              enum priv;
            }
          }
          leaf context {
            status obsolete;
            description
              "OBSOLETE specify a context to associate these views for the group";
            type string;
          }
          leaf match {
            status obsolete;
            description
              "OBSOLETE context name match criteria";
            type enumeration {
              enum exact;
              enum prefix;
            }
          }
          leaf read {
            status obsolete;
            description
              "OBSOLETE specify a read view for the group";
            type string;
          }
          leaf write {
            status obsolete;
            description
              "OBSOLETE specify a write view for the group";
            type string;
          }
          leaf notify {
            status obsolete;
            description
              "OBSOLETE specify a notify view for the group";
            type string;
          }
          leaf access {
            status obsolete;
            description
              "OBSOLETE specify an access-list associated with this group";
            type union {
              type uint8 {
                range "1..99";
              }
              type string;
            }
          }
        }
      }
    }
    container user {
      description
        "Define a user who can access the SNMP engine";
      list names {
        key "username grpname";
        leaf username {
          description
            "Name of the user";
          type string;
        }
        leaf grpname {
          description
            "Group to which the user belongs";
          type string;
        }
        container v3 {
          description
            "user using the v3 security model";
          presence "true";
          container auth-config {
            description
              "authentication parameters for the user";
            presence "true";
            leaf algorithm {
              description
                "Use HMAC SHA/MD5 algorithm for authentication";
              type enumeration {
                enum md5;
                enum sha;
              }
            }
            leaf sha-2 {
              description
                "Use HMAC SHA-2 algorithm for authentication";
              type enumeration {
                enum 256;
                enum 384;
                enum 512;
              }
            }
            uses config-encryption-type-grouping;
            leaf password {
              description
                "Authentication password for user";
              mandatory true;
              type string;
            }
            uses config-priv-encryption-type-grouping;
            uses config-access-grouping;
          }
          container auth {
            description
              "authentication parameters for the user";
            status obsolete;
            container sha {
              description
                "Use HMAC SHA algorithm for authentication";
              status obsolete;
              uses config-auth-grouping;
            }
            container md5 {
              description
                "Use HMAC MD5 algorithm for authentication";
              status obsolete;
              uses config-auth-grouping;
            }
          }
          container encrypted {
            description
              "user using the encrypted security model";
            presence "true";
            uses config-access-grouping;
            container auth-config {
              description
                "authentication parameters for the user";
              presence "true";
              leaf algorithm {
                description
                  "Use HMAC SHA/MD5 algorithm for authentication";
                type enumeration {
                  enum md5;
                  enum sha;
                }
              }
              leaf sha-2 {
                description
                  "Use HMAC SHA-2 algorithm for authentication";
                type enumeration {
                  enum 256;
                  enum 384;
                  enum 512;
                }
              }
              leaf password {
                description
                  "Authentication password for user";
                mandatory true;
                type string;
              }
              uses config-priv-grouping;
              uses config-access-grouping;
            }
            container auth {
              description
                "authentication parameters for the user";
              status obsolete;
              container sha {
                description
                  "Use HMAC SHA algorithm for authentication";
                status obsolete;
                uses config-auth-grouping;
              }
              container md5 {
                description
                  "Use HMAC MD5 algorithm for authentication";
                status obsolete;
                uses config-auth-grouping;
              }
            }
          }
        }
      }
    }
    container host-config {
      description
        "Specify hosts to receive SNMP notifications,
         including four lists with different key fields.
         When udp-port is 162, please use either ip-(vrf-)community
         or ip-(vrf-)community-port. Don't use them simultaneously.";
      list ip-community {
        description
          "Specify hosts keyed by (ip-address, community-or-user)";
        key "ip-address community-or-user";
        leaf ip-address {
          type ios-types:host-type;
        }
        leaf community-or-user {
          description
            "SNMPv1/v2c community string or SNMPv3 user name";
          type string;
        }
        choice informs-traps-choice {
          leaf informs {
            description
              "Send Inform messages to this host";
            type empty;
          }
          leaf traps {
            description
              "Send Trap messages to this host";
            type empty;
          }
        }
        leaf version {
          description
            "SNMP version to use for notification messages";
          type enumeration {
            enum 1;
            enum 2c;
            enum 3;
          }
        }
        leaf security-level {
          type enumeration {
            enum auth;
            enum noauth;
            enum priv;
          }
        }
        uses config-host-attribute-grouping;
        leaf encryption {
          description
            "Specifies an encryption type for community string";
          type enumeration {
            enum 0;
            enum 6;
            enum 7;
          }
        }
      }
      list ip-community-port {
        description
          "Specify hosts keyed by (ip-address, community-or-user, udp-port)";
        key "ip-address community-or-user udp-port";
        leaf ip-address {
          type ios-types:host-type;
        }
        leaf community-or-user {
          description
            "SNMPv1/v2c community string or SNMPv3 user name";
          type string;
        }
        leaf udp-port {
          description
            "The notification host's UDP port number (default port 162)";
          type uint16;
        }
        choice informs-traps-choice {
          leaf informs {
            description
              "Send Inform messages to this host";
            type empty;
          }
          leaf traps {
            description
              "Send Trap messages to this host";
            type empty;
          }
        }
        leaf version {
          description
            "SNMP version to use for notification messages";
          type enumeration {
            enum 1;
            enum 2c;
            enum 3;
          }
        }
        leaf security-level {
          type enumeration {
            enum auth;
            enum noauth;
            enum priv;
          }
        }
        uses config-host-attribute-grouping;
        leaf encryption {
          description
            "Specifies an encryption type for community string";
          type enumeration {
            enum 0;
            enum 6;
            enum 7;
          }
        }
      }
      list ip-vrf-community {
        description
          "Specify hosts keyed by (ip-address, vrf, community-or-user)";
        key "ip-address vrf community-or-user";
        leaf ip-address {
          type ios-types:host-type;
        }
        leaf vrf {
          description
            "VPN Routing instance for this host";
          must '/ios:native/ios:vrf/ios:definition[ios:name=current()] or /ios:native/ios:ip/ios:vrf[ios:name=current()]' {
            error-message "VRF must be created 1st, deleted last";
          }
          type string;
        }
        leaf community-or-user {
          description
            "SNMPv1/v2c community string or SNMPv3 user name";
          type string;
        }
        choice informs-traps-choice {
          leaf informs {
            description
              "Send Inform messages to this host";
            type empty;
          }
          leaf traps {
            description
              "Send Trap messages to this host";
            type empty;
          }
        }
        leaf version {
          description
            "SNMP version to use for notification messages";
          type enumeration {
            enum 1;
            enum 2c;
            enum 3;
          }
        }
        leaf security-level {
          type enumeration {
            enum auth;
            enum noauth;
            enum priv;
          }
        }
        uses config-host-attribute-grouping;
        leaf encryption {
          description
            "Specifies an encryption type for community string";
          type enumeration {
            enum 0;
            enum 6;
            enum 7;
          }
        }
      }
      list ip-vrf-community-port {
        description
          "Specify hosts keyed by (ip-address, vrf, community-or-user, udp-port)";
        key "ip-address vrf community-or-user udp-port";
        leaf ip-address {
          type ios-types:host-type;
        }
        leaf vrf {
          description
            "VPN Routing instance for this host";
          must '/ios:native/ios:vrf/ios:definition[ios:name=current()] or /ios:native/ios:ip/ios:vrf[ios:name=current()]' {
            error-message "VRF must be created 1st, deleted last";
          }
          type string;
        }
        leaf community-or-user {
          description
            "SNMPv1/v2c community string or SNMPv3 user name";
          type string;
        }
        leaf udp-port {
          description
            "The notification host's UDP port number (default port 162)";
          type uint16;
        }
        choice informs-traps-choice {
          leaf informs {
            description
              "Send Inform messages to this host";
            type empty;
          }
          leaf traps {
            description
              "Send Trap messages to this host";
            type empty;
          }
        }
        leaf version {
          description
            "SNMP version to use for notification messages";
          type enumeration {
            enum 1;
            enum 2c;
            enum 3;
          }
        }
        leaf security-level {
          type enumeration {
            enum auth;
            enum noauth;
            enum priv;
          }
        }
        uses config-host-attribute-grouping;
        leaf encryption {
          description
            "Specifies an encryption type for community string";
          type enumeration {
            enum 0;
            enum 6;
            enum 7;
          }
        }
      }
    }
    list host {
      status obsolete;
      description
        "Specify hosts to receive SNMP notifications";
      key "ip-address community-or-user";
      leaf ip-address {
        status obsolete;
        type ios-types:host-type;
      }
      leaf community-or-user {
        status obsolete;
        description
          "OBSOLETE SNMPv1/v2c community string or SNMPv3 user name";
        type string;
      }
      leaf vrf {
        status obsolete;
        description
          "OBSOLETE VPN Routing instance for this host";
        must '/ios:native/ios:vrf/ios:definition[ios:name=current()] or /ios:native/ios:ip/ios:vrf[ios:name=current()]' {
          error-message "VRF must be created 1st, deleted last";
        }
        type string;
      }
      choice informs-traps-choice {
        status obsolete;
        leaf informs {
          status obsolete;
          description
            "OBSOLETE Send Inform messages to this host";
          type empty;
        }
        leaf traps {
          status obsolete;
          description
            "OBSOLETE Send Trap messages to this host";
          type empty;
        }
      }
      leaf version {
        status obsolete;
        description
          "OBSOLETE SNMP version to use for notification messages";
        type enumeration {
          enum 1;
          enum 2c;
          enum 3;
        }
      }
      leaf security-level {
        status obsolete;
        type enumeration {
          enum auth;
          enum noauth;
          enum priv;
        }
      }
      leaf udp-port {
        status obsolete;
        description
          "OBSOLETE The notification host's UDP port number (default port 162)";
        type uint16;
      }
      container trap-enable {
        status obsolete;
        leaf aaa_server {
          status obsolete;
          description
            "OBSOLETE Allow SNMP AAA traps";
          type empty;
        }
        leaf alarms {
          status obsolete;
          description
            "OBSOLETE Allow SNMP alarms traps";
          type empty;
        }
        leaf atm {
          status obsolete;
          description
            "OBSOLETE Allow SNMP atm traps";
          type empty;
        }
        leaf bfd {
          status obsolete;
          description
            "OBSOLETE Allow SNMP BFD traps";
          type empty;
        }
        leaf bgp {
          status obsolete;
          description
            "OBSOLETE Allow BGP state change traps";
          type empty;
        }
        leaf bstun {
          status obsolete;
          description
            "OBSOLETE Allow bstun event traps";
          type empty;
        }
        leaf bulkstat {
          status obsolete;
          description
            "OBSOLETE Allow Data-Collection-MIB traps";
          type empty;
        }
        leaf call-home {
          status obsolete;
          description
            "OBSOLETE Allow SNMP CISCO-CALLHOME-MIB traps";
          type empty;
        }
        leaf casa {
          status obsolete;
          description
            "OBSOLETE Allow casa event traps";
          type empty;
        }
        leaf cef {
          status obsolete;
          description
            "OBSOLETE Allows cef traps";
          type empty;
        }
        leaf cnpd {
          status obsolete;
          description
            "OBSOLETE Allow NBAR Protocol Discovery traps";
          type empty;
        }
        leaf config {
          status obsolete;
          description
            "OBSOLETE Allow SNMP config traps";
          type empty;
        }
        leaf config-copy {
          status obsolete;
          description
            "OBSOLETE Allow SNMP config-copy traps";
          type empty;
        }
        leaf config-ctid {
          status obsolete;
          description
            "OBSOLETE Allow SNMP config-ctid traps";
          type empty;
        }
        leaf cpu {
          status obsolete;
          description
            "OBSOLETE Allow cpu related traps";
          type empty;
        }
        leaf dhcp {
          status obsolete;
          description
            "OBSOLETE Allow dhcp traps";
          type empty;
        }
        leaf dlsw {
          status obsolete;
          description
            "OBSOLETE Allow dlsw traps";
          type empty;
        }
        leaf ds1 {
          status obsolete;
          description
            "OBSOLETE Allow SNMP ds1 traps";
          type empty;
        }
        leaf dsp {
          status obsolete;
          description
            "OBSOLETE Allow SNMP DSP traps";
          type empty;
        }
        leaf dspu {
          status obsolete;
          description
            "OBSOLETE Allow dspu event traps";
          type empty;
        }
        leaf eigrp {
          status obsolete;
          description
            "OBSOLETE Allow SNMP EIGRP traps";
          type empty;
        }
        leaf entity {
          status obsolete;
          description
            "OBSOLETE Allow SNMP entity traps";
          type empty;
        }
        leaf entity-diag {
          status obsolete;
          description
            "OBSOLETE Allow SNMP CISCO-ENTITY-DIAG-MIB traps";
          type empty;
        }
        leaf entity-qfp {
          status obsolete;
          description
            "OBSOLETE Allow SNMP CISCO-ENTITY-QFP-MIB traps";
          type empty;
        }
        leaf entity-state {
          status obsolete;
          description
            "OBSOLETE Allow ENTITY-STATE-MIB traps";
          type empty;
        }
        leaf ethernet-cfm {
          status obsolete;
          description
            "OBSOLETE Allow SNMP Ethernet CFM traps";
          type empty;
        }
        leaf evc {
          status obsolete;
          description
            "OBSOLETE Allow SNMP EVC traps";
          type empty;
        }
        leaf event-manager {
          status obsolete;
          description
            "OBSOLETE Allow SNMP Embedded Event Manager traps";
          type empty;
        }
        leaf firewall {
          status obsolete;
          description
            "OBSOLETE Allow SNMP Firewall traps";
          type empty;
        }
        leaf flash {
          status obsolete;
          description
            "OBSOLETE Allow SNMP FLASH traps";
          type empty;
        }
        leaf flowmon {
          status obsolete;
          description
            "OBSOLETE Allow SNMP flow monitor notifications";
          type empty;
        }
        leaf frame-relay {
          status obsolete;
          description
            "OBSOLETE Allow SNMP frame-relay traps";
          type empty;
        }
        leaf fru-ctrl {
          status obsolete;
          description
            "OBSOLETE Allow entity FRU control traps";
          type empty;
        }
        leaf gdoi {
          status obsolete;
          description
            "OBSOLETE Allows gdoi traps";
          type empty;
        }
        leaf hsrp {
          status obsolete;
          description
            "OBSOLETE Allow SNMP HSRP traps";
          type empty;
        }
        leaf iplocalpool {
          status obsolete;
          description
            "OBSOLETE Allow SNMP IP Local Pool traps";
          type empty;
        }
        leaf ipmulticast {
          status obsolete;
          description
            "OBSOLETE Allow SNMP ipmulticast traps";
          type empty;
        }
        leaf ipsec {
          status obsolete;
          description
            "OBSOLETE Allow SNMP IPsec traps";
          type empty;
        }
        leaf ipsla {
          status obsolete;
          description
            "OBSOLETE Allow SNMP Host IP SLA traps";
          type empty;
        }
        leaf isakmp {
          status obsolete;
          description
            "OBSOLETE Allow SNMP ISAKMP traps";
          type empty;
        }
        leaf isg-mib {
          status obsolete;
          description
            "OBSOLETE Allow SNMP isgmib traps";
          type empty;
        }
        leaf isis {
          status obsolete;
          description
            "OBSOLETE Allow IS-IS traps";
          type empty;
        }
        leaf l2tun-pseudowire-status {
          status obsolete;
          description
            "OBSOLETE Allow SNMP L2 pseudowire status traps";
          type empty;
        }
        leaf l2tun-session {
          status obsolete;
          description
            "OBSOLETE Allow SNMP L2 session traps";
          type empty;
        }
        leaf license {
          status obsolete;
          description
            "OBSOLETE Allow license traps";
          type empty;
        }
        leaf memory {
          status obsolete;
          description
            "OBSOLETE Allow SNMP Mempool traps";
          type empty;
        }
        leaf mpls-fast-reroute {
          status obsolete;
          description
            "OBSOLETE Allow SNMP MPLS traffic engineering fast reroute traps";
          type empty;
        }
        leaf mpls-ldp {
          status obsolete;
          description
            "OBSOLETE Allow SNMP MPLS label distribution protocol traps";
          type empty;
        }
        leaf mpls-traffic-eng {
          status obsolete;
          description
            "OBSOLETE Allow SNMP MPLS traffic engineering traps";
          type empty;
        }
        leaf mpls-vpn {
          status obsolete;
          description
            "OBSOLETE Allow SNMP MPLS Virtual Private Network traps";
          type empty;
        }
        leaf msdp {
          status obsolete;
          description
            "OBSOLETE Allow SNMP MSDP traps";
          type empty;
        }
        leaf mvpn {
          status obsolete;
          description
            "OBSOLETE Allow Multicast Virtual Private Network traps";
          type empty;
        }
        leaf nhrp {
          status obsolete;
          description
            "OBSOLETE Allow SNMP NHRP traps";
          type empty;
        }
        leaf ospf {
          status obsolete;
          description
            "OBSOLETE Allow OSPF traps";
          type empty;
        }
        leaf ospfv3 {
          status obsolete;
          description
            "OBSOLETE Allow OSPFv3 traps";
          type empty;
        }
        leaf pfr {
          status obsolete;
          description
            "OBSOLETE Allow SNMP PfR traps";
          type empty;
        }
        leaf pim {
          status obsolete;
          description
            "OBSOLETE Allow SNMP PIM traps";
          type empty;
        }
        leaf pw-vc {
          status obsolete;
          description
            "OBSOLETE Allow SNMP Pseudowire VC traps";
          type empty;
        }
        leaf resource-policy {
          status obsolete;
          description
            "OBSOLETE Enable CISCO-ERM-MIB notifications";
          type empty;
        }
        leaf rf {
          status obsolete;
          description
            "OBSOLETE Allow all SNMP traps defined in CISCO-RF-MIB";
          type empty;
        }
        leaf rsrb {
          status obsolete;
          description
            "OBSOLETE Allow rsrb event traps";
          type empty;
        }
        leaf rsvp {
          status obsolete;
          description
            "OBSOLETE Allow RSVP flow change traps";
          type empty;
        }
        leaf sdlc {
          status obsolete;
          description
            "OBSOLETE Allow sdlc event traps";
          type empty;
        }
        leaf sdllc {
          status obsolete;
          description
            "OBSOLETE Allow sdllc event traps";
          type empty;
        }
        leaf snmp {
          status obsolete;
          description
            "OBSOLETE Allow SNMP-type notifications";
          type empty;
        }
        leaf sonet {
          status obsolete;
          description
            "OBSOLETE Allow SNMP SONET traps";
          type empty;
        }
        leaf srp {
          status obsolete;
          description
            "OBSOLETE Allow SRP protocol traps";
          type empty;
        }
        leaf stun {
          status obsolete;
          description
            "OBSOLETE Allow stun event traps";
          type empty;
        }
        leaf syslog {
          status obsolete;
          description
            "OBSOLETE Allow SNMP syslog traps";
          type empty;
        }
        leaf trustsec-sxp {
          status obsolete;
          description
            "OBSOLETE Allow SNMP CISCO-TRUSTSEC-SXP-MIB traps";
          type empty;
        }
        leaf tty {
          status obsolete;
          description
            "OBSOLETE Allow TCP connection traps";
          type empty;
        }
        leaf voice {
          status obsolete;
          description
            "OBSOLETE Allow SNMP Voice traps";
          type empty;
        }
        leaf vrfmib {
          status obsolete;
          description
            "OBSOLETE Allow SNMP vrfmib traps";
          type empty;
        }
        leaf vrrp {
          status obsolete;
          description
            "OBSOLETE Allow SNMP vrrp traps";
          type empty;
        }
        leaf x25 {
          status obsolete;
          description
            "OBSOLETE Allow x25 event traps";
          type empty;
        }
      }
    }
    container ip {
      description
        "IP ToS configuration for SNMP traffic";
      leaf dscp {
        description
          "IP DSCP value for SNMP traffic";
        type uint8 {
          range "0..63";
        }
      }
      leaf precedence {
        description
          "IP Precedence value for SNMP traffic";
        type uint8 {
          range "0..7";
        }
      }
    }
    container ifindex {
      description
        "Enable ifindex persistence";
      leaf persist {
        description
          "Persist interface indices";
        type empty;
      }
    }
    leaf location {
      description
        "Text for mib object sysLocation";
      type string;
    }
    container manager {
      description
        "Modify SNMP manager parameters";
      presence "true";
      leaf session-timeout {
        description
          "Timeout value for destroying sessions";
        type uint32 {
          range "10..2147483";
        }
      }
    }
    leaf packetsize {
      description
        "Largest SNMP packet size";
      type uint32 {
        range "484..17892";
      }
    }
    leaf queue-length {
      description
        "Message queue length for each TRAP host";
      type uint16 {
        range "1..5000";
      }
    }
    container source-interface {
      description
        "Assign an source interface";
      container informs {
        description
          "source interface for informs";
        uses ios-ifc:interface-grouping;
      }
      container traps {
        description
          "source interface for traps";
        uses ios-ifc:interface-grouping;
      }
    }
    leaf sparse-tables {
      description
        "Turn on snmp sparse table implementation";
      type boolean;
      default "true";
    }
    container subagent {
      description
        "subagent commands";
      container cache {
        description
          "Subagent cache";
        leaf timeout {
          description
            "Subagent cache timeout interval in seconds";
          type uint8 {
            range "0..100";
          }
          default "60";
        }
      }
      leaf cache-stats {
        description
          "Subagent cache statistics configuration";
        type boolean;
        default "false";
      }
      container datastage {
        description
          "Subagent datastage";
        leaf timeout {
          description
            "Subagent datastage timeout in  minutes";
          type uint8 {
            range "0..100";
          }
          default "5";
        }
      }
      leaf enable {
        description
          "Subagent Configuration";
        type boolean;
        default "true";
      }
      container fetch {
        description
          "subagent Fetch";
        leaf count {
          description
            "fetch count";
          type uint8 {
            range "1..100";
          }
          default "50";
        }
      }
    }
    leaf system-shutdown {
      description
        "Enable use of the SNMP reload command";
      type empty;
    }
    leaf tftp-server-list {
      description
        "Limit TFTP servers used via SNMP";
      type union {
        type uint8 {
          range "1..99";
        }
        type string;
      }
    }
    container trap {
      description
        "SNMP trap options";
      container authentication {
        description
          "fine-tune enable/disable of authentication traps";
        leaf unknown-context {
          description
            "enable authentication traps for unknown context error";
          type boolean;
          default "true";
        }
        leaf acl-failure {
          description
            "Authentication traps for access-list failure";
          type boolean;
          default "true";
        }
      }
      container link {
        description
          "Assign/Enable SNMP link traps";
        leaf ietf {
          description
            "Use IETF standard for SNMP traps";
          type empty;
        }
        leaf switchover {
          description
            "Enable link up/down traps during switchover";
          type empty;
        }
      }
      leaf timeout {
        description
          "Set timeout for TRAP message retransmissions";
        type uint16 {
          range "1..1000";
        }
      }
    }
    container trap-source {
      description
        "Assign an interface for the source address of all traps";
      uses ios-ifc:interface-grouping;
    }
    list view {
      description
        "Define an SNMPv2 MIB view";
      key "name mib";
      leaf name {
        type string;
      }
      leaf mib {
        type string;
      }
      leaf inc-exl {
        type enumeration {
          enum excluded;
          enum included;
        }
      }
    }
  }

  grouping router-snmp-grouping {
    container snmp {
      description
        "Modify snmp parameters";
      list context {
        description
          "Configure a SNMP context";
        key "name";
        leaf name {
          description
            "Context Name";
          type string;
        }
        container community {
          description
            "Configure a SNMP v2c Community string and access privs";
          leaf community-string {
            type string;
          }
          container access {
            leaf ro {
              description
                "Read-only access with this community string";
              type empty;
            }
            leaf rw {
              description
                "Read-write access with this community string";
              type empty;
            }
            leaf standard-acl {
              type uint32 {
                range "1..99";
              }
            }
            leaf expanded-acl {
              type uint32 {
                range "1300..1999";
              }
            }
            leaf acl-name {
              type string;
            }
            leaf ipv6 {
              description
                "Specify IPv6 Named Access-List";
              type string;
            }
          }
        }
        container user {
          description
            "Configure a SNMP v3 user";
          leaf name {
            type string;
          }
          container permisssion {
            container access {
              description
                "specify an access-list associated with this group";
              leaf standard-acl {
                type uint32 {
                  range "1..99";
                }
              }
              leaf acl-name {
                type string;
              }
              leaf ipv6 {
                type string;
              }
            }
            container auth-config {
              description
                "authentication parameters for the user";
              presence "true";
              leaf algorithm {
                description
                  "Use HMAC SHA/MD5 algorithm for authentication";
                mandatory true;
                type enumeration {
                  enum md5;
                  enum sha;
                }
              }
              leaf password {
                description
                  "Authentication password for user";
                mandatory true;
                type string;
              }
              uses config-priv-grouping;
              uses config-access-grouping;
            }
            container auth {
              description
                "authentication parameters for the user";
              status obsolete;
              leaf md5 {
                description
                  "OBSOLETE Use HMAC MD5 algorithm for authentication";
                status obsolete;
                type string;
              }
              leaf sha {
                description
                  "OBSOLETE Use HMAC SHA algorithm for authentication";
                status obsolete;
                type string;
              }
            }
            leaf credential {
              description
                "If the user password is already configured and saved";
              type empty;
            }
            container encrypted-config {
              description
                "user using the encrypted security model";
              presence "true";
              container auth-config {
                presence "true";
                leaf algorithm {
                  mandatory true;
                  type enumeration {
                    enum md5;
                    enum sha;
                  }
                }
                leaf password {
                  description
                    "Authentication password for user";
                  mandatory true;
                  type string;
                }
                uses config-priv-grouping;
                uses config-access-grouping;
              }
              uses config-access-grouping;
            }
            leaf encrypted {
              description
                "OBSOLETE specifying passwords as MD5 or SHA digests";
              status obsolete;
              type empty;
            }
          }
        }
      }
    }
  }

  grouping config-snmp-grouping {
    container ifmib {
      description
        "IF-MIB commands";
      container ifindex {
        description
          "ifindex persistence";
        leaf persist {
          description
            "Persist interface indices";
          type empty;
        }
      }
      container ifalias {
        description
          "ifAlias description option, by default it is limited to 64 character";
        leaf long {
          description
            "ifAlias description can be up to 256 characters";
          type empty;
        }
      }
    }
    container mib {
      description
        "MIB commands";
      container community-map {
        description
          "Community Mapping as per RFC-2576";
        list community-map-list {
          description
            "SNMP community string";
          key "name";
          leaf name {
            type string;
          }
          leaf encryption {
            description
              "Specifies an encryption type";
            type enumeration {
              enum 0;
              enum 6;
              enum 7;
            }
          }
          leaf engineid {
            description
              "Engine ID for the community mapping";
            type string {
              length "10..64";
              pattern '[0-9a-fA-F]*';
            }
          }
        }
      }
      container event {
        description
          "The Event scalar configuration";
        container sample {
          description
            "Event scalar variables configuration";
          leaf minimum {
            description
              "Event scalar sample minimum";
            type uint32 {
              range "1..2147483647";
            }
            default "60";
          }
          container instance {
            description
              "Event scalar sample instance maximum";
            leaf maximum {
              description
                "Event scalar sample instance maximum";
              type uint32 {
                range "0..4294967295";
              }
              default "0";
            }
          }
        }
      }
      container expression {
        description
          "SNMP MIB expression";
        container delta {
          description
            "System wide delta parameters";
          leaf minimum {
            description
              "Minimum delta interval or use -1 to denote no delta minimum";
            type int16 {
              range "-1 | 1..600";
            }
            default "1";
          }
          container wildcard {
            description
              "Delta Wildcard Maximum configuration";
            leaf maximum {
              description
                "Delta Wildcard Maximum configuration";
              type uint32 {
                range "0..4294967295";
              }
              default "0";
            }
          }
        }
        container owner {
          description
            "Expression Owner Name";
          list owner-name-list {
            description
              "Owner Name";
            key "owner-name name";
            leaf owner-name {
              description
                "Set owner name";
              type string;
            }
            leaf name {
              description
                "Expression Name";
              type string;
            }
            container value {
              description
                "Expression value type Configuration";
              leaf type {
                description
                  "Expression value type";
                type enumeration {
                  enum counter32 {
                    description
                      "Expression value type counter32";
                  }
                  enum counter64 {
                    description
                      "Expression value type counter64";
                  }
                  enum integer32 {
                    description
                      "Expression value type integer32";
                  }
                  enum ipaddress {
                    description
                      "Expression value type ipaddress";
                  }
                  enum objectid {
                    description
                      "Expression value type objectid";
                  }
                  enum octetstring {
                    description
                      "Expression value type octetstring";
                  }
                  enum timeticks {
                    description
                      "Expression value type timeticks";
                  }
                  enum unsigned32 {
                    description
                      "Expression value type undigned32";
                  }
                }
                default "counter32";
              }
            }
          }
        }
      }
      container bulkstat {
        description
          "Bulkstat Configuration commands";
        list object-list {
          description
            "Configure an Object List.";
          key "name";
          leaf name {
            type string;
          }
        }
      }
      container flowmon {
        description
          "Flow monitor maximum number of entries";
        leaf alarmhistorysize {
          description
            "Maximum number of entries maintained by the flow monitor";
          type uint32 {
            range "1..1000000";
          }
          default "500";
        }
      }
      container flash {
        description
          "Flash MIB related commands";
        container cache {
          description
            "Flash Cache process state";
          presence "true";
          leaf interval {
            description
              "Time interval for IFS cache data updation in minutes";
            type uint8 {
              range "1..60";
            }
            default "2";
          }
        }
      }
      container persist-config {
        description
          "Persistence config for MIBS";
        leaf cbqos {
          description
            "Class-Based QOS MIB index persistence";
          type empty;
        }
        leaf circuit {
          description
            "Circuit interface identification persistence";
          type empty;
        }
        leaf v3mibs {
          description
            "Persistence for v3 MIBS";
          type empty;
        }
        leaf dsmib {
          description
            "DiffServ MIB persistence";
          type empty;
        }
      }
      container persist {
        description
          "DEPRECATED Persistence for MIBS";
        status deprecated;
        presence "true";
        leaf persist-enum {
          status deprecated;
          type enumeration {
            enum cbqos;
            enum circuit;
            enum v3mibs;
          }
        }
      }
      leaf nhrp {
        description
          "NHRP Configuration";
        type empty;
      }
      container notification-log {
        description
          "Notification log MIB configuration";
        leaf globalageout {
          description
            "Global age-out time of notifications in seconds";
          type uint32 {
            range "1..4294967295";
          }
          default "15";
        }
        leaf globalsize {
          description
            "Global entries upper limit";
          type uint16 {
            range "1..15000";
          }
          default "500";
        }
      }
    }
    container monitor {
      description
        "Monitor Response Time in milliseconds";
      leaf response {
        description
          "SNMP Response";
        type uint16 {
          range "1000..10000";
        }
        default "10000";
      }
    }
  }

  grouping config-interface-ATMsubinterface-snmp-grouping {
    container snmp {
      description
        "Modify SNMP interface parameters";
      container trap {
        description
          "Allow a specific SNMP trap";
        leaf link-status {
          description
            "Allow SNMP LINKUP and LINKDOWN traps";
          type boolean;
          default "false";
        }
      }
    }
  }

  grouping config-interface-snmp-grouping {
    container snmp {
      description
        "Modify SNMP interface parameters";
      container ifindex {
        description
          "Persist ifindex for the interface";
        choice ifindex-choice {
          leaf persist {
            description
              "Enable/Disable ifIndex persistence ";
            type empty;
          }
          leaf clear {
            description
              "Clear Enable/Disable ifIndex persistence";
            type boolean;
          }
        }
      }
      container trap {
        description
          "Allow a specific SNMP trap";
        leaf link-status {
          description
            "Allow SNMP LINKUP and LINKDOWN traps";
          type boolean;
        }
        container link-status-capas {
          container link-status {
            description
              "Allow SNMP LINKUP and LINKDOWN traps";
            container permit {
              description
                "Permit the following capability";
              leaf duplicates {
                description
                  "Permit duplicate SNMP LINKUP and LINKDOWN traps";
                type empty;
              }
            }
          }
        }
      }
    }
  }

  augment "/ios:native/ios:snmp" {
    uses config-snmp-grouping;
  }

  augment "/ios:native/ios:snmp-server" {
    uses config-snmp-server-grouping;
  }

  augment "/ios:native/ios:interface/ios:FastEthernet" {
    uses config-interface-snmp-grouping;
  }

  augment "/ios:native/ios:interface/ios:ATM-subinterface/ios:ATM" {
    uses config-interface-ATMsubinterface-snmp-grouping;
  }

  augment "/ios:native/ios:interface/ios:GigabitEthernet" {
    uses config-interface-snmp-grouping;
  }

  augment "/ios:native/ios:interface/ios:TenGigabitEthernet" {
    uses config-interface-snmp-grouping;
  }

  augment "/ios:native/ios:interface/ios:FiveGigabitEthernet" {
    uses config-interface-snmp-grouping;
  }

  augment "/ios:native/ios:interface/ios:AppGigabitEthernet" {
    uses config-interface-snmp-grouping;
  }

  augment "/ios:native/ios:interface/ios:TwentyFiveGigabitEthernet" {
    status obsolete;
    uses config-interface-snmp-grouping {
      status obsolete;
    }
  }

  augment "/ios:native/ios:interface/ios:TwentyFiveGigE" {
    uses config-interface-snmp-grouping;
  }

  augment "/ios:native/ios:interface/ios:TwoGigabitEthernet" {
    uses config-interface-snmp-grouping;
  }

  augment "/ios:native/ios:interface/ios:FortyGigabitEthernet" {
    uses config-interface-snmp-grouping;
  }

  augment "/ios:native/ios:interface/ios:HundredGigE" {
    uses config-interface-snmp-grouping;
  }

  augment "/ios:native/ios:interface/ios:Loopback" {
    uses config-interface-snmp-grouping;
  }

  augment "/ios:native/ios:interface/ios:Port-channel" {
    uses config-interface-snmp-grouping;
  }

  augment "/ios:native/ios:interface/ios:Tunnel" {
    uses config-interface-snmp-grouping;
  }

  augment "/ios:native/ios:interface/ios:Virtual-Template" {
    uses config-interface-snmp-grouping;
  }

  augment "/ios:native/ios:interface/ios:VirtualPortGroup" {
    uses config-interface-snmp-grouping;
  }

  augment "/ios:native/ios:interface/ios:Serial" {
    uses config-interface-snmp-grouping;
  }
}
