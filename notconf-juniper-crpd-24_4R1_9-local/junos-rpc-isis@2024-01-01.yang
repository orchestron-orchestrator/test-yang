module junos-rpc-isis {
  namespace "http://yang.juniper.net/junos/rpc/isis";
  prefix isis;

  import junos-common-types {
    prefix jt;
    revision-date 2024-01-01;
  }

  organization
    "Juniper Networks, Inc.";
  contact
    "yang-support@juniper.net";
  description
    "Junos RPC YANG module for isis command(s)";

  revision 2024-01-01 {
    description
      "Junos: 20241218.202301_builder.r1463698";
  }

  grouping isis-adjacency-information-block {
    list isis-adjacency-instance-information {
      list isis-adjacency {
        list snpa {
          leaf snpa-type {
            type string;
            description
              "Type of SNPA";
          }
          list pfe-port-snpa {
            leaf pfe-id {
              type int32;
            }
            leaf port-id {
              type int32;
            }
          }
          list network-element-port-snpa {
            leaf port-id {
              type int32;
            }
          }
          list mstp-root-snpa {
            leaf mstp-root-id {
              type int32;
            }
          }
          list gateway-snpa {
            leaf gateway-addr {
              type jt:ipaddr;
            }
          }
          list layer2-domain-port-snpa {
            leaf port-id {
              type int32;
            }
          }
          list replication-block-snpa {
            leaf replication-block-id {
              type int32;
            }
          }
          list replication-route-snpa {
            leaf network-element-id {
              type jt:ipaddr;
            }
          }
          list layer2-multicast-port-snpa {
            leaf layer2-multicast-port-id {
              type int32;
            }
          }
          list inh-snpa {
            leaf inh-id {
              type int32;
            }
          }
        }
        list srv6-micro-adjacency-segment-information {
          leaf srv6-micro-adjacency-segment-level {
            type int32;
            description
              "Micro adjacency Level";
          }
          leaf srv6-protected-micro-adjacency-segment {
            type jt:ipv6addr;
            description
              "SRv6 protected micro-adjacency-SID";
          }
          leaf srv6-unprotected-micro-adjacency-segment {
            type jt:ipv6addr;
            description
              "SRv6 unprotected micro-adjacency-SID";
          }
          leaf srv6-micro-adjacency-segment-end-point-func {
            type string;
            description
              "SRv6 micro-adjacency-SID Function";
          }
          leaf srv6-micro-adjacency-segment-flags {
            type string;
            description
              "SRv6 micro adjacency flags";
          }
          leaf srv6-micro-adjacency-segment-algorithm {
            type uint32;
            description
              "SRv6 micro adjacency algorithm";
          }
        }
        container isis-bfd-nlpid-stats {
          leaf isis-bfd-nlpid-stats-header {
            type string;
          }
          container isis-bfd-tlv-mtids {
            leaf isis-bfd-tlv-mtid {
              type int32;
            }
            leaf isis-bfd-mtid-v4nlpid-state {
              type string;
            }
            leaf isis-bfd-mtid-v6nlpid-state {
              type string;
            }
          }
        }
        leaf interface-name {
          type string;
          description
            "Name of interface";
        }
        leaf system-name {
          type string;
          description
            "Hostname for a system";
        }
        leaf not-remote-address {
          type empty;
        }
        leaf level {
          type int32;
          description
            "IS-IS Level";
        }
        leaf adjacency-state {
          type string;
          description
            "State of the adjacency";
        }
        leaf holdtime {
          type int32;
          description
            "Delay before timing out the adjacency (default is 180 seconds)";
        }
        leaf interface-priority {
          type int32;
        }
        leaf transition-count {
          type int32;
        }
        leaf last-transition-time {
          type string;
        }
        leaf circuit-type {
          type int32;
        }
        leaf adjacency-flag {
          type string;
        }
        leaf mac-address {
          type jt:mac-addr;
        }
        leaf adjacency-topologies {
          type string;
        }
        leaf adjacency-restart-capable {
          type string;
          description
            "Restart capability of the adjacency";
        }
        leaf adjacency-advertisement {
          type string;
          description
            "State of the adjacency advertisment";
        }
        leaf lan-id {
          type string;
        }
        leaf ip-address {
          type jt:ipaddr;
        }
        leaf ipv6-address {
          type jt:ipv6addr;
        }
        leaf global-ipv6-address {
          type jt:ipv6addr;
        }
        leaf flood-ref-level {
          type int32;
        }
        leaf flood-ref-node {
          type string;
          description
            "Flood reflector";
        }
        leaf flood-ref-cluster-id {
          type uint32;
          description
            "Flood reflector cluster id";
        }
        leaf adjacency-segment-level {
          type int32;
        }
        leaf ipv4-adjacency-segment-id {
          type int32;
        }
        leaf ipv6-adjacency-segment-id {
          type int32;
        }
        container adjacency-segment-information {
          leaf adjacency-segment-level {
            type int32;
          }
          leaf ipv4-protected-adjacency-segment-id {
            type int32;
          }
          leaf ipv4-unprotected-adjacency-segment-id {
            type int32;
          }
          leaf ipv6-protected-adjacency-segment-id {
            type int32;
          }
          leaf ipv6-unprotected-adjacency-segment-id {
            type int32;
          }
          leaf adjacency-segment-flags {
            type string;
          }
        }
        container srv6-adjacency-segment-information {
          leaf srv6-adjacency-segment-level {
            type int32;
            description
              "Adjacency Level";
          }
          leaf srv6-protected-adjacency-segment {
            type jt:ipv6addr;
            description
              "SRv6 Protected END-X-SID";
          }
          leaf srv6-unprotected-adjacency-segment {
            type jt:ipv6addr;
            description
              "SRv6 UnProtected END-X-SID";
          }
          leaf srv6-adjacency-segment-end-point-func {
            type string;
            description
              "SRv6 END-X-SID Function";
          }
          leaf srv6-adjacency-segment-flags {
            type string;
            description
              "SRv6 Adjacency Flags";
          }
          leaf srv6-adjacency-segment-algorithm {
            type uint32;
            description
              "SRv6 Adjacency Algorithm";
          }
        }
        container bfd-tlv-information {
          leaf bfd-tlv-info-level {
            type string;
          }
        }
        container isis-adj-bfd-state-info {
          leaf isis-bfd-v4-sess-state {
            type string;
          }
          leaf isis-bfd-v6-sess-state {
            type string;
          }
          leaf isis-bfd-req-state {
            type string;
          }
          leaf isis-bfd-adj-usable {
            type string;
          }
        }
        list isis-adjacency-log {
          leaf adjacency-when {
            type string;
            description
              "Time at which the transition occurred";
          }
          leaf adjacency-state {
            type string;
            description
              "State of the adjacency";
          }
          leaf adjacency-event {
            type string;
            description
              "Event which triggered the transition";
          }
          leaf adjacency-down-reason {
            type string;
            description
              "Reason for the down transition event";
          }
        }
      }
      leaf isis-instance-name {
        type string;
        description
          "Name of ISIS instance";
      }
      leaf isis-routing-instance-name {
        type string;
        description
          "Name of Routing instance";
      }
    }
    list isis-adjacency {
      key "interface-name";
      leaf interface-name {
        type string;
        description
          "Name of interface";
      }
      leaf system-name {
        type string;
        description
          "Hostname for a system";
      }
      leaf not-remote-address {
        type empty;
      }
      leaf level {
        type int32;
        description
          "IS-IS Level";
      }
      leaf adjacency-state {
        type string;
        description
          "State of the adjacency";
      }
      leaf holdtime {
        type int32;
        description
          "Delay before timing out the adjacency (default is 180 seconds)";
      }
      leaf-list snpa {
        type string;
      }
      leaf snpa-type {
        type string;
        description
          "Type of SNPA";
      }
      list pfe-port-snpa {
        leaf pfe-id {
          type int32;
        }
        leaf port-id {
          type int32;
        }
      }
      list network-element-port-snpa {
        leaf port-id {
          type int32;
        }
      }
      list mstp-root-snpa {
        leaf mstp-root-id {
          type int32;
        }
      }
      list gateway-snpa {
        leaf gateway-addr {
          type jt:ipaddr;
        }
      }
      list layer2-domain-port-snpa {
        leaf port-id {
          type int32;
        }
      }
      list replication-block-snpa {
        leaf replication-block-id {
          type int32;
        }
      }
      list replication-route-snpa {
        leaf network-element-id {
          type jt:ipaddr;
        }
      }
      list layer2-multicast-port-snpa {
        leaf layer2-multicast-port-id {
          type int32;
        }
      }
      list inh-snpa {
        leaf inh-id {
          type int32;
        }
      }
      list srv6-micro-adjacency-segment-information {
        leaf srv6-micro-adjacency-segment-level {
          type int32;
          description
            "Micro adjacency Level";
        }
        leaf srv6-protected-micro-adjacency-segment {
          type jt:ipv6addr;
          description
            "SRv6 protected micro-adjacency-SID";
        }
        leaf srv6-unprotected-micro-adjacency-segment {
          type jt:ipv6addr;
          description
            "SRv6 unprotected micro-adjacency-SID";
        }
        leaf srv6-micro-adjacency-segment-end-point-func {
          type string;
          description
            "SRv6 micro-adjacency-SID Function";
        }
        leaf srv6-micro-adjacency-segment-flags {
          type string;
          description
            "SRv6 micro adjacency flags";
        }
        leaf srv6-micro-adjacency-segment-algorithm {
          type uint32;
          description
            "SRv6 micro adjacency algorithm";
        }
      }
      container isis-bfd-nlpid-stats {
        leaf isis-bfd-nlpid-stats-header {
          type string;
        }
        container isis-bfd-tlv-mtids {
          leaf isis-bfd-tlv-mtid {
            type int32;
          }
          leaf isis-bfd-mtid-v4nlpid-state {
            type string;
          }
          leaf isis-bfd-mtid-v6nlpid-state {
            type string;
          }
        }
      }
      leaf interface-priority {
        type int32;
      }
      leaf transition-count {
        type int32;
      }
      leaf last-transition-time {
        type string;
      }
      leaf circuit-type {
        type int32;
      }
      leaf adjacency-flag {
        type string;
      }
      leaf mac-address {
        type jt:mac-addr;
      }
      leaf adjacency-topologies {
        type string;
      }
      leaf adjacency-restart-capable {
        type string;
        description
          "Restart capability of the adjacency";
      }
      leaf adjacency-advertisement {
        type string;
        description
          "State of the adjacency advertisment";
      }
      leaf lan-id {
        type string;
      }
      leaf ip-address {
        type jt:ipaddr;
      }
      leaf ipv6-address {
        type jt:ipv6addr;
      }
      leaf global-ipv6-address {
        type jt:ipv6addr;
      }
      leaf flood-ref-level {
        type int32;
      }
      leaf flood-ref-node {
        type string;
        description
          "Flood reflector";
      }
      leaf flood-ref-cluster-id {
        type uint32;
        description
          "Flood reflector cluster id";
      }
      leaf adjacency-segment-level {
        type int32;
      }
      leaf ipv4-adjacency-segment-id {
        type int32;
      }
      leaf ipv6-adjacency-segment-id {
        type int32;
      }
      container adjacency-segment-information {
        leaf adjacency-segment-level {
          type int32;
        }
        leaf ipv4-protected-adjacency-segment-id {
          type int32;
        }
        leaf ipv4-unprotected-adjacency-segment-id {
          type int32;
        }
        leaf ipv6-protected-adjacency-segment-id {
          type int32;
        }
        leaf ipv6-unprotected-adjacency-segment-id {
          type int32;
        }
        leaf adjacency-segment-flags {
          type string;
        }
      }
      container srv6-adjacency-segment-information {
        leaf srv6-adjacency-segment-level {
          type int32;
          description
            "Adjacency Level";
        }
        leaf srv6-protected-adjacency-segment {
          type jt:ipv6addr;
          description
            "SRv6 Protected END-X-SID";
        }
        leaf srv6-unprotected-adjacency-segment {
          type jt:ipv6addr;
          description
            "SRv6 UnProtected END-X-SID";
        }
        leaf srv6-adjacency-segment-end-point-func {
          type string;
          description
            "SRv6 END-X-SID Function";
        }
        leaf srv6-adjacency-segment-flags {
          type string;
          description
            "SRv6 Adjacency Flags";
        }
        leaf srv6-adjacency-segment-algorithm {
          type uint32;
          description
            "SRv6 Adjacency Algorithm";
        }
      }
      container bfd-tlv-information {
        leaf bfd-tlv-info-level {
          type string;
        }
      }
      container isis-adj-bfd-state-info {
        leaf isis-bfd-v4-sess-state {
          type string;
        }
        leaf isis-bfd-v6-sess-state {
          type string;
        }
        leaf isis-bfd-req-state {
          type string;
        }
        leaf isis-bfd-adj-usable {
          type string;
        }
      }
      list isis-adjacency-log {
        leaf adjacency-when {
          type string;
          description
            "Time at which the transition occurred";
        }
        leaf adjacency-state {
          type string;
          description
            "State of the adjacency";
        }
        leaf adjacency-event {
          type string;
          description
            "Event which triggered the transition";
        }
        leaf adjacency-down-reason {
          type string;
          description
            "Reason for the down transition event";
        }
      }
    }
  }

  rpc get-isis-adjacency-information {
    description
      "Show IS-IS adjacency database";

    input {
      choice daemon-select {
        case logical-system {
          leaf logical-system {
            type string;
            description
              "Name of logical system, or 'all'";
          }
        }
      }
      leaf igp-instance {
        type string;
        description
          "Regular expression for igp-instance names to match";
      }
      leaf verbosity_level {
        type enumeration {
          enum "brief" {
            description
              "Display brief output (default)";
          }
          enum "detail" {
            description
              "Display detailed output";
          }
          enum "extensive" {
            description
              "Display extensive output";
          }
        }
        default "brief";
      }
      leaf instance {
        type string;
        description
          "Name of IS-IS instance";
      }
      leaf system-id {
        type string;
        description
          "System ID of intermediate system";
      }
    }
    output {
      container isis-adjacency-information {
        uses isis-adjacency-information-block;
      }
    }
  }
}
