module junos-conf-root {
  namespace "http://yang.juniper.net/junos/conf/root";
  prefix jc;

  import junos-common-types {
    prefix jt;
    revision-date 2024-01-01;
  }

  organization
    "Juniper Networks, Inc.";
  contact
    "yang-support@juniper.net";
  description
    "Junos YANG module for configuration hierarchies.";

  revision 2024-01-01 {
    description
      "Junos: 20241218.202301_builder.r1463698";
  }

  grouping juniper-config {
    leaf rcsid {
      type string;
      description
        "Revision control system identifier";
    }
    leaf version {
      type string;
      description
        "Software version information";
    }
    leaf-list apply-groups {
      type string;
      ordered-by user;
      description
        "Groups from which to inherit configuration data";
    }
    list apply-macro {
      key "name";
      ordered-by user;
      description
        "Macro and parameters for commit script expansion";
      uses apply-macro-type;
    }
    container system {
      description
        "System parameters";
      uses juniper-system;
    }
    container services {
      description
        "System services";
      uses apply-advanced;
      container rpm {
        presence "enable rpm";
        description
          "Real-time performance monitoring";
        uses apply-advanced;
        container traceoptions {
          description
            "RMOPD trace options";
          uses rmopd-traceoptions;
        }
        leaf probe-limit {
          type union {
            type string {
              pattern "<.*>|$.*";
            }
            type uint32 {
              range "1 .. 2000";
            }
          }
          default "100";
          description
            "Maximum number of concurrent probes allowed";
        }
        container twamp {
          description
            "Two-way Active Measurement Protocol configuration";
          uses apply-advanced;
          container client {
            description
              "TWAMP client configuration";
            uses apply-advanced;
            list control-connection {
              key "name";
              ordered-by user;
              description
                "TWAMP control session configuration";
              leaf name {
                type string {
                  length "1 .. 32";
                }
                description
                  "Client name";
              }
              uses apply-advanced;
              container authentication-mode {
                description
                  "Authentication modes";
                uses apply-advanced;
                leaf none {
                  type empty;
                  description
                    "No authentication or encryption";
                }
              }
              leaf destination-interface {
                type union {
                  type jt:interface-name;
                  type string {
                    pattern "<.*>|$.*";
                  }
                }
                description
                  "Name of output interface for all test sessions";
              }
              leaf persistent-results {
                type empty;
                description
                  "Displays the old results along with present. Default disable";
              }
              leaf control-type {
                type enumeration {
                  enum "light" {
                    description
                      "No control connection to manage test sessions";
                  }
                  enum "managed" {
                    description
                      "Control connection will negotiate test sessions";
                  }
                }
                default "managed";
                description
                  "TWAMP control connection type";
              }
              leaf tcp-keepidle {
                type union {
                  type string {
                    pattern "<.*>|$.*";
                  }
                  type uint32 {
                    range "1 .. 600";
                  }
                }
                units "seconds";
                default "120";
                description
                  "Time to start TCP KEEPALIVEs on control connection (default 120)";
              }
              leaf tcp-keepintvl {
                type union {
                  type string {
                    pattern "<.*>|$.*";
                  }
                  type uint32 {
                    range "1 .. 600";
                  }
                }
                units "seconds";
                default "5";
                description
                  "Delay between succesive TCP KEEPALIVEs (default 5)";
              }
              leaf tcp-keepcnt {
                type union {
                  type string {
                    pattern "<.*>|$.*";
                  }
                  type uint32 {
                    range "1 .. 50";
                  }
                }
                default "6";
                description
                  "Number of TCP KEEPALIVEs sent (default 6)";
              }
              leaf destination-port {
                type union {
                  type string {
                    pattern "<.*>|$.*";
                  }
                  type uint16 {
                    range "862 .. 65535";
                  }
                }
                default "862";
                description
                  "TCP TWAMP client listening port for the test sessions. Default 862";
              }
              leaf history-size {
                type union {
                  type string {
                    pattern "<.*>|$.*";
                  }
                  type uint32 {
                    range "0 .. 512";
                  }
                }
                default "50";
                description
                  "Number of stored history entries";
              }
              leaf moving-average-size {
                type union {
                  type string {
                    pattern "<.*>|$.*";
                  }
                  type uint32 {
                    range "0 .. 512";
                  }
                }
                default "0";
                description
                  "Number of samples used for moving average";
              }
              leaf routing-instance {
                type string;
                description
                  "Routing instance used by the test sessions";
              }
              leaf source-address {
                type jt:ipv4addr;
                description
                  "Source address of TWAMP Control client";
              }
              leaf target-address {
                type jt:ipv4addr;
                description
                  "Destination IPv4 address of TWAMP responder";
              }
              leaf test-count {
                type union {
                  type string {
                    pattern "<.*>|$.*";
                  }
                  type uint32 {
                    range "0 .. 4294967290";
                  }
                }
                default "0";
                description
                  "Total number of test session iterations";
              }
              leaf test-interval {
                type union {
                  type string {
                    pattern "<.*>|$.*";
                  }
                  type uint16 {
                    range "1 .. 255";
                  }
                }
                units "seconds";
                default "1";
                description
                  "Delay between test session iterations";
              }
              container traps {
                description
                  "Trap to send if threshold is met or exceeded";
                uses apply-advanced;
                leaf test-iteration-done {
                  type empty;
                  description
                    "All test sessions configured under the control connection have completed an iteration";
                }
                leaf control-connection-closed {
                  type empty;
                  description
                    "Control connection closed";
                }
              }
              list test-session {
                key "name";
                ordered-by user;
                description
                  "Test session details";
                leaf name {
                  type string {
                    length "1 .. 32";
                  }
                  description
                    "Test session name";
                }
                uses apply-advanced;
                leaf source-address {
                  type jt:ipaddr;
                  description
                    "Source address of TWAMP Probes";
                }
                container target-address {
                  presence "enable target-address";
                  description
                    "Destination IPv4 or IPv6 address of TWAMP responder";
                  leaf address {
                    type jt:ipaddr;
                    mandatory true;
                    description
                      "Address of TWAMP session reflector";
                  }
                  leaf local-link {
                    type union {
                      type jt:interface-name;
                      type string {
                        pattern "<.*>|$.*";
                      }
                    }
                    description
                      "Link scope for IPv6 link-local address";
                  }
                }
                leaf destination-port {
                  type union {
                    type string {
                      pattern "<.*>|$.*";
                    }
                    type uint16 {
                      range "862 .. 65535";
                    }
                  }
                  default "862";
                  description
                    "Target port number for test";
                }
                leaf data-fill-with-zeros {
                  type empty;
                  description
                    "Fill contents of test packet with zeros";
                }
                leaf data-size {
                  type union {
                    type string {
                      pattern "<.*>|$.*";
                    }
                    type uint16 {
                      range "60 .. 1400";
                    }
                  }
                  default "60";
                  description
                    "Size of the data portion of the probes";
                }
                leaf dscp-code-points {
                  type string;
                  default "000000";
                  description
                    "Differentiated Services code point bits or alias used for TCP control and UDP TWAMP test packets";
                }
                leaf ttl {
                  type union {
                    type string {
                      pattern "<.*>|$.*";
                    }
                    type uint32 {
                      range "1 .. 254";
                    }
                  }
                  default "64";
                  description
                    "Time to Live (hop-limit) value for an RPM IPv4(IPv6) packet";
                }
                leaf probe-count {
                  type union {
                    type string {
                      pattern "<.*>|$.*";
                    }
                    type uint32 {
                      range "1 .. 4294967290";
                    }
                  }
                  default "1";
                  description
                    "Total number of probes per test";
                }
                leaf probe-interval {
                  type union {
                    type string {
                      pattern "<.*>|$.*";
                    }
                    type uint32 {
                      range "1 .. 255";
                    }
                  }
                  units "seconds";
                  default "1";
                  description
                    "Delay between two consecutive probes";
                }
                container thresholds {
                  presence "enable thresholds";
                  description
                    "TWAMP test threshold values. Set 0 to disable respective threshold";
                  uses apply-advanced;
                  leaf successive-loss {
                    type union {
                      type string {
                        pattern "<.*>|$.*";
                      }
                      type uint32 {
                        range "0 .. 15";
                      }
                    }
                    default "1";
                    description
                      "Successive probe loss count indicating probe failure";
                  }
                  leaf total-loss {
                    type union {
                      type string {
                        pattern "<.*>|$.*";
                      }
                      type uint32 {
                        range "0 .. 4294967290";
                      }
                    }
                    default "1";
                    description
                      "Total probe loss count indicating test failure";
                  }
                  leaf rtt {
                    type union {
                      type string {
                        pattern "<.*>|$.*";
                      }
                      type uint32 {
                        range "0 .. 60000000";
                      }
                    }
                    units "microseconds";
                    default "0";
                    description
                      "Maximum round trip time per probe";
                  }
                  leaf max-rtt {
                    type union {
                      type string {
                        pattern "<.*>|$.*";
                      }
                      type uint32 {
                        range "0 .. 60000000";
                      }
                    }
                    units "microseconds";
                    default "0";
                    status deprecated;
                    description
                      "Maximum round trip time per test";
                  }
                  leaf jitter-rtt {
                    type union {
                      type string {
                        pattern "<.*>|$.*";
                      }
                      type uint32 {
                        range "0 .. 60000000";
                      }
                    }
                    units "microseconds";
                    default "0";
                    description
                      "Maximum jitter per test";
                  }
                  leaf std-dev-rtt {
                    type union {
                      type string {
                        pattern "<.*>|$.*";
                      }
                      type uint32 {
                        range "0 .. 60000000";
                      }
                    }
                    units "microseconds";
                    default "0";
                    description
                      "Maximum standard deviation per test";
                  }
                  leaf egress-time {
                    type union {
                      type string {
                        pattern "<.*>|$.*";
                      }
                      type uint32 {
                        range "0 .. 60000000";
                      }
                    }
                    units "microseconds";
                    default "0";
                    description
                      "Maximum source to destination time per probe";
                  }
                  leaf ingress-time {
                    type union {
                      type string {
                        pattern "<.*>|$.*";
                      }
                      type uint32 {
                        range "0 .. 60000000";
                      }
                    }
                    units "microseconds";
                    default "0";
                    description
                      "Maximum destination to source time per probe";
                  }
                  leaf jitter-ingress {
                    type union {
                      type string {
                        pattern "<.*>|$.*";
                      }
                      type uint32 {
                        range "0 .. 60000000";
                      }
                    }
                    units "microseconds";
                    default "0";
                    description
                      "Maximum destination to source jitter per test";
                  }
                  leaf jitter-egress {
                    type union {
                      type string {
                        pattern "<.*>|$.*";
                      }
                      type uint32 {
                        range "0 .. 60000000";
                      }
                    }
                    units "microseconds";
                    default "0";
                    description
                      "Maximum source to destination jitter per test";
                  }
                  leaf std-dev-ingress {
                    type union {
                      type string {
                        pattern "<.*>|$.*";
                      }
                      type uint32 {
                        range "0 .. 60000000";
                      }
                    }
                    units "microseconds";
                    default "0";
                    description
                      "Maximum destination to source standard deviation per test";
                  }
                  leaf std-dev-egress {
                    type union {
                      type string {
                        pattern "<.*>|$.*";
                      }
                      type uint32 {
                        range "0 .. 60000000";
                      }
                    }
                    units "microseconds";
                    default "0";
                    description
                      "Maximum source to destination standard deviation per test";
                  }
                }
                container traps {
                  description
                    "Trap to send if threshold is met or exceeded";
                  uses apply-advanced;
                  leaf probe-failure {
                    type empty;
                    description
                      "Successive probe loss threshold reached";
                  }
                  leaf test-failure {
                    type empty;
                    description
                      "Total probe loss threshold reached";
                  }
                  leaf test-completion {
                    type empty;
                    description
                      "Test completed";
                  }
                  leaf rtt-exceeded {
                    type empty;
                    description
                      "Exceeded maximum round trip time threshold";
                  }
                  leaf max-rtt-exceeded {
                    type empty;
                    description
                      "Exceeded maximum round trip time threshold at the end of per test";
                  }
                  leaf std-dev-exceeded {
                    type empty;
                    description
                      "Exceeded round trip time standard deviation threshold";
                  }
                  leaf jitter-exceeded {
                    type empty;
                    description
                      "Exceeded jitter in round trip time threshold";
                  }
                  leaf ingress-time-exceeded {
                    type empty;
                    description
                      "Exceeded maximum ingress time threshold";
                  }
                  leaf ingress-std-dev-exceeded {
                    type empty;
                    description
                      "Exceeded ingress time standard deviation threshold";
                  }
                  leaf ingress-jitter-exceeded {
                    type empty;
                    description
                      "Exceeded jitter in ingress time threshold";
                  }
                  leaf egress-time-exceeded {
                    type empty;
                    description
                      "Exceeded maximum egress time threshold";
                  }
                  leaf egress-std-dev-exceeded {
                    type empty;
                    description
                      "Exceeded egress time standard deviation threshold";
                  }
                  leaf egress-jitter-exceeded {
                    type empty;
                    description
                      "Exceeded jitter in egress time threshold";
                  }
                }
              }
            }
          }
          container server {
            description
              "TWAMP server configuration";
            uses apply-advanced;
            leaf tcp-keepidle {
              type union {
                type string {
                  pattern "<.*>|$.*";
                }
                type uint32 {
                  range "1 .. 600";
                }
              }
              units "seconds";
              default "120";
              description
                "Time to start TCP KEEPALIVEs on control connection (default 120)";
            }
            leaf tcp-keepintvl {
              type union {
                type string {
                  pattern "<.*>|$.*";
                }
                type uint32 {
                  range "1 .. 600";
                }
              }
              units "seconds";
              default "5";
              description
                "Delay between succesive TCP KEEPALIVEs (default 5)";
            }
            leaf tcp-keepcnt {
              type union {
                type string {
                  pattern "<.*>|$.*";
                }
                type uint32 {
                  range "1 .. 50";
                }
              }
              default "6";
              description
                "Number of TCP KEEPALIVEs sent (default 6)";
            }
            list routing-instance-list {
              key "name";
              ordered-by user;
              description
                "List of allowed routing instances,not more than 100, along with ports";
              leaf name {
                type string;
                description
                  "Name of the routing instance";
              }
              uses apply-advanced;
              leaf port {
                type union {
                  type string {
                    pattern "<.*>|$.*";
                  }
                  type uint32 {
                    range "1 .. 65535";
                  }
                }
                mandatory true;
                description
                  "Port to be used by the routing instance";
              }
            }
            container authentication-mode {
              description
                "Authentication modes";
              uses apply-advanced;
              leaf none {
                type empty;
                description
                  "No authentication or encryption";
              }
              container authenticated {
                presence "enable authenticated";
                description
                  "Authenticated mode";
                leaf control-only {
                  type empty;
                  status deprecated;
                  description
                    "Authentication mode only for TWAMP control protocol";
                }
              }
              container encrypted {
                presence "enable encrypted";
                description
                  "Encrypted mode";
                leaf control-only {
                  type empty;
                  status deprecated;
                  description
                    "Encryption mode only for TWAMP control protocol";
                }
              }
              leaf control-only-encrypted {
                type empty;
                description
                  "Encrypted control and unauthenticated data mode";
              }
            }
            list authentication-key-chain {
              key "name";
              ordered-by user;
              description
                "Authentication key chain configuration";
              uses twamp-authentication-key-chain;
            }
            leaf server-inactivity-timeout {
              type union {
                type string {
                  pattern "<.*>|$.*";
                }
                type uint32 {
                  range "0 .. 30";
                }
              }
              units "minutes";
              default "15";
              description
                "Control packet idle timeout value in minutes, 0 to disable";
            }
            leaf max-connection-duration {
              type union {
                type string {
                  pattern "<.*>|$.*";
                }
                type uint32 {
                  range "0 .. 120";
                }
              }
              units "hours";
              default "0";
              description
                "Maximum Connection duration in hours, 0 to disable";
            }
            leaf maximum-sessions {
              type union {
                type string {
                  pattern "<.*>|$.*";
                }
                type uint32 {
                  range "1 .. 2048";
                }
              }
              default "64";
              description
                "Maximum number of test sessions for the server";
            }
            leaf maximum-sessions-per-connection {
              type union {
                type string {
                  pattern "<.*>|$.*";
                }
                type uint32 {
                  range "1 .. 1024";
                }
              }
              description
                "Maximum number of test sessions per client connection";
            }
            leaf maximum-connections {
              type union {
                type string {
                  pattern "<.*>|$.*";
                }
                type uint32 {
                  range "1 .. 1000";
                }
              }
              default "64";
              description
                "Maximum number of connections for the server";
            }
            leaf maximum-connections-per-client {
              type union {
                type string {
                  pattern "<.*>|$.*";
                }
                type uint32 {
                  range "1 .. 500";
                }
              }
              description
                "Maximum number of server connections per client";
            }
            leaf port {
              type union {
                type string {
                  pattern "<.*>|$.*";
                }
                type uint32 {
                  range "1 .. 65535";
                }
              }
              default "862";
              description
                "TWAMP server listening port";
            }
            list client-list {
              key "name";
              ordered-by user;
              description
                "List of allowed clients";
              leaf name {
                type string {
                  length "1 .. 127";
                }
                description
                  "Name of client list";
              }
              uses apply-advanced;
              list address {
                key "name";
                ordered-by user;
                description
                  "IPv4 prefix of TWAMP client";
                leaf name {
                  type jt:ipv4prefix;
                  description
                    "IPv4 prefix of TWAMP client";
                }
                uses apply-advanced;
              }
            }
            container light {
              presence "enable light";
              description
                "Enable TWAMP server for light control on the default port";
              uses apply-advanced;
              leaf-list port {
                type union {
                  type uint16;
                  type string {
                    pattern "<.*>|$.*";
                  }
                }
                max-elements 1000;
                ordered-by user;
                description
                  "UDP ports reflecting TWAMP light test packets";
              }
            }
          }
        }
      }
      container analytics {
        presence "enable analytics";
        description
          "Traffic analytics configuration options";
        uses apply-advanced;
        container zero-suppression {
          description
            "Configure suppression of zeros for GRPC sensors";
          uses apply-advanced;
          leaf no-zero-suppression {
            type empty;
            mandatory true;
            description
              "Disable zero suppression";
          }
        }
        list streaming-server {
          key "name";
          ordered-by user;
          description
            "Define Telemetry data servers";
          leaf name {
            type string {
              length "1 .. 128";
            }
            description
              "Telemetry App server Name";
          }
          uses apply-advanced;
          leaf remote-address {
            type jt:host;
            description
              "Telemetry server IP address";
          }
          leaf remote-port {
            type union {
              type uint16;
              type string {
                pattern "<.*>|$.*";
              }
            }
            description
              "Telemetry server Port";
          }
          leaf transport {
            type enumeration {
              enum "udp" {
                description
                  "Use UDP transport protocol";
              }
              enum "grpc" {
                description
                  "Use grpc transport";
              }
            }
            description
              "Telemetry export transport protocol";
          }
          leaf dialout {
            type empty;
            description
              "Supports dynamic dialout subscriptions";
          }
        }
        list export-profile {
          key "name";
          ordered-by user;
          description
            "Telemetry export profile name";
          leaf name {
            type string {
              length "1 .. 128";
            }
            description
              "Telemetry export profile name";
          }
          uses apply-advanced;
          leaf local-address {
            type jt:ipaddr;
            description
              "Source address for exported packets";
          }
          leaf local-port {
            type union {
              type uint16;
              type string {
                pattern "<.*>|$.*";
              }
            }
            description
              "Source port for exported packets";
          }
          leaf dscp {
            type union {
              type string {
                pattern "<.*>|$.*";
              }
              type uint8 {
                range "0 .. 63";
              }
            }
            description
              "DSCP value for exported packets";
          }
          leaf forwarding-class {
            type string {
              length "1 .. 64";
            }
            description
              "Forwarding-class for exported packets, applicable only for PFE sensors";
          }
          leaf reporting-rate {
            type union {
              type string {
                pattern "<.*>|$.*";
              }
              type uint32 {
                range "0 .. 86400";
              }
            }
            units "seconds";
            description
              "Telemetry interval in seconds, max 24 hours";
          }
          leaf payload-size {
            type union {
              type string {
                pattern "<.*>|$.*";
              }
              type uint32 {
                range "1400 .. 9192";
              }
            }
            units "bytes";
            default "5000";
            description
              "Telemetry payload size";
          }
          leaf format {
            type enumeration {
              enum "gpb" {
                description
                  "Use gpb format";
              }
              enum "gpb-gnmi" {
                description
                  "Use gnmi format for gpb messages";
              }
              enum "json-gnmi" {
                description
                  "Use gnmi format for json messages";
              }
            }
            description
              "Telemetry export record format";
          }
          leaf transport {
            type enumeration {
              enum "udp" {
                description
                  "Use UDP transport protocol";
              }
              enum "grpc" {
                description
                  "Use grpc transport";
              }
            }
            description
              "Telemetry export transport protocol";
          }
          leaf routing-instance {
            type string;
            description
              "Routing instance to be used for grpc transport";
          }
        }
        list sensor {
          key "name";
          ordered-by user;
          description
            "Define Telemetry sensors";
          leaf name {
            type string {
              length "1 .. 128";
            }
            description
              "Name of the sensor";
          }
          uses apply-advanced;
          leaf-list server-name {
            type string {
              length "1 .. 128";
            }
            ordered-by user;
            description
              "Define Telemetry server ";
          }
          leaf export-name {
            type string {
              length "1 .. 128";
            }
            description
              "Define Telemetry export profiles";
          }
          leaf polling-interval {
            type union {
              type string {
                pattern "<.*>|$.*";
              }
              type uint32 {
                range "1 .. 4294967295";
              }
            }
            units "nanoseconds";
            status deprecated;
            description
              "Define sensor polling interval in nano secs (1 .. 4294967295)";
          }
          leaf resource {
            type string {
              length "1 .. 1024";
            }
            mandatory true;
            description
              "System resource identifier string";
          }
          leaf resource-filter {
            type string {
              length "1 .. 1024";
            }
            description
              "Regexp for filtering resource instances (1 .. 1024)";
          }
          leaf subscription-id {
            type union {
              type uint64;
              type string {
                pattern "<.*>|$.*";
              }
            }
            description
              "Subscription ID (Used internally to group sensors)";
          }
          leaf suppress-zeros {
            type empty;
            description
              "Supress zeros while data export";
          }
          leaf reporting-rate {
            type union {
              type string {
                pattern "<.*>|$.*";
              }
              type uint32 {
                range "0 .. 86400";
              }
            }
            units "seconds";
            description
              "Telemetry interval in seconds, max 24 hours";
          }
          leaf-list end-of-sync-identifiers {
            type union {
              type string {
                pattern "<.*>|$.*";
              }
              type uint32 {
                range "1 .. 64";
              }
            }
            max-elements 30;
            ordered-by user;
            description
              "Set of end-of-syncs for this sensor";
          }
          leaf target-defined {
            type empty;
            description
              "Allow target to decide periodic, on-change or mix";
          }
          leaf life-time {
            type enumeration {
              enum "long-lived" {
                description
                  "A long-lived subscription";
              }
              enum "one-off" {
                description
                  "An one-off subscription";
              }
            }
            description
              "Denotes sensor life-time";
          }
        }
        container agent {
          description
            "Configure analytics agent";
          uses apply-advanced;
          list service-agents {
            key "name";
            ordered-by user;
            description
              "Analytics service agent configuration";
            leaf name {
              type string;
              description
                "Analytics service agent name";
            }
            uses apply-advanced;
            container inputs {
              description
                "List of input plugins";
              uses apply-advanced;
              container input-jti-ipfix {
                presence "enable input-jti-ipfix";
                description
                  "Junos grpc IPFIX group plugin";
                uses apply-advanced;
                container parameters {
                  presence "enable parameters";
                  uses apply-advanced;
                  list record-group {
                    key "name";
                    max-elements 10;
                    ordered-by user;
                    description
                      "Group sensors";
                    leaf name {
                      type string;
                      description
                        "Group sensors";
                    }
                    uses apply-advanced;
                    leaf reporting-interval {
                      type union {
                        type string {
                          pattern "<.*>|$.*";
                        }
                        type uint32 {
                          range "60 .. 86400";
                        }
                      }
                      default "900";
                      description
                        "Reporting-interval";
                    }
                    leaf-list record {
                      type enumeration {
                        enum "port-statistics" {
                          description
                            "Port statistics";
                        }
                        enum "address-pool-utilization" {
                          description
                            "Address pool utilization";
                        }
                        enum "dhcpv4-server-stats" {
                          description
                            "Dhcpv4 server statistics";
                        }
                        enum "thermal" {
                          description
                            "Thermal statistics";
                        }
                        enum "chassis-inventory" {
                          description
                            "Chassis inventory details";
                        }
                        enum "chassis-power" {
                          description
                            "Chassis power details";
                        }
                        enum "resource-utilization" {
                          description
                            "Resource utilization details";
                        }
                        enum "uptime" {
                          description
                            "Uptime value";
                        }
                        enum "subscriber-statistics" {
                          description
                            "Subscriber statistics";
                        }
                        enum "interface-metadata" {
                          description
                            "Interface metadata details";
                        }
                        enum "interface-queue-statistics" {
                          description
                            "Interface Queue statistics";
                        }
                      }
                      ordered-by user;
                      description
                        "Ipfix record name";
                    }
                  }
                }
              }
              container input-ipfix {
                presence "enable input-ipfix";
                description
                  "Junos IPFIX Mediator input plugin";
                uses apply-advanced;
                container parameters {
                  presence "enable parameters";
                  description
                    "List of IPFIX parameters";
                  uses apply-advanced;
                  leaf tcp-port {
                    type union {
                      type uint16;
                      type string {
                        pattern "<.*>|$.*";
                      }
                    }
                    description
                      "Listening TCP Port for IPFIX Mediator";
                  }
                  leaf maximum-connections {
                    type union {
                      type string {
                        pattern "<.*>|$.*";
                      }
                      type uint32 {
                        range "1 .. 500";
                      }
                    }
                    description
                      "Maximum TCP Connections 1..500";
                  }
                  leaf vrf-name {
                    type string;
                    description
                      "VRF name on which IPFIX packets are accepted";
                  }
                }
              }
              container analytics {
                presence "enable analytics";
                description
                  "Junos Telemetry plugin";
                uses apply-advanced;
                container parameters {
                  presence "enable parameters";
                  description
                    "List of key:value parameters";
                  uses apply-advanced;
                  leaf sample-frequency {
                    type union {
                      type string {
                        pattern "<.*>|$.*";
                      }
                      type uint32 {
                        range "0 .. 86400";
                      }
                    }
                    units "seconds";
                    default "5";
                    description
                      "Interval for sensor data in seconds, max 24 hours";
                  }
                  leaf sensors {
                    type string {
                      length "1 .. 2048";
                    }
                    mandatory true;
                    description
                      "Space separated list of sensor paths";
                  }
                  leaf generate-tags {
                    type empty;
                    description
                      "Enable generation of tags";
                  }
                }
              }
            }
            list outputs {
              key "name";
              max-elements 1;
              ordered-by user;
              description
                "List of output plugins";
              uses output-plugin;
            }
          }
          container traceoptions {
            presence "enable traceoptions";
            uses apply-advanced;
            leaf flag {
              type enumeration {
                enum "trace" {
                  description
                    "Log level TRACE, will trace everything";
                }
                enum "debug" {
                  description
                    "Log level DEBUG, will trace debug messages";
                }
                enum "info" {
                  description
                    "Log level INFO";
                }
                enum "error" {
                  description
                    "Log level ERROR, will trace all error messages";
                }
              }
              description
                "Set log level for tracing";
            }
            leaf filename {
              type string;
              default "ntf-agent.log";
              description
                "Configure filename for trace messages";
            }
          }
        }
        container traceoptions {
          description
            "Traffic analytics trace options";
          uses apply-advanced;
          leaf no-remote-trace {
            type empty;
            description
              "Disable remote tracing";
          }
          container file {
            description
              "Trace file information";
            leaf filename {
              type string {
                length "1 .. 1024";
              }
              description
                "Name of file in which to write trace information";
            }
            leaf size {
              type string;
              description
                "Maximum trace file size";
            }
            leaf files {
              type union {
                type string {
                  pattern "<.*>|$.*";
                }
                type uint32 {
                  range "2 .. 1000";
                }
              }
              default "3";
              description
                "Maximum number of trace files";
            }
            choice world-readable-choice {
              leaf world-readable {
                type empty;
                description
                  "Allow any user to read the log file";
              }
              leaf no-world-readable {
                type empty;
                description
                  "Don't allow any user to read the log file";
              }
            }
            leaf match {
              type jt:regular-expression;
              description
                "Regular expression for lines to be logged";
            }
          }
          list flag {
            key "name";
            description
              "Tracing parameters";
            leaf name {
              type enumeration {
                enum "all" {
                  description
                    "Trace configuration events";
                }
                enum "configuration" {
                  description
                    "Log configuration events";
                }
                enum "rtsock" {
                  description
                    "Trace rtsock message events";
                }
                enum "client-server" {
                  description
                    "Trace client-server events";
                }
                enum "interface" {
                  description
                    "Trace interface update events";
                }
                enum "xmlproxy" {
                  description
                    "Trace xmlproxy events";
                }
              }
            }
            leaf disable {
              type empty;
              description
                "Disable this trace flag";
            }
          }
        }
        list export-profiles {
          key "name";
          ordered-by user;
          description
            "Mapping of export-profiles to collectors";
          leaf name {
            type string {
              length "1 .. 64";
            }
            description
              "Export profile name";
          }
          uses apply-advanced;
          leaf stream-format {
            type enumeration {
              enum "gpb" {
                description
                  "Google protocol buffer format";
              }
              enum "json" {
                description
                  "Java script object notation format";
              }
              enum "csv" {
                description
                  "Comma separated value";
              }
              enum "tsv" {
                description
                  "Tab separated value";
              }
            }
            default "gpb";
            description
              "Streaming data format";
          }
          container interface {
            presence "enable interface";
            description
              "Interface specific information";
            uses apply-advanced;
            leaf information {
              type empty;
              description
                "Enable streaming of interface information";
            }
            container statistics {
              description
                "Type of statistics to stream";
              uses apply-advanced;
              leaf traffic {
                type empty;
                description
                  "Enable streaming of interface traffic statistics";
              }
              leaf queue {
                type empty;
                description
                  "Enable streaming of interface queue statistics";
              }
            }
            container status {
              description
                "Type of statistics to stream";
              uses apply-advanced;
              leaf link {
                type empty;
                description
                  "Enable streaming of interface link status";
              }
              leaf traffic {
                type empty;
                description
                  "Enable streaming of interface traffic status";
              }
              leaf queue {
                type empty;
                description
                  "Enable streaming of interface queue status";
              }
            }
          }
          container system {
            presence "enable system";
            description
              "Interface specific information";
            uses apply-advanced;
            leaf information {
              type empty;
              description
                "Enable streaming of system information";
            }
            container status {
              description
                "Type of statistics to stream";
              uses apply-advanced;
              leaf traffic {
                type empty;
                description
                  "Enable streaming of system traffic status";
              }
              leaf queue {
                type empty;
                description
                  "Enable streaming of system queue status";
              }
            }
          }
        }
        list resource-profiles {
          key "name";
          ordered-by user;
          description
            "Mapping of resource profiles to interfaces/queues/system";
          leaf name {
            type string {
              length "1 .. 64";
            }
            description
              "Export profile name";
          }
          uses apply-advanced;
          choice queue-monitoring-choice {
            leaf queue-monitoring {
              type empty;
              description
                "Enable queue statistics monitoring";
            }
            leaf no-queue-monitoring {
              type empty;
              description
                "Don't enable queue statistics monitoring";
            }
          }
          choice traffic-monitoring-choice {
            leaf traffic-monitoring {
              type empty;
              description
                "Enable traffic statistics monitoring";
            }
            leaf no-traffic-monitoring {
              type empty;
              description
                "Don't enable traffic statistics monitoring";
            }
          }
          container depth-threshold {
            description
              "Depth threshold configuration";
            leaf high {
              type union {
                type string {
                  pattern "<.*>|$.*";
                }
                type uint32 {
                  range "1 .. 1250000000";
                }
              }
              units "bytes";
              mandatory true;
              description
                "High queue depth threshold";
            }
            leaf low {
              type union {
                type string {
                  pattern "<.*>|$.*";
                }
                type uint32 {
                  range "1 .. 1250000000";
                }
              }
              units "bytes";
              mandatory true;
              description
                "Low queue depth threshold";
            }
          }
          container latency-threshold {
            description
              "Latency threshold configuration";
            leaf high {
              type union {
                type string {
                  pattern "<.*>|$.*";
                }
                type uint32 {
                  range "1 .. 100000000";
                }
              }
              units "nanoseconds";
              mandatory true;
              description
                "High latency threshold";
            }
            leaf low {
              type union {
                type string {
                  pattern "<.*>|$.*";
                }
                type uint32 {
                  range "1 .. 100000000";
                }
              }
              units "nanoseconds";
              mandatory true;
              description
                "Low latency threshold";
            }
          }
        }
        container resource {
          presence "enable resource";
          uses apply-advanced;
          container system {
            description
              "System configuration options";
            uses apply-advanced;
            leaf resource-profile {
              type string {
                length "1 .. 64";
              }
              description
                "Resouce profile name";
            }
            container polling-interval {
              description
                "Polling interval";
              uses apply-advanced;
              leaf traffic-monitoring {
                type union {
                  type string {
                    pattern "<.*>|$.*";
                  }
                  type uint32 {
                    range "1 .. 300";
                  }
                }
                units "seconds";
                description
                  "Traffic statistics polling interval";
              }
              leaf queue-monitoring {
                type union {
                  type string {
                    pattern "<.*>|$.*";
                  }
                  type uint32 {
                    range "1 .. 1000";
                  }
                }
                units "milliseconds";
                description
                  "Queue statistics polling interval";
              }
            }
          }
          container interfaces {
            description
              "Interface configuration options";
            uses apply-advanced;
            list interface {
              key "name";
              uses interface_type;
            }
          }
        }
        container collector {
          description
            "Remote streaming servers configuration options";
          uses apply-advanced;
          container local {
            description
              "Remote streaming servers configuration options";
            uses apply-advanced;
            container file {
              description
                "Log file information";
              leaf filename {
                type jt:filename;
                description
                  "Name of file in which to write log information";
              }
              leaf size {
                type string;
                description
                  "Maximum log file size";
              }
              leaf files {
                type union {
                  type string {
                    pattern "<.*>|$.*";
                  }
                  type uint32 {
                    range "2 .. 1000";
                  }
                }
                default "10";
                description
                  "Maximum number of trace files";
              }
            }
          }
          list address {
            key "name";
            description
              "IP address of remote server";
            leaf name {
              type jt:ipaddr;
              description
                "IP address";
            }
            uses apply-advanced;
            list port {
              key "name";
              description
                "Remote streaming server port number";
              leaf name {
                type union {
                  type string {
                    pattern "<.*>|$.*";
                  }
                  type uint32 {
                    range "1 .. 65535";
                  }
                }
                description
                  "Port number";
              }
              uses apply-advanced;
              list transport {
                key "name";
                description
                  "Transport protocol";
                leaf name {
                  type enumeration {
                    enum "tcp" {
                      description
                        "Transmission control protocol";
                    }
                    enum "udp" {
                      description
                        "User datagram protocol";
                    }
                  }
                }
                uses apply-advanced;
                leaf export-profile {
                  type string {
                    length "1 .. 64";
                  }
                  description
                    "Export profile name";
                }
              }
            }
          }
        }
      }
    }
    container security {
      description
        "Security configuration";
      uses apply-advanced;
      container alarms {
        description
          "Configure security alarms";
        uses apply-advanced;
        container audible {
          presence "enable audible";
          description
            "Beep when new security alarms arrive";
          uses apply-advanced;
          leaf continuous {
            type empty;
            description
              "Keep beeping until all security alarms have been cleared";
          }
        }
        container potential-violation {
          description
            "Configure potential security violations";
          uses apply-advanced;
          leaf authentication {
            type union {
              type string {
                pattern "<.*>|$.*";
              }
              type uint32 {
                range "2 .. 10";
              }
            }
            description
              "Raise alarm for specified number of authentication failures";
          }
          leaf cryptographic-self-test {
            type empty;
            description
              "Raise alarm for cryptographic self test failures";
          }
          leaf key-generation-self-test {
            type empty;
            description
              "Raise alarm for key generation self test failures";
          }
          leaf non-cryptographic-self-test {
            type empty;
            description
              "Raise alarm for non-cryptographic self test failures";
          }
          container policy {
            description
              "Raise alarm for flow policy violations";
          }
          container replay-attacks {
            presence "enable replay-attacks";
            description
              "No. of Replay attacks before which an alarm needs to be raised";
            uses apply-advanced;
            leaf threshold {
              type union {
                type string {
                  pattern "<.*>|$.*";
                }
                type uint32 {
                  range "1 .. 1000000000";
                }
              }
              default "1000";
              description
                "Replay threshold value";
            }
          }
          leaf security-log-percent-full {
            type union {
              type string {
                pattern "<.*>|$.*";
              }
              type uint8 {
                range "0 .. 100";
              }
            }
            description
              "Raise alarm when security log exceeds this percent capacity";
          }
        }
      }
      container log {
        description
          "Configure auditable security logs";
        uses log-object;
      }
      container traceoptions {
        description
          "Trace options for IPSec key management";
        uses security-traceoptions;
      }
      container ipsec {
        description
          "IPSec configuration";
        uses security-ipsec-vpn;
      }
      container certificates {
        description
          "X.509 certificate configuration";
        uses apply-advanced;
        list local {
          key "name";
          ordered-by user;
          description
            "Local X.509 certificate configuration";
          uses certificate-object;
        }
        leaf path-length {
          type union {
            type string {
              pattern "<.*>|$.*";
            }
            type uint32 {
              range "0 .. 15";
            }
          }
          default "15";
          description
            "Maximum certificate path length";
        }
        leaf maximum-certificates {
          type union {
            type string {
              pattern "<.*>|$.*";
            }
            type uint32 {
              range "64 .. 4294967295";
            }
          }
          default "1024";
          description
            "Maximum number of certificates to cache";
        }
        leaf cache-size {
          type string;
          units "bytes";
          description
            "Maximum size of certificate cache";
        }
        leaf cache-timeout-negative {
          type union {
            type string {
              pattern "<.*>|$.*";
            }
            type uint32 {
              range "10 .. 4294967295";
            }
          }
          default "20";
          description
            "Time in seconds to cache negative responses";
        }
        leaf enrollment-retry {
          type union {
            type string {
              pattern "<.*>|$.*";
            }
            type uint32 {
              range "0 .. 1080";
            }
          }
          description
            "Number of retry attempts for an enrollment request";
        }
        list certification-authority {
          key "name";
          ordered-by user;
          description
            "CA X.509 certificate configuration";
          leaf name {
            type string;
            description
              "CA profile name";
          }
          uses apply-advanced;
          leaf ca-name {
            type string;
            description
              "CA name";
          }
          leaf file {
            type string;
            description
              "File to read certificate from";
          }
          leaf crl {
            type string;
            description
              "File to read crl from";
          }
          leaf enrollment-url {
            type string;
            description
              "URL";
          }
          leaf ldap-url {
            type string;
            description
              "URL";
          }
          leaf encoding {
            type enumeration {
              enum "binary" {
                description
                  "DER encoding";
              }
              enum "pem" {
                description
                  "Privacy-enhanced-mail encoding, base64";
              }
            }
            default "binary";
            description
              "Encoding to use for certificate or CRL on disk";
          }
        }
      }
    }
    container interfaces {
      description
        "Interface configuration";
      uses apply-advanced;
      container traceoptions {
        description
          "Interface trace options";
        uses apply-advanced;
        container file {
          description
            "Trace file options";
          leaf filename {
            type string {
              length "1 .. 1024";
            }
            description
              "Name of file in which to write trace information";
          }
          leaf replace {
            type empty;
            status deprecated;
            description
              "Replace trace file rather than appending to it";
          }
          leaf size {
            type string;
            description
              "Maximum trace file size";
          }
          leaf files {
            type union {
              type string {
                pattern "<.*>|$.*";
              }
              type uint32 {
                range "2 .. 1000";
              }
            }
            default "10";
            description
              "Maximum number of trace files";
          }
          leaf no-stamp {
            type empty;
            status deprecated;
            description
              "Do not timestamp trace file";
          }
          choice world-readable-choice {
            leaf world-readable {
              type empty;
              description
                "Allow any user to read the log file";
            }
            leaf no-world-readable {
              type empty;
              description
                "Don't allow any user to read the log file";
            }
          }
        }
        list flag {
          key "name";
          description
            "Tracing parameters";
          leaf name {
            type enumeration {
              enum "all" {
                description
                  "Enable all configuration logging";
              }
              enum "kernel" {
                description
                  "Log configuration IPC messages to kernel";
              }
              enum "error" {
                description
                  "Log error events";
              }
              enum "warning" {
                description
                  "Log warning events";
              }
              enum "notice" {
                description
                  "Log notification events";
              }
              enum "info" {
                description
                  "Log informations";
              }
              enum "debugging" {
                description
                  "Log debug events";
              }
            }
          }
        }
      }
      list interface {
        key "name";
        uses interfaces_type;
      }
    }
    container forwarding-options {
      presence "enable forwarding-options";
    }
    container event-options {
      description
        "Event processing configuration";
      uses apply-advanced;
      leaf max-policies {
        type union {
          type string {
            pattern "<.*>|$.*";
          }
          type uint32 {
            range "0 .. 20";
          }
        }
        default "15";
        description
          "Number of policies that can be executed simultaneously";
      }
      list generate-event {
        key "name";
        max-elements 10;
        ordered-by user;
        description
          "Generate an internal event";
        leaf name {
          type string {
            length "1 .. 63";
          }
          description
            "Name of the event to be generated";
        }
        choice time_choice {
          case case_1 {
            leaf time-of-day {
              type jt:time-of-day;
              description
                "Time of day at which to generate event (hh:mm:ss)";
            }
          }
          case case_2 {
            leaf time-interval {
              type union {
                type string {
                  pattern "<.*>|$.*";
                }
                type uint32 {
                  range "60 .. 2592000";
                }
              }
              units "seconds";
              description
                "Frequency for generating the event";
            }
          }
        }
        leaf start-time {
          type jt:time;
          description
            "Start-time to generate event (yyyy-mm-dd.hh:mm)";
        }
        leaf no-drift {
          type empty;
          description
            "Avoid event generation delay propagating to next event";
        }
      }
      list policy {
        key "name";
        ordered-by user;
        description
          "Event policy for event policy manager";
        leaf name {
          type string {
            length "1 .. 63";
          }
          description
            "Name of policy";
        }
        uses apply-advanced;
        leaf-list events {
          type string;
          ordered-by user;
          description
            "List of events that trigger this policy";
        }
        list within {
          key "name";
          ordered-by user;
          description
            "List of events correlated with trigering events";
          leaf name {
            type union {
              type string {
                pattern "<.*>|$.*";
              }
              type uint32 {
                range "1 .. 604800";
              }
            }
            units "seconds";
            description
              "Time within which correlated events must occur (or not)";
          }
          uses apply-advanced;
          container trigger {
            description
              "Correlate events based on the number of occurrences";
            choice when {
              case case_1 {
                leaf until {
                  type empty;
                  description
                    "Trigger when occurrences of triggering event < 'count'";
                }
              }
              case case_2 {
                leaf on {
                  type empty;
                  description
                    "Trigger when occurrences of triggering event = 'count'";
                }
              }
              case case_3 {
                leaf after {
                  type empty;
                  description
                    "Trigger when occurrences of triggering event > 'count'";
                }
              }
            }
            leaf count {
              type union {
                type uint32;
                type string {
                  pattern "<.*>|$.*";
                }
              }
              mandatory true;
              description
                "Number of occurrences of triggering event";
            }
          }
          leaf-list events {
            type string;
            ordered-by user;
            description
              "List of events that must occur within time interval";
          }
          container not {
            description
              "Events must not occur within time interval";
            leaf-list events {
              type string;
              ordered-by user;
              description
                "List of events that must not occur within time interval";
            }
          }
        }
        list attributes-match {
          key "from-event-attribute condition to-event-attribute-value";
          ordered-by user;
          description
            "List of attributes to compare for two events";
          leaf from-event-attribute {
            type string;
            description
              "First attribute to compare";
          }
          leaf condition {
            type enumeration {
              enum "equals" {
                description
                  "Attributes match";
              }
              enum "starts-with" {
                description
                  "Second attribute starts with first attribute value";
              }
              enum "matches" {
                description
                  "Regular expression matching the first attribute value";
              }
            }
            description
              "Relationship that must hold between attributes";
          }
          leaf to-event-attribute-value {
            type string;
            description
              "Second attribute or value to compare";
          }
        }
        container then {
          description
            "List of actions to perform when policy matches";
          uses apply-advanced;
          leaf ignore {
            type empty;
            description
              "Do not log event or perform any other action";
          }
          list upload {
            key "filename destination";
            ordered-by user;
            description
              "Upload file to specified destination";
            leaf filename {
              type string;
              description
                "Name of file to upload";
            }
            leaf destination {
              type string;
              description
                "Location to which to output file";
            }
            uses apply-advanced;
            leaf user-name {
              type string;
              description
                "User under whose privileges upload action will execute";
            }
            leaf transfer-delay {
              type union {
                type uint32;
                type string {
                  pattern "<.*>|$.*";
                }
              }
              units "seconds";
              description
                "Delay before uploading file to the destination";
            }
            container retry-count {
              description
                "Upload output-filename retry attempt count";
              leaf retry {
                type union {
                  type string {
                    pattern "<.*>|$.*";
                  }
                  type uint8 {
                    range "0 .. 10";
                  }
                }
                mandatory true;
                description
                  "Number of retry attempts";
              }
              leaf retry-interval {
                type union {
                  type uint32;
                  type string {
                    pattern "<.*>|$.*";
                  }
                }
                units "seconds";
                mandatory true;
                description
                  "Time interval between each retry";
              }
            }
          }
          container change-configuration {
            description
              "Change configuration";
            uses apply-advanced;
            container retry {
              description
                "Change configuration retry attempt count";
              leaf count {
                type union {
                  type string {
                    pattern "<.*>|$.*";
                  }
                  type uint8 {
                    range "0 .. 10";
                  }
                }
                mandatory true;
                description
                  "Number of retry attempts";
              }
              leaf interval {
                type union {
                  type uint32;
                  type string {
                    pattern "<.*>|$.*";
                  }
                }
                units "seconds";
                mandatory true;
                description
                  "Time interval between each retry";
              }
            }
            list commands {
              key "name";
              ordered-by user;
              description
                "List of configuration commands";
              leaf name {
                type string;
                description
                  "Configuration command to issue";
              }
              uses apply-advanced;
            }
            leaf user-name {
              type string;
              description
                "User under whose privileges configuration should be changed";
            }
            container commit-options {
              description
                "List of commit options";
              uses apply-advanced;
              container check {
                presence "enable check";
                description
                  "Check correctness of syntax; do not apply changes";
                uses apply-advanced;
                leaf synchronize {
                  type empty;
                  description
                    "Synchronize commit on both Routing Engines";
                }
              }
              leaf synchronize {
                type empty;
                description
                  "Synchronize commit on both Routing Engines";
              }
              leaf force {
                type empty;
                description
                  "Force commit on other Routing Engine (ignore warnings)";
              }
              leaf log {
                type string {
                  length "1 .. 512";
                }
                description
                  "Message to write to commit log";
              }
            }
          }
          container execute-commands {
            description
              "Issue one or more CLI commands";
            uses apply-advanced;
            list commands {
              key "name";
              ordered-by user;
              description
                "List of CLI commands to issue";
              leaf name {
                type string;
                description
                  "CLI command to issue";
              }
              uses apply-advanced;
            }
            leaf user-name {
              type string;
              description
                "User under whose privileges command will execute";
            }
            leaf output-filename {
              type string;
              description
                "Name of file in which to write command output";
            }
            list destination {
              key "name";
              max-elements 1;
              ordered-by user;
              description
                "Location to which to upload command output";
              leaf name {
                type string;
                description
                  "Location to which to upload command output";
              }
              uses apply-advanced;
              leaf transfer-delay {
                type union {
                  type uint32;
                  type string {
                    pattern "<.*>|$.*";
                  }
                }
                units "seconds";
                description
                  "Delay before uploading file to the destination";
              }
              container retry-count {
                description
                  "Upload output-filename retry attempt count";
                leaf retry {
                  type union {
                    type string {
                      pattern "<.*>|$.*";
                    }
                    type uint8 {
                      range "0 .. 10";
                    }
                  }
                  mandatory true;
                  description
                    "Number of retry attempts";
                }
                leaf retry-interval {
                  type union {
                    type uint32;
                    type string {
                      pattern "<.*>|$.*";
                    }
                  }
                  units "seconds";
                  mandatory true;
                  description
                    "Time interval between each retry";
                }
              }
            }
            leaf output-format {
              type enumeration {
                enum "text" {
                  description
                    "Formatted ASCII text";
                }
                enum "xml" {
                  description
                    "JUNOS XML tags";
                }
              }
              default "xml";
              description
                "Format of output from CLI commands";
            }
          }
          list event-script {
            key "name";
            ordered-by user;
            description
              "Invoke event scripts";
            leaf name {
              type string {
                length "1 .. 254";
              }
              description
                "Local filename of the script file";
            }
            uses apply-advanced;
            list arguments {
              key "name";
              ordered-by user;
              description
                "Command line argument to the script";
              leaf name {
                type string {
                  length "1 .. 254";
                }
                description
                  "Name of the argument";
              }
              leaf value {
                type string;
                mandatory true;
                description
                  "Value of the argument";
              }
            }
            leaf user-name {
              type string;
              description
                "User under whose privileges event script will execute";
            }
            leaf output-filename {
              type string;
              description
                "Name of file in which to write event script output";
            }
            list destination {
              key "name";
              max-elements 1;
              ordered-by user;
              description
                "Location to which to upload event script output";
              leaf name {
                type string;
                description
                  "Location to which to upload event script output";
              }
              uses apply-advanced;
              leaf transfer-delay {
                type union {
                  type uint32;
                  type string {
                    pattern "<.*>|$.*";
                  }
                }
                units "seconds";
                description
                  "Delay before uploading files";
              }
              container retry-count {
                description
                  "Upload output-filename retry attempt count";
                leaf retry {
                  type union {
                    type string {
                      pattern "<.*>|$.*";
                    }
                    type uint8 {
                      range "0 .. 10";
                    }
                  }
                  mandatory true;
                  description
                    "Number of retry attempts";
                }
                leaf retry-interval {
                  type union {
                    type uint32;
                    type string {
                      pattern "<.*>|$.*";
                    }
                  }
                  units "seconds";
                  mandatory true;
                  description
                    "Time interval between each retry";
                }
              }
            }
            leaf output-format {
              type enumeration {
                enum "text" {
                  description
                    "Formatted ASCII text";
                }
                enum "xml" {
                  description
                    "JUNOS XML tags";
                }
              }
              description
                "Format of output from event-script";
            }
          }
        }
      }
      container event-script {
        description
          "Configure event-scripts";
        uses apply-advanced;
        leaf optional {
          type empty;
          description
            "Allow commit to succeed if the script is missing";
        }
        leaf max-datasize {
          type string;
          units "bytes";
          description
            "Maximum data segment size for scripts execution";
        }
        container dampen {
          presence "enable dampen";
          description
            "Run event scripts in dampen mode";
          uses apply-advanced;
          container dampen-options {
            description
              "Dampen options for event scripts";
            uses apply-advanced;
            leaf cpu-factor {
              type union {
                type string {
                  pattern "<.*>|$.*";
                }
                type uint32 {
                  range "1 .. 100";
                }
              }
              description
                "CPU factor at which to pause";
            }
            leaf line-interval {
              type union {
                type string {
                  pattern "<.*>|$.*";
                }
                type uint32 {
                  range "1 .. 4294967295";
                }
              }
              description
                "Line interval at which to pause";
            }
            leaf time-interval {
              type union {
                type string {
                  pattern "<.*>|$.*";
                }
                type uint32 {
                  range "1 .. 4294967295";
                }
              }
              units "microseconds";
              description
                "Time to pause";
            }
          }
        }
        container start {
          description
            "Start event scripts with start-criteria check";
          uses apply-advanced;
          container start-options {
            description
              "Start options for event scripts";
            uses apply-advanced;
            leaf mem-factor {
              type union {
                type string {
                  pattern "<.*>|$.*";
                }
                type uint32 {
                  range "1 .. 100";
                }
              }
              description
                "Memory factor at which to start/stop";
            }
          }
        }
        container traceoptions {
          description
            "Trace options for event scripts";
          uses apply-advanced;
          leaf no-remote-trace {
            type empty;
            description
              "Disable remote tracing";
          }
          container file {
            description
              "Trace file information";
            leaf filename {
              type string {
                length "1 .. 1024";
              }
              description
                "Name of file in which to write trace information";
            }
            leaf size {
              type string;
              description
                "Maximum trace file size";
            }
            leaf files {
              type union {
                type string {
                  pattern "<.*>|$.*";
                }
                type uint32 {
                  range "2 .. 1000";
                }
              }
              default "3";
              description
                "Maximum number of trace files";
            }
            choice world-readable-choice {
              leaf world-readable {
                type empty;
                description
                  "Allow any user to read the log file";
              }
              leaf no-world-readable {
                type empty;
                description
                  "Don't allow any user to read the log file";
              }
            }
          }
          list flag {
            key "name";
            description
              "Tracing parameters";
            leaf name {
              type enumeration {
                enum "events" {
                  description
                    "Trace important events";
                }
                enum "input" {
                  description
                    "Trace script input data";
                }
                enum "offline" {
                  description
                    "Generate data for offline development";
                }
                enum "output" {
                  description
                    "Trace script output data";
                }
                enum "rpc" {
                  description
                    "Trace script RPCs";
                }
                enum "xslt" {
                  description
                    "Trace the XSLT library";
                }
                enum "all" {
                  description
                    "Trace all operations";
                }
              }
            }
          }
        }
        list file {
          key "name";
          ordered-by user;
          description
            "File name for event script";
          leaf name {
            type string {
              length "1 .. 254";
            }
            description
              "Local filename of the script file";
          }
          uses apply-advanced;
          leaf source {
            type string {
              length "1 .. 254";
            }
            description
              "URL of source for this script";
          }
          leaf cert-file {
            type string;
            description
              "Specify the certificate file name";
          }
          leaf python-script-user {
            type string;
            description
              "Run the python event script with privileges of user";
          }
          container dampen {
            presence "enable dampen";
            description
              "Run script in dampen mode";
            uses apply-advanced;
            container dampen-options {
              description
                "Dampen options for the script";
              uses apply-advanced;
              leaf cpu-factor {
                type union {
                  type string {
                    pattern "<.*>|$.*";
                  }
                  type uint32 {
                    range "1 .. 100";
                  }
                }
                description
                  "CPU factor at which to pause";
              }
              leaf line-interval {
                type union {
                  type string {
                    pattern "<.*>|$.*";
                  }
                  type uint32 {
                    range "1 .. 4294967295";
                  }
                }
                description
                  "Line interval at which to pause";
              }
              leaf time-interval {
                type union {
                  type string {
                    pattern "<.*>|$.*";
                  }
                  type uint32 {
                    range "1 .. 4294967295";
                  }
                }
                units "microseconds";
                description
                  "Time to pause";
              }
            }
          }
          container start {
            description
              "Start script with start-criteria check";
            uses apply-advanced;
            container start-options {
              description
                "Start options for the event script";
              uses apply-advanced;
              leaf mem-factor {
                type union {
                  type string {
                    pattern "<.*>|$.*";
                  }
                  type uint32 {
                    range "1 .. 100";
                  }
                }
                description
                  "Memory factor at which to start/stop";
              }
            }
          }
          leaf routing-instance {
            type string;
            description
              "Routing instance";
          }
          leaf refresh {
            type empty;
            description
              "Refresh all operation scripts from their source";
          }
          leaf refresh-from {
            type string {
              length "1 .. 254";
            }
            description
              "Refresh all operation scripts from a given base URL";
          }
          container checksum {
            description
              "Checksum of this script";
            uses apply-advanced;
            leaf sha-256 {
              type string {
                length "1 .. 254";
              }
              description
                "SHA-256 checksum of this script";
            }
          }
          list remote-execution {
            key "name";
            ordered-by user;
            description
              "Remote login username and password details for script";
            leaf name {
              type string {
                length "1 .. 255";
              }
              description
                "Remote hostname";
            }
            uses apply-advanced;
            leaf username {
              type string;
              mandatory true;
              description
                "SSH username for login into the remote host";
            }
            leaf passphrase {
              type jt:unreadable;
              mandatory true;
              description
                "SSH passphrase for login into the remote host";
            }
          }
        }
        leaf refresh {
          type empty;
          description
            "Refresh all operation scripts from their source";
        }
        leaf refresh-from {
          type string {
            length "1 .. 254";
          }
          description
            "Refresh all operation scripts from a given base URL";
        }
      }
      list destinations {
        key "name";
        ordered-by user;
        description
          "List of destinations referred to in 'then' clause";
        leaf name {
          type string;
          description
            "Destination name";
        }
        uses apply-advanced;
        leaf transfer-delay {
          type union {
            type uint32;
            type string {
              pattern "<.*>|$.*";
            }
          }
          units "seconds";
          default "0";
          description
            "Delay before transferring files";
        }
        list archive-sites {
          key "name";
          ordered-by user;
          description
            "List of archive destinations";
          leaf name {
            type string;
            description
              "URL of destination for file";
          }
          leaf password {
            type jt:unreadable;
            description
              "Password for login into the archive site";
          }
        }
      }
      container traceoptions {
        description
          "Trace options for the event processing daemon";
        uses apply-advanced;
        leaf no-remote-trace {
          type empty;
          description
            "Disable remote tracing";
        }
        container file {
          description
            "Trace file information";
          leaf filename {
            type string {
              length "1 .. 1024";
            }
            description
              "Name of file in which to write trace information";
          }
          leaf size {
            type string;
            description
              "Maximum trace file size";
          }
          leaf files {
            type union {
              type string {
                pattern "<.*>|$.*";
              }
              type uint32 {
                range "2 .. 1000";
              }
            }
            default "3";
            description
              "Maximum number of trace files";
          }
          choice world-readable-choice {
            leaf world-readable {
              type empty;
              description
                "Allow any user to read the log file";
            }
            leaf no-world-readable {
              type empty;
              description
                "Don't allow any user to read the log file";
            }
          }
          leaf match {
            type jt:regular-expression;
            description
              "Regular expression for lines to be logged";
          }
        }
        list flag {
          key "name";
          ordered-by user;
          description
            "List of event types to include in trace";
          leaf name {
            type enumeration {
              enum "server" {
                description
                  "Communication with processes that are generating events";
              }
              enum "configuration" {
                description
                  "Reading of configuration";
              }
              enum "events" {
                description
                  "Event processing";
              }
              enum "timer-events" {
                description
                  "Internally generated events";
              }
              enum "database" {
                description
                  "Events involving storage and retrieval in events database";
              }
              enum "policy" {
                description
                  "Policy processing";
              }
              enum "registration" {
                description
                  "Event registration";
              }
              enum "syslogd" {
                description
                  "Syslog related traces";
              }
              enum "all" {
                description
                  "Everything";
              }
            }
          }
        }
      }
    }
    container policy-options {
      description
        "Policy option configuration";
      uses juniper-policy-options;
    }
    container class-of-service {
      description
        "Class-of-service configuration";
      uses juniper-class-of-service-options;
    }
    container firewall {
      description
        "Define a Firewall configuration";
      uses juniper-firewall-options;
    }
    container routing-instances {
      description
        "Routing instance configuration";
      uses apply-advanced;
      list instance {
        key "name";
        uses juniper-routing-instance;
      }
    }
    container routing-options {
      description
        "Protocol-independent routing option configuration";
      uses juniper-routing-options;
    }
    container protocols {
      description
        "Routing protocol configuration";
      uses juniper-protocols;
    }
  }

  grouping apply-advanced {
    description
      "Apply advanced configuration logic";
    leaf-list apply-groups {
      type string;
      ordered-by user;
      description
        "Groups from which to inherit configuration data";
    }
    leaf-list apply-groups-except {
      type string;
      ordered-by user;
      description
        "Don't inherit configuration data from these groups";
    }
    list apply-macro {
      key "name";
      ordered-by user;
      description
        "Macro and parameters for commit script expansion";
      uses apply-macro-type;
    }
  }

  grouping apply-macro-type {
    description
      "Macro data for commit-script expansion";
    leaf name {
      type string;
      description
        "Name of the macro to be expanded";
    }
    list data {
      key "name";
      uses macro-data-type;
    }
  }

  grouping certificate-object {
    leaf name {
      type string;
      description
        "Simple name to identify this certificate";
    }
    uses apply-advanced;
    leaf certificate {
      type string;
      description
        "Certificate and private key string";
    }
  }

  grouping interface_type {
    description
      "Physical interface";
    leaf name {
      type string;
    }
    uses apply-advanced;
    choice queue-statistics-choice {
      leaf queue-statistics {
        type empty;
        status deprecated;
        description
          "Enable queue statistics collection";
      }
      leaf no-queue-statistics {
        type empty;
        status deprecated;
        description
          "Don't enable queue statistics collection";
      }
    }
    choice traffic-statistics-choice {
      leaf traffic-statistics {
        type empty;
        status deprecated;
        description
          "Enable traffic statistics collection";
      }
      leaf no-traffic-statistics {
        type empty;
        status deprecated;
        description
          "Don't enable traffic statistics collection";
      }
    }
    leaf resource-profile {
      type string {
        length "1 .. 64";
      }
      description
        "Resouce profile name";
    }
  }

  grouping interfaces_type {
    description
      "Physical interface";
    leaf name {
      type string;
    }
    uses apply-advanced;
    leaf description {
      type string;
      description
        "Text description of interface";
    }
    leaf mtu {
      type union {
        type string {
          pattern "<.*>|$.*";
        }
        type uint32 {
          range "1 .. 16000";
        }
      }
      description
        "Maximum transmit packet size";
    }
    leaf mac {
      type jt:mac-unicast;
      description
        "Hardware MAC address";
    }
    leaf native-vlan-id {
      type union {
        type string {
          pattern "<.*>|$.*";
        }
        type uint32 {
          range "0 .. 4094";
        }
      }
      description
        "Virtual LAN identifier for untagged frames";
    }
    list unit {
      key "name";
      description
        "Logical interface";
      leaf name {
        type string;
      }
      uses apply-advanced;
      leaf alias {
        type string;
        description
          "Interface alias";
      }
      leaf description {
        type string;
        description
          "Text description of interface";
      }
      leaf-list security-group {
        type string;
        ordered-by user;
        description
          "Security-group for the interface";
      }
      choice vlan_choice {
        case case_1 {
          leaf vlan-id {
            type string;
            description
              "Virtual LAN identifier value for 802.1q VLAN tags";
          }
        }
      }
      leaf encapsulation {
        type enumeration {
          enum "ethernet-ccc" {
            description
              "Ethernet for a cross-connect";
          }
          enum "ethernet-bridge" {
            description
              "Ethernet II bridging";
          }
          enum "vlan-ccc" {
            description
              "802.1q tagging for a cross-connect";
          }
          enum "vlan-bridge" {
            description
              "VLAN layer-2 bridging";
          }
        }
        description
          "Logical link-layer encapsulation";
      }
      container family {
        description
          "Protocol family";
        container inet {
          presence "enable inet";
          description
            "IPv4 parameters";
          uses apply-advanced;
          container filter {
            description
              "Packet filtering";
            uses apply-advanced;
            container input {
              description
                "Filter to be applied to received packets";
              leaf filter-name {
                type string;
                description
                  "Name of the filter";
              }
            }
          }
          list address {
            key "name";
            ordered-by user;
            description
              "Interface address/destination prefix";
            leaf name {
              type jt:ipv4prefix;
              description
                "Interface address/destination prefix";
            }
            uses apply-advanced;
            list vrrp-group {
              key "name";
              ordered-by user;
              description
                "VRRP group";
              uses vrrp-group;
            }
          }
        }
        container inet6 {
          presence "enable inet6";
          description
            "IPv6 protocol parameters";
          uses apply-advanced;
          container filter {
            description
              "Packet filtering";
            uses apply-advanced;
            container input {
              description
                "Filter to be applied to received packets";
              leaf filter-name {
                type string;
                mandatory true;
                description
                  "Name of the filter";
              }
            }
          }
          list address {
            key "name";
            ordered-by user;
            description
              "Interface address or destination prefix";
            leaf name {
              type jt:ipv6prefix;
              description
                "Interface address or destination prefix";
            }
            uses apply-advanced;
            list vrrp-inet6-group {
              key "name";
              ordered-by user;
              description
                "VRRP group";
              uses vrrp-inet6-group;
            }
          }
        }
        container iso {
          presence "enable iso";
          description
            "OSI ISO protocol parameters";
          uses apply-advanced;
          list address {
            key "name";
            ordered-by user;
            description
              "Interface address";
            leaf name {
              type jt:isoaddr;
              description
                "Interface address";
            }
            uses apply-advanced;
          }
        }
        container mpls {
          presence "enable mpls";
          uses apply-advanced;
          container filter {
            description
              "Packet filtering";
            uses apply-advanced;
            container input {
              description
                "Filter to be applied to received packets";
              leaf filter-name {
                type string;
                mandatory true;
                description
                  "Name of the filter";
              }
            }
          }
        }
        container bridge {
          presence "enable bridge";
          description
            "Layer-2 bridging parameters";
          uses apply-advanced;
          leaf interface-mode {
            type enumeration {
              enum "access" {
                description
                  "Interface mode is access";
              }
              enum "trunk" {
                description
                  "Interface mode is trunk";
              }
            }
            description
              "Interface mode (access or trunk)";
          }
          choice vlan_list {
            case case_1 {
              leaf vlan-id {
                type union {
                  type string {
                    pattern "<.*>|$.*";
                  }
                  type uint32 {
                    range "0 .. 4094";
                  }
                }
                description
                  "Access mode and trunk mode VLAN membership";
              }
            }
            case case_2 {
              leaf-list vlan-id-list {
                type jt:vlan-range;
                description
                  "Trunk mode VLAN membership for this interface";
              }
            }
          }
          choice bridge_intf_type {
            case case_1 {
              leaf ce-facing {
                type empty;
                description
                  "Interface is ce facing";
              }
            }
            case case_2 {
              leaf core-facing {
                type empty;
                description
                  "Interface is core facing";
              }
            }
          }
        }
      }
      leaf mtu {
        type union {
          type string {
            pattern "<.*>|$.*";
          }
          type uint32 {
            range "1 .. 16000";
          }
        }
        description
          "Maximum transmission unit packet size";
      }
      leaf mac {
        type jt:mac-unicast;
        description
          "Configure logical interface MAC address";
      }
    }
  }

  grouping juniper-class-of-service-options {
    uses apply-advanced;
    container classifiers {
      description
        "Classify incoming packets based on code point value";
      uses apply-advanced;
      list dscp {
        key "name";
        max-elements 16;
        ordered-by user;
        description
          "Differentiated Services code point classifier";
        leaf name {
          type string {
            length "1 .. 64";
          }
          description
            "Classifier name";
        }
        uses apply-advanced;
        list forwarding-class {
          key "name";
          description
            "Define a classification of code point aliases";
          leaf name {
            type string {
              length "1 .. 64";
            }
            description
              "Forwarding class name";
          }
          uses apply-advanced;
          list loss-priority {
            key "name";
            description
              "Classify code points to a loss priority";
            leaf name {
              type enumeration {
                enum "low" {
                  description
                    "Code points to classify to loss priority low";
                }
                enum "medium-low" {
                  description
                    "Code points to classify to loss priority medium-low";
                }
                enum "medium-high" {
                  description
                    "Code points to classify to loss priority medium-high";
                }
                enum "high" {
                  description
                    "Code points to classify to loss priority high";
                }
              }
            }
            leaf-list code-points {
              type string;
              ordered-by user;
              description
                "List of code point aliases and/or bit strings";
            }
          }
        }
      }
      list dscp-ipv6 {
        key "name";
        max-elements 16;
        ordered-by user;
        description
          "Differentiated Services code point classifier IPv6";
        leaf name {
          type string {
            length "1 .. 64";
          }
          description
            "Classifier name";
        }
        uses apply-advanced;
        list forwarding-class {
          key "name";
          description
            "Define a classification of code point aliases";
          leaf name {
            type string {
              length "1 .. 64";
            }
            description
              "Forwarding class name";
          }
          uses apply-advanced;
          list loss-priority {
            key "name";
            description
              "Classify code points to a loss priority";
            leaf name {
              type enumeration {
                enum "low" {
                  description
                    "Code points to classify to loss priority low";
                }
                enum "medium-low" {
                  description
                    "Code points to classify to loss priority medium-low";
                }
                enum "medium-high" {
                  description
                    "Code points to classify to loss priority medium-high";
                }
                enum "high" {
                  description
                    "Code points to classify to loss priority high";
                }
              }
            }
            leaf-list code-points {
              type string;
              ordered-by user;
              description
                "List of code point aliases and/or bit strings";
            }
          }
        }
      }
    }
    container rewrite-rules {
      description
        "Rewrite rules applied to outgoing packets";
      uses apply-advanced;
      list dscp {
        key "name";
        max-elements 8;
        ordered-by user;
        description
          "Differentiated Services code point rewrite rule";
        leaf name {
          type string {
            length "1 .. 64";
          }
          description
            "Rewrite rule name";
        }
        uses apply-advanced;
        list forwarding-class {
          key "name";
          description
            "Markings for named forwarding class";
          leaf name {
            type string {
              length "1 .. 64";
            }
            description
              "Forwarding class name";
          }
          uses apply-advanced;
          list loss-priority {
            key "name";
            description
              "Code point marking based on loss priority";
            leaf name {
              type enumeration {
                enum "low" {
                  description
                    "Marking when loss priority is low";
                }
                enum "medium-low" {
                  description
                    "Marking when loss priority is medium-low";
                }
                enum "medium-high" {
                  description
                    "Marking when loss priority is medium-high";
                }
                enum "high" {
                  description
                    "Marking when loss priority is high";
                }
              }
            }
            leaf code-point {
              type string;
              mandatory true;
              description
                "Code point aliases or bit string";
            }
          }
        }
      }
      list dscp-ipv6 {
        key "name";
        max-elements 8;
        ordered-by user;
        description
          "Differentiated Services code point rewrite rule IPv6";
        leaf name {
          type string {
            length "1 .. 64";
          }
          description
            "Rewrite rule name";
        }
        uses apply-advanced;
        list forwarding-class {
          key "name";
          description
            "Markings for named forwarding class";
          leaf name {
            type string {
              length "1 .. 64";
            }
            description
              "Forwarding class name";
          }
          uses apply-advanced;
          list loss-priority {
            key "name";
            description
              "Code point marking based on loss priority";
            leaf name {
              type enumeration {
                enum "low" {
                  description
                    "Marking when loss priority is low";
                }
                enum "medium-low" {
                  description
                    "Marking when loss priority is medium-low";
                }
                enum "medium-high" {
                  description
                    "Marking when loss priority is medium-high";
                }
                enum "high" {
                  description
                    "Marking when loss priority is high";
                }
              }
            }
            leaf code-point {
              type string;
              mandatory true;
              description
                "Code point aliases or bit string";
            }
          }
        }
      }
      list exp {
        key "name";
        max-elements 8;
        ordered-by user;
        description
          "MPLS EXP rewrite rule";
        leaf name {
          type string {
            length "1 .. 64";
          }
          description
            "Rewrite rule name";
        }
        uses apply-advanced;
        list forwarding-class {
          key "name";
          description
            "Markings for named forwarding class";
          leaf name {
            type string {
              length "1 .. 64";
            }
            description
              "Forwarding class name";
          }
          uses apply-advanced;
          list loss-priority {
            key "name";
            description
              "Code point marking based on loss priority";
            leaf name {
              type enumeration {
                enum "low" {
                  description
                    "Marking when loss priority is low";
                }
                enum "medium-low" {
                  description
                    "Marking when loss priority is medium-low";
                }
                enum "medium-high" {
                  description
                    "Marking when loss priority is medium-high";
                }
                enum "high" {
                  description
                    "Marking when loss priority is high";
                }
              }
            }
            leaf code-point {
              type string;
              mandatory true;
              description
                "Code point aliases or bit string";
            }
          }
        }
      }
    }
    list schedulers {
      key "name";
      max-elements 8;
      description
        "Packet schedulers";
      leaf name {
        type string {
          length "1 .. 64";
        }
        description
          "Scheduler name";
      }
      uses apply-advanced;
      leaf priority {
        type enumeration {
          enum "low" {
            description
              "Scheduling priority 7 (Least)";
          }
          enum "high" {
            description
              "Scheduling priority 1";
          }
          enum "medium-high" {
            description
              "Scheduling priority 2";
          }
          enum "medium-low" {
            description
              "Scheduling priority 3";
          }
          enum "strict-high" {
            description
              "Scheduling priority 0 (Highest)";
          }
          enum "low-latency" {
            description
              "Scheduling priority 4";
          }
          enum "low-medium" {
            description
              "Scheduling priority 6";
          }
          enum "low-high" {
            description
              "Scheduling priority 5";
          }
        }
        description
          "Scheduling priority";
      }
    }
    list scheduler-maps {
      key "name";
      max-elements 8;
      description
        "Mapping of forwarding classes to packet schedulers";
      leaf name {
        type string {
          length "1 .. 64";
        }
        description
          "Scheduler map name";
      }
      uses apply-advanced;
      list forwarding-class {
        key "name";
        description
          "Forwarding class name to map to scheduler";
        leaf name {
          type string {
            length "1 .. 64";
          }
          description
            "Forwarding class name";
        }
        leaf scheduler {
          type string {
            length "1 .. 64";
          }
          mandatory true;
          description
            "Scheduler name";
        }
      }
    }
    container interfaces {
      description
        "Apply class-of-service options to interfaces";
      uses apply-advanced;
      list interface {
        key "name";
        uses cos_interfaces_type;
      }
    }
    container forwarding-classes {
      description
        "One or more mappings of forwarding class to queue number";
      uses apply-advanced;
      list class {
        key "name";
        max-elements 16;
        description
          "Forwarding class to map to queue number";
        leaf name {
          type string {
            length "1 .. 64";
          }
          description
            "Name of forwarding class";
        }
        uses apply-advanced;
      }
    }
  }

  grouping cos_interfaces_type {
    description
      "Physical interface";
    leaf name {
      type string;
      description
        "Interface name";
    }
    uses apply-advanced;
    leaf scheduler-map {
      type string {
        length "1 .. 64";
      }
      description
        "Output scheduler map";
    }
    list unit {
      key "name";
      description
        "Logical interface unit";
      leaf name {
        type string;
        description
          "Logical unit number";
      }
      uses apply-advanced;
      container classifiers {
        description
          "Classifiers applied to incoming packets";
        uses apply-advanced;
        container dscp {
          description
            "Differentiated Services code point classifier";
          leaf classifier-name {
            type string {
              length "1 .. 64";
            }
            mandatory true;
            description
              "Name of classifier to be applied";
          }
        }
        container dscp-ipv6 {
          description
            "Differentiated Services code point classifier IPv6";
          leaf classifier-name {
            type string {
              length "1 .. 64";
            }
            mandatory true;
            description
              "Name of classifier to be applied";
          }
        }
      }
      container rewrite-rules {
        description
          "Rewrite rules applied to outgoing packets";
        uses apply-advanced;
        container dscp {
          description
            "Differentiated Services code point rewrite rule";
          leaf rewrite-rule-name {
            type string {
              length "1 .. 64";
            }
            mandatory true;
            description
              "Name of rewrite rule to be applied";
          }
        }
        container dscp-ipv6 {
          description
            "Differentiated Services code point rewrite rule IPv6";
          leaf rewrite-rule-name {
            type string {
              length "1 .. 64";
            }
            mandatory true;
            description
              "Name of rewrite rule to be applied";
          }
        }
        container exp {
          description
            "MPLS exp rewrite rule";
          leaf rewrite-rule-name {
            type string {
              length "1 .. 64";
            }
            mandatory true;
            description
              "Name of rewrite rule to be applied";
          }
        }
      }
    }
  }

  grouping juniper-firewall-options {
    uses apply-advanced;
    list three-color-policer {
      key "name";
      max-elements 16;
      description
        "Three-color policer";
      uses three-color-policer-type;
    }
    container family {
      description
        "Protocol Family";
      container bridge {
        description
          "Protocol family BRIDGE for firewall filter";
        uses apply-advanced;
        list filter {
          key "name";
          description
            "Define a BRIDGE firewall filter";
          uses bridge_filter;
        }
      }
      container inet {
        description
          "Protocol family IPv4 for firewall filter";
        uses apply-advanced;
        list filter {
          key "name";
          max-elements 16;
          description
            "Define an IPv4 firewall filter";
          uses inet_filter;
        }
      }
      container inet6 {
        description
          "Protocol family IPv6 for firewall filter";
        uses apply-advanced;
        list filter {
          key "name";
          max-elements 16;
          description
            "Define an IPv6 firewall filter";
          uses inet6_filter;
        }
      }
      container mpls {
        description
          "Protocol family MPLS for firewall filter";
        uses apply-advanced;
        list filter {
          key "name";
          max-elements 16;
          description
            "Define a MPLS firewall filter";
          uses mpls_filter;
        }
      }
    }
  }

  grouping bridge_filter {
    description
      "Define a BRIDGE firewall filter";
    leaf name {
      type string {
        length "1 .. 64";
      }
      description
        "Filter name";
    }
    uses apply-advanced;
    list term {
      key "name";
      max-elements 16;
      ordered-by user;
      description
        "Define a firewall term";
      leaf name {
        type string {
          length "1 .. 4";
        }
        description
          "Term name";
      }
      uses apply-advanced;
      container from {
        description
          "Define match criteria";
        uses apply-advanced;
        leaf source-mac-address {
          type jt:mac-addr-prefix;
          description
            "Match source mac address";
        }
        leaf destination-mac-address {
          type jt:mac-addr-prefix;
          description
            "Match destination mac address";
        }
        leaf-list ether-type {
          type string;
          max-elements 1;
          ordered-by user;
          description
            "Match Ethernet type";
        }
      }
      container then {
        description
          "Action to take if the 'from' condition is matched";
        uses apply-advanced;
        choice designation {
          case case_1 {
            leaf discard {
              type empty;
              description
                "Discard the packet";
            }
          }
        }
      }
    }
  }

  grouping inet6_filter {
    description
      "Define an IPv6 firewall filter";
    leaf name {
      type string {
        length "1 .. 127";
      }
      description
        "Filter name";
    }
    uses apply-advanced;
    list term {
      key "name";
      max-elements 16;
      ordered-by user;
      description
        "Define a firewall term";
      leaf name {
        type string {
          length "1 .. 127";
        }
        description
          "Term name";
      }
      uses apply-advanced;
      container from {
        description
          "Define match criteria";
        uses apply-advanced;
        list source-address {
          key "name";
          max-elements 1;
          ordered-by user;
          description
            "Match IP source address";
          uses firewall_addr6_object;
        }
        list destination-address {
          key "name";
          max-elements 1;
          ordered-by user;
          description
            "Match IP destination address";
          uses firewall_addr6_object;
        }
        leaf-list source-port {
          type string;
          ordered-by user;
        }
        leaf-list destination-port {
          type string;
          ordered-by user;
        }
        leaf-list icmp-type {
          type string;
          ordered-by user;
        }
        leaf-list tcp-flags {
          type string;
          ordered-by user;
        }
        leaf-list traffic-class {
          type string;
          ordered-by user;
        }
        leaf-list forwarding-class {
          type string;
          max-elements 1;
          ordered-by user;
          description
            "Match packet to forwarding class";
        }
      }
      container then {
        description
          "Action to take if the 'from' condition is matched";
        uses apply-advanced;
        choice designation {
          case case_1 {
            leaf accept {
              type empty;
              description
                "Accept the packet";
            }
          }
          case case_2 {
            leaf discard {
              type empty;
              description
                "Discard the packet";
            }
          }
        }
        leaf count {
          type string {
            length "1 .. 127";
          }
          description
            "Count the packet in the named counter";
        }
        leaf routing-instance {
          type string;
          description
            "Name of routing instance - Packets are directed to specified routing instance";
        }
        leaf log {
          type empty;
          description
            "Log the packet";
        }
        leaf syslog {
          type empty;
          description
            "System log (syslog) information about the packet";
        }
        choice policer-choice {
          case case_1 {
            container three-color-policer {
              description
                "Police the packet using a three-color-policer";
              uses apply-advanced;
              choice type-choice {
                case case_1 {
                  leaf single-rate {
                    type string;
                    description
                      "Name of single-rate three-color policer to use to rate-limit traffic";
                  }
                }
                case case_2 {
                  leaf two-rate {
                    type string;
                    description
                      "Name of two-rate three-color policer to use to rate-limit traffic";
                  }
                }
              }
            }
          }
        }
        leaf forwarding-class {
          type string;
          description
            "Classify packet to forwarding class";
        }
        leaf loss-priority {
          type enumeration {
            enum "low" {
              description
                "Loss priority low";
            }
            enum "high" {
              description
                "Loss priority high";
            }
            enum "medium-low" {
              description
                "Loss priority medium-low";
            }
            enum "medium-high" {
              description
                "Loss priority medium-high";
            }
          }
          description
            "Packet's loss priority";
        }
      }
    }
  }

  grouping firewall_addr6_object {
    leaf name {
      type jt:ipv6prefix;
      description
        "Prefix to match";
    }
  }

  grouping inet_filter {
    description
      "Define an IPv4 firewall filter";
    leaf name {
      type string {
        length "1 .. 127";
      }
      description
        "Filter name";
    }
    uses apply-advanced;
    list term {
      key "name";
      max-elements 16;
      ordered-by user;
      description
        "Define a firewall term";
      leaf name {
        type string {
          length "1 .. 127";
        }
        description
          "Term name";
      }
      uses apply-advanced;
      container from {
        description
          "Define match criteria";
        uses apply-advanced;
        list source-address {
          key "name";
          max-elements 1;
          ordered-by user;
          description
            "Match IP source address";
          uses firewall_addr_object;
        }
        list destination-address {
          key "name";
          max-elements 1;
          ordered-by user;
          description
            "Match IP destination address";
          uses firewall_addr_object;
        }
        leaf-list source-port {
          type string;
          ordered-by user;
        }
        leaf-list destination-port {
          type string;
          ordered-by user;
        }
        leaf-list icmp-type {
          type string;
          ordered-by user;
        }
        leaf-list tcp-flags {
          type string;
          ordered-by user;
        }
        leaf-list protocol {
          type string;
          ordered-by user;
        }
        leaf-list dscp {
          type string;
          ordered-by user;
        }
        leaf-list forwarding-class {
          type string;
          max-elements 1;
          ordered-by user;
          description
            "Match forwarding class";
        }
      }
      container then {
        description
          "Action to take if the 'from' condition is matched";
        uses apply-advanced;
        choice designation {
          case case_1 {
            leaf accept {
              type empty;
              description
                "Accept the packet";
            }
          }
          case case_2 {
            leaf discard {
              type empty;
              description
                "Discard the packet";
            }
          }
        }
        leaf count {
          type string {
            length "1 .. 127";
          }
          description
            "Count the packet in the named counter";
        }
        leaf routing-instance {
          type string;
          description
            "Name of routing instance - Packets are directed to specified routing instance";
        }
        leaf log {
          type empty;
          description
            "Log the packet";
        }
        leaf syslog {
          type empty;
          description
            "System log (syslog) information about the packet";
        }
        choice policer-choice {
          case case_1 {
            container three-color-policer {
              description
                "Police the packet using a three-color-policer";
              uses apply-advanced;
              choice type-choice {
                case case_1 {
                  leaf single-rate {
                    type string;
                    description
                      "Name of single-rate three-color policer to use to rate-limit traffic";
                  }
                }
                case case_2 {
                  leaf two-rate {
                    type string;
                    description
                      "Name of two-rate three-color policer to use to rate-limit traffic";
                  }
                }
              }
            }
          }
        }
        leaf forwarding-class {
          type string;
          description
            "Classify packet to forwarding class";
        }
        leaf loss-priority {
          type enumeration {
            enum "low" {
              description
                "Loss priority low";
            }
            enum "high" {
              description
                "Loss priority high";
            }
            enum "medium-low" {
              description
                "Loss priority medium-low";
            }
            enum "medium-high" {
              description
                "Loss priority medium-high";
            }
          }
          description
            "Packet's loss priority";
        }
      }
    }
  }

  grouping firewall_addr_object {
    leaf name {
      type jt:ipv4prefix;
      description
        "Prefix to match";
    }
  }

  grouping juniper-group {
    description
      "Configuration groups";
    leaf name {
      type string {
        length "1 .. 254";
      }
      description
        "Group name";
    }
    container when {
      description
        "Specify additional conditions for groups";
      uses apply-advanced;
      container time {
        description
          "Time at which group should be effective";
        leaf start-time {
          type string;
          description
            "Start time([yyyy-mm-dd.]hh:mm)";
        }
        container to {
          description
            "End time";
          uses apply-advanced;
          leaf end-time {
            type string;
            description
              "End time([yyyy-mm-dd.]hh:mm)";
          }
        }
      }
      leaf-list peers {
        type string {
          length "1 .. 255";
        }
        ordered-by user;
        description
          "Hosts on which this group should be effective";
      }
      leaf chassis {
        type enumeration {
          enum "lcc0" {
            description
              "Chassis lcc0";
          }
          enum "lcc1" {
            description
              "Chassis lcc1";
          }
          enum "lcc2" {
            description
              "Chassis lcc2";
          }
          enum "lcc3" {
            description
              "Chassis lcc3";
          }
          enum "lcc4" {
            description
              "Chassis lcc4";
          }
          enum "lcc5" {
            description
              "Chassis lcc5";
          }
          enum "lcc6" {
            description
              "Chassis lcc6";
          }
          enum "lcc7" {
            description
              "Chassis lcc7";
          }
          enum "scc" {
            description
              "Chassis scc";
          }
          enum "sfc0" {
            description
              "Chassis sfc0";
          }
        }
        description
          "Chassis id";
      }
      leaf model {
        type string;
        description
          "Model name";
      }
      leaf routing-engine {
        type enumeration {
          enum "re0" {
            description
              "RE0";
          }
          enum "re1" {
            description
              "RE1";
          }
        }
        description
          "Routing Engine";
      }
      leaf member {
        type string;
        description
          "Member of virtual chassis";
      }
      leaf node {
        type enumeration {
          enum "node0" {
            description
              "Node0";
          }
          enum "node1" {
            description
              "Node1";
          }
        }
        description
          "Node of cluster";
      }
    }
    uses juniper-config;
  }

  grouping juniper-policy-options {
    uses apply-advanced;
    list prefix-list {
      key "name";
      description
        "Define a named set of address prefixes";
      leaf name {
        type string;
        description
          "Prefix list name";
      }
      uses apply-advanced;
      list prefix-list-item {
        key "name";
        uses prefix_list_items;
      }
      leaf apply-path {
        type string;
        description
          "Apply IP prefixes from a configuration statement";
      }
    }
    list rib-list {
      key "name";
      ordered-by user;
      description
        "Define a named set of RIB names or wildcards";
      leaf name {
        type string;
        description
          "RIB list name";
      }
      uses apply-advanced;
      list rib-list-item {
        key "name";
        uses rib_list_items;
      }
    }
    list route-filter-list {
      key "name";
      description
        "Define a named set of route-filter address prefixes";
      leaf name {
        type string;
        description
          "Route filter list name";
      }
      uses apply-advanced;
      list rf_list {
        key "address choice-ident choice-value";
        ordered-by user;
        uses route_filter_list_items;
      }
    }
    list source-address-filter-list {
      key "name";
      description
        "Define a named set of source address filter address prefixes";
      leaf name {
        type string;
        description
          "Source address filter list name";
      }
      uses apply-advanced;
      list saf_list {
        key "address choice-ident choice-value";
        ordered-by user;
        uses source_address_filter_list_items;
      }
    }
    list fast-lookup-tuple-list {
      key "name";
      description
        "Define a named set of address prefixes";
      leaf name {
        type string;
        description
          "Five tuple combination list name";
      }
      uses apply-advanced;
      list fast_lookup_tuple_list_item {
        key "name";
        uses fast_lookup_tuple_list_items;
      }
    }
    list policy-statement {
      key "name";
      description
        "Routing policy";
      leaf name {
        type string;
        description
          "Name to identify a policy filter";
      }
      uses apply-advanced;
      container defaults {
        description
          "Policy default behaviour";
        uses apply-advanced;
        container route-filter {
          description
            "Set route filter behaviour";
          choice scope-choice {
            case case_1 {
              leaf no-walkup {
                type empty;
                description
                  "Route filter walk up disable";
              }
            }
            case case_2 {
              leaf walkup {
                type empty;
                description
                  "Route filter walk up enable";
              }
            }
          }
        }
      }
      list term {
        key "name";
        ordered-by user;
        description
          "Policy term";
        leaf name {
          type string;
        }
        uses apply-advanced;
        container from {
          description
            "Conditions to match the source of a route";
          uses apply-advanced;
          leaf instance {
            type string;
            description
              "Routing protocol instance";
          }
          leaf instance-any {
            type empty;
            description
              "Any routing protocol instance";
          }
          leaf-list instance-list {
            type string;
            description
              "A list of routing protocol instances";
          }
          leaf-list igp-instance {
            type string;
            description
              "IGP instance";
          }
          leaf igp-instance-regex {
            type jt:regular-expression;
            description
              "IGP instance name regular expression";
          }
          leaf family {
            type enumeration {
              enum "inet" {
                description
                  "IPv4 family";
              }
              enum "inet-vpn" {
                description
                  "IPv4-VPN family";
              }
              enum "inet6" {
                description
                  "IPv6 family";
              }
              enum "inet6-vpn" {
                description
                  "IPv6-VPN family";
              }
              enum "iso-vpn" {
                description
                  "ISO-VPN family";
              }
              enum "iso" {
                description
                  "ISO family";
              }
              enum "evpn" {
                description
                  "EVPN family";
              }
              enum "inet-mvpn" {
                description
                  "IPv4 Multicast VPN family";
              }
              enum "inet6-mvpn" {
                description
                  "IPv6 Multicast VPN family";
              }
              enum "inet-mdt" {
                description
                  "IPv4 MDT Signaling family";
              }
              enum "route-target" {
                description
                  "Local route target VPN family";
              }
              enum "traffic-engineering" {
                description
                  "Traffic Engineering family";
              }
              enum "inet-srte" {
                description
                  "IPv4 srtte family";
              }
              enum "inet6-srte" {
                description
                  "IPv6 srte family";
              }
            }
          }
          leaf-list protocol {
            type enumeration {
              enum "aggregate" {
                description
                  "Aggregate routes";
              }
              enum "bgp" {
                description
                  "BGP";
              }
              enum "direct" {
                description
                  "Directly connected routes";
              }
              enum "dvmrp" {
                description
                  "Distance Vector Multicast Routing Protocol";
              }
              enum "isis" {
                description
                  "Intermediate System-to-Intermediate System";
              }
              enum "esis" {
                description
                  "End System-to-Intermediate System";
              }
              enum "l-isis" {
                description
                  "Labelled ISIS";
              }
              enum "l2circuit" {
                description
                  "Layer 2 circuits";
              }
              enum "l2vpn" {
                description
                  "Layer 2 MPLS virtual private networks";
              }
              enum "local" {
                description
                  "Local system addresses";
              }
              enum "ospf" {
                description
                  "Open Shortest Path First";
              }
              enum "ospf2" {
                description
                  "Open Shortest Path First Version 2";
              }
              enum "ospf3" {
                description
                  "Open Shortest Path First Version 3";
              }
              enum "l-ospf" {
                description
                  "Labelled OSPF";
              }
              enum "pim" {
                description
                  "Protocol Independent Multicast";
              }
              enum "rip" {
                description
                  "Routing Information Protocol";
              }
              enum "ripng" {
                description
                  "Routing Information Protocol next generation";
              }
              enum "static" {
                description
                  "Statically defined addresses";
              }
              enum "arp" {
                description
                  "Addresses learned from ARP";
              }
              enum "frr" {
                description
                  "Addresses created by Host Fast Re-route";
              }
              enum "mpls" {
                description
                  "Multiprotocol Label Switching";
              }
              enum "ldp" {
                description
                  "Label Distribution Protocol";
              }
              enum "rsvp" {
                description
                  "Resource Reservation Protocol";
              }
              enum "msdp" {
                description
                  "Multicast Source Discovery Protocol";
              }
              enum "route-target" {
                description
                  "Local route target VPN membership";
              }
              enum "access" {
                description
                  "Access server routes";
              }
              enum "access-internal" {
                description
                  "Internal routes to directly connected clients";
              }
              enum "anchor" {
                description
                  "Anchor routes connected to UEs";
              }
              enum "bgp-static" {
                description
                  "BGP static routes";
              }
              enum "vpls" {
                description
                  "Virtual Private LAN Service";
              }
              enum "evpn" {
                description
                  "Ethernet VPN Service";
              }
              enum "spring-te" {
                description
                  "SPRING Traffic-Engineered";
              }
              enum "bgp-ls-epe" {
                description
                  "Addresses created by BGP-LS egress TE";
              }
              enum "express-segments" {
                description
                  "Express-segment routes";
              }
              enum "rift" {
                description
                  "RIFT routes";
              }
              enum "l2-learned-host-routing" {
                description
                  "Layer2-learned host routes";
              }
              enum "srv6-isis" {
                description
                  "SRV6 ISIS";
              }
              enum "ari-ts" {
                description
                  "ARI TS routes";
              }
              enum "srv6" {
                description
                  "Segment Routing IPv6 local route";
              }
            }
            ordered-by user;
            description
              "Protocol from which route was learned";
          }
          leaf rib {
            type string;
            description
              "Routing table";
          }
          leaf-list neighbor {
            type jt:ipaddr;
            ordered-by user;
            description
              "Neighboring router";
          }
          leaf-list next-hop {
            type jt:ipaddr;
            ordered-by user;
            description
              "Next-hop router";
          }
          leaf-list interface {
            type union {
              type jt:ipaddr-or-interface;
              type string {
                pattern "<.*>|$.*";
              }
            }
            ordered-by user;
            description
              "Interface name or address";
          }
          leaf area {
            type jt:areaid;
            description
              "OSPF area identifier";
          }
          leaf-list as-path {
            type string;
            ordered-by user;
            description
              "Name of AS path regular expression (BGP only)";
          }
          leaf-list as-path-group {
            type string;
            ordered-by user;
            description
              "Name of AS path group (BGP only)";
          }
          leaf origin {
            type enumeration {
              enum "igp" {
                description
                  "Path originated in the local IGP";
              }
              enum "egp" {
                description
                  "Path originated in another AS";
              }
              enum "incomplete" {
                description
                  "Path was learned by some other means";
              }
            }
            description
              "BGP origin attribute";
          }
          leaf-list community {
            type string;
            ordered-by user;
            description
              "BGP community";
          }
          leaf level {
            type union {
              type uint32;
              type string {
                pattern "<.*>|$.*";
              }
            }
            description
              "IS-IS level";
          }
          container external {
            presence "enable external";
            description
              "External route";
            uses apply-advanced;
            leaf type {
              type union {
                type string {
                  pattern "<.*>|$.*";
                }
                type int32 {
                  range "1 .. 2";
                }
              }
              description
                "OSPF external metric type";
            }
          }
          leaf bgp-srte-discriminator {
            type union {
              type uint32;
              type string {
                pattern "<.*>|$.*";
              }
            }
            description
              "Srte discriminator";
          }
          leaf srte-color {
            type union {
              type uint32;
              type string {
                pattern "<.*>|$.*";
              }
            }
            description
              "Srte color";
          }
          leaf programmed {
            type empty;
            description
              "API-programmed route";
          }
          leaf validation-database {
            type enumeration {
              enum "valid" {
                description
                  "Match for valid database validation-state";
              }
              enum "invalid" {
                description
                  "Match for invalid database validation-state";
              }
              enum "unknown" {
                description
                  "Match for unknown database validation-state";
              }
            }
            description
              "Name to identify a validation-state";
          }
          container validation-database-instance {
            presence "enable validation-database-instance";
            description
              "Name to identify a validation-state with DB name";
            uses apply-advanced;
            leaf database-name {
              type string;
              description
                "Route Validation Database name to be looked at";
            }
            leaf state {
              type enumeration {
                enum "valid" {
                  description
                    "Match for valid database validation-state";
                }
                enum "invalid" {
                  description
                    "Match for invalid database validation-state";
                }
                enum "unknown" {
                  description
                    "Match for unknown database validation-state";
                }
              }
              mandatory true;
              description
                "Name to identify a validation-state";
            }
          }
          list nexthop-weight {
            key "choice-ident choice-value weight";
            ordered-by user;
            description
              "Weight of the gateway";
            leaf choice-ident {
              type enumeration {
                enum "equal";
                enum "greater-than";
                enum "less-than";
                enum "greater-than-equal";
                enum "less-than-equal";
              }
            }
            leaf choice-value {
              type string;
            }
            leaf weight {
              type union {
                type string {
                  pattern "<.*>|$.*";
                }
                type uint32 {
                  range "1 .. 65535";
                }
              }
              description
                "Weight of the gateway";
            }
            uses apply-advanced;
            choice weight_type {
              case case_1 {
                leaf all-nexthop {
                  type empty;
                  description
                    "All the gateway weight should be matched";
                }
              }
            }
          }
          list nexthop-ecmp {
            key "choice-ident choice-value ecmp";
            ordered-by user;
            description
              "Qualify nexthop equal cost multipath gateways";
            leaf choice-ident {
              type enumeration {
                enum "equal";
                enum "greater-than";
                enum "less-than";
                enum "greater-than-equal";
                enum "less-than-equal";
              }
            }
            leaf choice-value {
              type string;
            }
            leaf ecmp {
              type union {
                type string {
                  pattern "<.*>|$.*";
                }
                type uint32 {
                  range "1 .. 512";
                }
              }
              description
                "Number of equal cost multipath gateways";
            }
            uses apply-advanced;
          }
          leaf metric {
            type union {
              type uint32;
              type string {
                pattern "<.*>|$.*";
              }
            }
            description
              "Metric value";
          }
          leaf metric2 {
            type union {
              type uint32;
              type string {
                pattern "<.*>|$.*";
              }
            }
            description
              "Metric value 2";
          }
          leaf metric3 {
            type union {
              type uint32;
              type string {
                pattern "<.*>|$.*";
              }
            }
            description
              "Metric value 3";
          }
          leaf metric4 {
            type union {
              type uint32;
              type string {
                pattern "<.*>|$.*";
              }
            }
            description
              "Metric value 4";
          }
          leaf-list tag {
            type union {
              type uint32;
              type string {
                pattern "<.*>|$.*";
              }
            }
            ordered-by user;
            description
              "Tag string";
          }
          leaf-list tag2 {
            type union {
              type uint32;
              type string {
                pattern "<.*>|$.*";
              }
            }
            ordered-by user;
            description
              "Tag string 2";
          }
          leaf preference {
            type union {
              type uint32;
              type string {
                pattern "<.*>|$.*";
              }
            }
            description
              "Preference value";
          }
          leaf preference2 {
            type union {
              type uint32;
              type string {
                pattern "<.*>|$.*";
              }
            }
            description
              "Preference value 2";
          }
          leaf color {
            type union {
              type uint32;
              type string {
                pattern "<.*>|$.*";
              }
            }
            description
              "Color (preference) value";
          }
          leaf color2 {
            type union {
              type uint32;
              type string {
                pattern "<.*>|$.*";
              }
            }
            description
              "Color (preference) value 2";
          }
          leaf local-preference {
            type union {
              type uint32;
              type string {
                pattern "<.*>|$.*";
              }
            }
            description
              "Local preference associated with a route";
          }
          leaf-list policy {
            type jt:policy-algebra;
            ordered-by user;
            description
              "Name of policy to evaluate";
          }
          choice lsp-name-type {
            case case_1 {
              leaf lsp {
                type string;
                description
                  "Label switched path name";
              }
            }
            case case_2 {
              leaf lsp-regex {
                type string;
                description
                  "Label switched path name regular expression";
              }
            }
          }
          container source-routing-path {
            presence "enable source-routing-path";
            description
              "Spring-te lsp policy attributes";
            leaf name-regex {
              type string;
              description
                "Spring-te lsp name regex";
            }
            leaf dest {
              type jt:ipaddr;
              description
                "Spring-te lsp IPV4/IPV6 destination without color";
            }
            leaf origin {
              type jt:ipaddr;
              description
                "Spring-te lsp origin address";
            }
            leaf tunnel-source {
              type enumeration {
                enum "pcep" {
                  description
                    "Spring-te lsp src pcep";
                }
                enum "bgp" {
                  description
                    "Spring-te lsp src bgp";
                }
              }
              description
                "Spring-te lsp source protocol";
            }
            leaf route-distinguisher {
              type union {
                type uint32;
                type string {
                  pattern "<.*>|$.*";
                }
              }
              description
                "Spring-te lsp route distinguisher";
            }
            leaf color {
              type union {
                type uint32;
                type string {
                  pattern "<.*>|$.*";
                }
              }
              description
                "Spring-te lsp color";
            }
          }
          list route-filter {
            key "address choice-ident choice-value";
            ordered-by user;
            description
              "List of routes to match";
            uses control_route_filter_type;
          }
          list source-address-filter {
            key "address choice-ident choice-value";
            ordered-by user;
            description
              "List of source addresses to match";
            uses control_source_address_filter_type;
          }
          list prefix-list {
            key "name";
            ordered-by user;
            description
              "List of prefix-lists of routes to match";
            uses control_prefix_list_type;
          }
          list rib-list {
            key "name";
            ordered-by user;
            description
              "List of routing-tables";
            uses control_rib_list_type;
          }
          list as-path-neighbors {
            key "list-type list-name";
            ordered-by user;
            description
              "List of peer AS to match";
            uses control_as_list_type;
          }
          list as-path-origins {
            key "list-type list-name";
            ordered-by user;
            description
              "List of originating AS to match";
            uses control_as_list_type;
          }
          list as-path-transits {
            key "list-type list-name";
            ordered-by user;
            description
              "List of originating AS to match";
            uses control_as_list_type;
          }
          list prefix-list-filter {
            key "list_name choice-ident choice-value";
            ordered-by user;
            description
              "List of prefix-list-filters to match";
            uses control_prefix_list_filter_type;
          }
          list rtf-prefix-list {
            key "name";
            ordered-by user;
            description
              "List of rtf-prefix-lists of routes to match";
            uses control_rtf_prefix_list_type;
          }
          list route-filter-list {
            key "name";
            ordered-by user;
            description
              "List of route-filter-lists of routes to match";
            uses control_route_filter_list_type;
          }
          list source-address-filter-list {
            key "name";
            ordered-by user;
            description
              "List of source-address-filter-lists of routes to match";
            uses control_source_address_filter_list_type;
          }
          container multicast-scope {
            description
              "Multicast scope to match";
            choice scope-choice {
              case case_1 {
                leaf node-local {
                  type empty;
                  description
                    "Node-local scope";
                }
              }
              case case_2 {
                leaf link-local {
                  type empty;
                  description
                    "Link-local scope";
                }
              }
              case case_3 {
                leaf site-local {
                  type empty;
                  description
                    "Site-local scope";
                }
              }
              case case_4 {
                leaf organization-local {
                  type empty;
                  description
                    "Organization-local scope";
                }
              }
              case case_5 {
                leaf global {
                  type empty;
                  description
                    "Global scope";
                }
              }
              case case_6 {
                leaf scope_value {
                  type union {
                    type string {
                      pattern "<.*>|$.*";
                    }
                    type uint32 {
                      range "0 .. 15";
                    }
                  }
                  description
                    "Scope value";
                }
              }
            }
            choice scope-operator {
              case case_1 {
                leaf orhigher {
                  type empty;
                  description
                    "Match higher values";
                }
              }
              case case_2 {
                leaf orlower {
                  type empty;
                  description
                    "Match lower values";
                }
              }
            }
          }
          leaf aggregate-contributor {
            type empty;
            description
              "Match more specifics of an aggregate";
          }
          leaf state {
            type enumeration {
              enum "active" {
                description
                  "Active route";
              }
              enum "inactive" {
                description
                  "Inactive route";
              }
            }
            description
              "Route state";
          }
          leaf-list tunnel-type {
            type enumeration {
              enum "gre" {
                description
                  "GRE tunnel";
              }
              enum "udp" {
                description
                  "UDP tunnel";
              }
              enum "ipip" {
                description
                  "IPIP tunnel";
              }
            }
            ordered-by user;
            description
              "Tunnel type";
          }
          leaf route-type {
            type enumeration {
              enum "internal" {
                description
                  "Internal route";
              }
              enum "external" {
                description
                  "External route";
              }
            }
            description
              "Route type";
          }
          leaf-list nlri-route-type {
            type union {
              type string {
                pattern "<.*>|$.*";
              }
              type uint32 {
                range "1 .. 10";
              }
            }
            ordered-by user;
            description
              "Route type from NLRI";
          }
          leaf-list evpn-tag {
            type union {
              type string {
                pattern "<.*>|$.*";
              }
              type uint32 {
                range "0 .. 4294967295";
              }
            }
            ordered-by user;
            description
              "Tag in EVPN Route";
          }
          leaf-list evpn-esi {
            type string;
            ordered-by user;
            description
              "ESI in EVPN Route";
          }
          list mac-filter-list {
            key "name";
            ordered-by user;
            description
              "List of mac-filter-list macs to match";
            uses control_mac_address_filter_list_type;
          }
          leaf evpn-mac-route {
            type enumeration {
              enum "mac-only" {
                description
                  "MAC route";
              }
              enum "mac-ipv4" {
                description
                  "MAC IPV4 route";
              }
              enum "mac-ipv6" {
                description
                  "MAC IPV6 route";
              }
            }
            description
              "EVPN Mac Route type";
          }
          leaf-list bridge-domain-id {
            type union {
              type string {
                pattern "<.*>|$.*";
              }
              type uint32 {
                range "0 .. 4294967295";
              }
            }
            ordered-by user;
            description
              "Bridge Domain Identifier (Vlan or VNI)";
          }
          leaf next-hop-type {
            type enumeration {
              enum "merged" {
                description
                  "Merged next hop";
              }
            }
            description
              "Next-hop type";
          }
          leaf-list condition {
            type string;
            ordered-by user;
            description
              "Condition to match on";
          }
          list community-count {
            key "name";
            ordered-by user;
            description
              "Number of BGP communities";
            uses community_count_type;
          }
          list large-community-count {
            key "name";
            ordered-by user;
            description
              "Number of Large BGP communities";
            uses community_count_type;
          }
          list as-path-unique-count {
            key "name";
            ordered-by user;
            description
              "Number of unique BGP ASes excluding confederations";
            uses as-path-unique-count-type;
          }
          list as-path-calc-length {
            key "name";
            ordered-by user;
            description
              "Number of BGP ASes excluding confederations";
            uses as-path-calc-length-type;
          }
          container traffic-engineering {
            presence "enable traffic-engineering";
            description
              "Traffic-Engineering related parameters";
            uses apply-advanced;
            leaf-list protocol {
              type enumeration {
                enum "direct" {
                  description
                    "Directly originated";
                }
                enum "ospf" {
                  description
                    "OSPF originated";
                }
                enum "isis-level-1" {
                  description
                    "ISIS level-1 originated";
                }
                enum "isis-level-2" {
                  description
                    "ISIS level-2 originated";
                }
                enum "spring-te" {
                  description
                    "SPRING-TE originated";
                }
                enum "static" {
                  description
                    "Statically originated";
                }
                enum "unknown" {
                  description
                    "Originated by unknown sources";
                }
              }
              ordered-by user;
              description
                "Protocol that originated the entry";
            }
            container node {
              presence "enable node";
              description
                "Node-related parameters";
              uses apply-advanced;
              leaf as {
                type string;
                description
                  "AS number";
              }
              leaf node-type {
                type enumeration {
                  enum "router" {
                    description
                      "Real node";
                  }
                  enum "pseudo-node" {
                    description
                      "Pseudo-node";
                  }
                }
                description
                  "Real or pseudo-node";
              }
              leaf router-id {
                type jt:ipprefix;
                description
                  "IP prefix to match the router-id against";
              }
              leaf sys-id {
                type jt:sysid;
                description
                  "ISO address of the node";
              }
            }
            container ipv4-prefix {
              presence "enable ipv4-prefix";
              description
                "IPV4 prefix-related parameters";
              uses apply-advanced;
              leaf as {
                type string;
                description
                  "AS number";
              }
              leaf router-id {
                type jt:ipprefix;
                description
                  "IP prefix to match the router-id against";
              }
              leaf prefix {
                type jt:ipprefix;
                description
                  "IP prefix to match against";
              }
              leaf sys-id {
                type jt:sysid;
                description
                  "ISO address of the node";
              }
            }
            container ipv6-prefix {
              presence "enable ipv6-prefix";
              description
                "IPV6 prefix related parameters";
              uses apply-advanced;
              leaf as {
                type string;
                description
                  "AS number";
              }
              leaf router-id {
                type jt:ipprefix;
                description
                  "IPv6 prefix to match the router-id against";
              }
              leaf prefix {
                type jt:ipv6prefix;
                description
                  "IPv6 prefix to match against";
              }
              leaf sys-id {
                type jt:sysid;
                description
                  "ISO address of the node";
              }
            }
            container srv6-sid {
              presence "enable srv6-sid";
              description
                "SRV6 SID related parameters";
              uses apply-advanced;
              leaf as {
                type string;
                description
                  "AS number";
              }
              leaf router-id {
                type jt:ipprefix;
                description
                  "SRv6 SID to match the router-id against";
              }
              leaf sid {
                type jt:ipv6addr;
                description
                  "SRv6 SID to match against";
              }
              leaf sys-id {
                type jt:sysid;
                description
                  "ISO address of the node";
              }
            }
            container spring-te {
              presence "enable spring-te";
              description
                "SPRING-TE policy related parameters";
              uses apply-advanced;
              leaf node-as {
                type string;
                description
                  "Node AS number";
              }
              leaf router-id {
                type jt:ipprefix;
                description
                  "IP prefix to match against the node for the SPRING TE policy";
              }
              leaf color {
                type union {
                  type uint32;
                  type string {
                    pattern "<.*>|$.*";
                  }
                }
                description
                  "Color of the SPRING-TE policy candidate path";
              }
              leaf discriminator {
                type union {
                  type uint32;
                  type string {
                    pattern "<.*>|$.*";
                  }
                }
                description
                  "Discriminator of the SPRING-TE policy candidate path";
              }
              leaf endpoint {
                type jt:ipaddr;
                description
                  "Endpoint of the SPRING-TE policy candidate path";
              }
              leaf protocol-origin {
                type enumeration {
                  enum "bgp" {
                    description
                      "SPRING-TE policy candidate path originated by BGP";
                  }
                  enum "cli" {
                    description
                      "SPRING-TE policy candidate path originated by cli";
                  }
                  enum "pcep" {
                    description
                      "SPRING-TE policy candidate path originated by PCEP";
                  }
                }
                description
                  "Protocol originating the SPRING-TE policy candidate path";
              }
              leaf origin-as {
                type string;
                description
                  "AS number of the node creating the SPRING-TE policy candidate path";
              }
              leaf origin-addr {
                type jt:ipaddr;
                description
                  "Address of the node originating the SPRING-TE policy candidate path";
              }
            }
            container link {
              presence "enable link";
              description
                "Link-related parameters";
              uses apply-advanced;
              container from {
                description
                  "Specify parameter of the 'from' side";
                uses apply-advanced;
                leaf as {
                  type string;
                  description
                    "AS number";
                }
                leaf router-id {
                  type jt:ipprefix;
                  description
                    "IP prefix to match the router-id against";
                }
                leaf sys-id {
                  type jt:sysid;
                  description
                    "System-ID of the node";
                }
                leaf node-type {
                  type enumeration {
                    enum "router" {
                      description
                        "Real node";
                    }
                    enum "pseudo-node" {
                      description
                        "Pseudo-node";
                    }
                  }
                  description
                    "Type of the node";
                }
                leaf link-address {
                  type jt:ipprefix;
                  description
                    "IP prefix to match the link address against";
                }
              }
              container to {
                description
                  "Specify parameters of the 'to' side";
                uses apply-advanced;
                leaf as {
                  type string;
                  description
                    "AS number";
                }
                leaf router-id {
                  type jt:ipprefix;
                  description
                    "IP prefix to match the router-id against";
                }
                leaf sys-id {
                  type jt:sysid;
                  description
                    "System-ID of the node";
                }
                leaf node-type {
                  type enumeration {
                    enum "router" {
                      description
                        "Real node";
                    }
                    enum "pseudo-node" {
                      description
                        "Pseudo-node";
                    }
                  }
                  description
                    "Type of the node";
                }
                leaf link-address {
                  type jt:ipprefix;
                  description
                    "IP prefix to match the link address against";
                }
              }
            }
            leaf identifier {
              type union {
                type string {
                  pattern "<.*>|$.*";
                }
                type uint64 {
                  range "2 .. 18446744073709551615";
                }
              }
              description
                "BGP-TE identifier";
            }
          }
          leaf-list route-distinguisher {
            type string;
            ordered-by user;
            description
              "Name of the route-distinguisher";
          }
          leaf prefix-segment {
            type empty;
            description
              "Prefix segment present in route extended data";
          }
        }
        container to {
          description
            "Conditions to match the destination of a route";
          uses apply-advanced;
          leaf instance {
            type string;
            description
              "Routing protocol instance";
          }
          leaf instance-any {
            type empty;
            description
              "Any routing protocol instance";
          }
          leaf-list instance-list {
            type string;
            description
              "A list of routing protocol instances";
          }
          leaf-list igp-instance {
            type string;
            description
              "IGP instance";
          }
          leaf igp-instance-regex {
            type jt:regular-expression;
            description
              "IGP instance name regular expression";
          }
          leaf family {
            type enumeration {
              enum "inet" {
                description
                  "IPv4 family";
              }
              enum "inet-vpn" {
                description
                  "IPv4-VPN family";
              }
              enum "inet6" {
                description
                  "IPv6 family";
              }
              enum "inet6-vpn" {
                description
                  "IPv6-VPN family";
              }
              enum "iso-vpn" {
                description
                  "ISO-VPN family";
              }
              enum "iso" {
                description
                  "ISO family";
              }
              enum "evpn" {
                description
                  "EVPN family";
              }
              enum "inet-mvpn" {
                description
                  "IPv4 Multicast VPN family";
              }
              enum "inet6-mvpn" {
                description
                  "IPv6 Multicast VPN family";
              }
              enum "inet-mdt" {
                description
                  "IPv4 MDT Signaling family";
              }
              enum "route-target" {
                description
                  "Local route target VPN family";
              }
              enum "traffic-engineering" {
                description
                  "Traffic Engineering family";
              }
              enum "inet-srte" {
                description
                  "IPv4 srtte family";
              }
              enum "inet6-srte" {
                description
                  "IPv6 srte family";
              }
            }
          }
          leaf-list protocol {
            type enumeration {
              enum "aggregate" {
                description
                  "Aggregate routes";
              }
              enum "bgp" {
                description
                  "BGP";
              }
              enum "direct" {
                description
                  "Directly connected routes";
              }
              enum "dvmrp" {
                description
                  "Distance Vector Multicast Routing Protocol";
              }
              enum "isis" {
                description
                  "Intermediate System-to-Intermediate System";
              }
              enum "esis" {
                description
                  "End System-to-Intermediate System";
              }
              enum "l-isis" {
                description
                  "Labelled ISIS";
              }
              enum "l2circuit" {
                description
                  "Layer 2 circuits";
              }
              enum "l2vpn" {
                description
                  "Layer 2 MPLS virtual private networks";
              }
              enum "local" {
                description
                  "Local system addresses";
              }
              enum "ospf" {
                description
                  "Open Shortest Path First";
              }
              enum "ospf2" {
                description
                  "Open Shortest Path First Version 2";
              }
              enum "ospf3" {
                description
                  "Open Shortest Path First Version 3";
              }
              enum "l-ospf" {
                description
                  "Labelled OSPF";
              }
              enum "pim" {
                description
                  "Protocol Independent Multicast";
              }
              enum "rip" {
                description
                  "Routing Information Protocol";
              }
              enum "ripng" {
                description
                  "Routing Information Protocol next generation";
              }
              enum "static" {
                description
                  "Statically defined addresses";
              }
              enum "arp" {
                description
                  "Addresses learned from ARP";
              }
              enum "frr" {
                description
                  "Addresses created by Host Fast Re-route";
              }
              enum "mpls" {
                description
                  "Multiprotocol Label Switching";
              }
              enum "ldp" {
                description
                  "Label Distribution Protocol";
              }
              enum "rsvp" {
                description
                  "Resource Reservation Protocol";
              }
              enum "msdp" {
                description
                  "Multicast Source Discovery Protocol";
              }
              enum "route-target" {
                description
                  "Local route target VPN membership";
              }
              enum "access" {
                description
                  "Access server routes";
              }
              enum "access-internal" {
                description
                  "Internal routes to directly connected clients";
              }
              enum "anchor" {
                description
                  "Anchor routes connected to UEs";
              }
              enum "bgp-static" {
                description
                  "BGP static routes";
              }
              enum "vpls" {
                description
                  "Virtual Private LAN Service";
              }
              enum "evpn" {
                description
                  "Ethernet VPN Service";
              }
              enum "spring-te" {
                description
                  "SPRING Traffic-Engineered";
              }
              enum "bgp-ls-epe" {
                description
                  "Addresses created by BGP-LS egress TE";
              }
              enum "express-segments" {
                description
                  "Express-segment routes";
              }
              enum "rift" {
                description
                  "RIFT routes";
              }
              enum "l2-learned-host-routing" {
                description
                  "Layer2-learned host routes";
              }
              enum "srv6-isis" {
                description
                  "SRV6 ISIS";
              }
              enum "ari-ts" {
                description
                  "ARI TS routes";
              }
              enum "srv6" {
                description
                  "Segment Routing IPv6 local route";
              }
            }
            ordered-by user;
            description
              "Protocol from which route was learned";
          }
          leaf rib {
            type string;
            description
              "Routing table";
          }
          leaf-list neighbor {
            type jt:ipaddr;
            ordered-by user;
            description
              "Neighboring router";
          }
          leaf-list next-hop {
            type jt:ipaddr;
            ordered-by user;
            description
              "Next-hop router";
          }
          leaf-list interface {
            type union {
              type jt:ipaddr-or-interface;
              type string {
                pattern "<.*>|$.*";
              }
            }
            ordered-by user;
            description
              "Interface name or address";
          }
          leaf area {
            type jt:areaid;
            description
              "OSPF area identifier";
          }
          leaf-list as-path {
            type string;
            ordered-by user;
            description
              "Name of AS path regular expression (BGP only)";
          }
          leaf-list as-path-group {
            type string;
            ordered-by user;
            description
              "Name of AS path group (BGP only)";
          }
          leaf origin {
            type enumeration {
              enum "igp" {
                description
                  "Path originated in the local IGP";
              }
              enum "egp" {
                description
                  "Path originated in another AS";
              }
              enum "incomplete" {
                description
                  "Path was learned by some other means";
              }
            }
            description
              "BGP origin attribute";
          }
          leaf-list community {
            type string;
            ordered-by user;
            description
              "BGP community";
          }
          leaf level {
            type union {
              type uint32;
              type string {
                pattern "<.*>|$.*";
              }
            }
            description
              "IS-IS level";
          }
          container external {
            presence "enable external";
            description
              "External route";
            uses apply-advanced;
            leaf type {
              type union {
                type string {
                  pattern "<.*>|$.*";
                }
                type int32 {
                  range "1 .. 2";
                }
              }
              description
                "OSPF external metric type";
            }
          }
          leaf bgp-srte-discriminator {
            type union {
              type uint32;
              type string {
                pattern "<.*>|$.*";
              }
            }
            description
              "Srte discriminator";
          }
          leaf srte-color {
            type union {
              type uint32;
              type string {
                pattern "<.*>|$.*";
              }
            }
            description
              "Srte color";
          }
          leaf programmed {
            type empty;
            description
              "API-programmed route";
          }
          leaf validation-database {
            type enumeration {
              enum "valid" {
                description
                  "Match for valid database validation-state";
              }
              enum "invalid" {
                description
                  "Match for invalid database validation-state";
              }
              enum "unknown" {
                description
                  "Match for unknown database validation-state";
              }
            }
            description
              "Name to identify a validation-state";
          }
          container validation-database-instance {
            presence "enable validation-database-instance";
            description
              "Name to identify a validation-state with DB name";
            uses apply-advanced;
            leaf database-name {
              type string;
              description
                "Route Validation Database name to be looked at";
            }
            leaf state {
              type enumeration {
                enum "valid" {
                  description
                    "Match for valid database validation-state";
                }
                enum "invalid" {
                  description
                    "Match for invalid database validation-state";
                }
                enum "unknown" {
                  description
                    "Match for unknown database validation-state";
                }
              }
              mandatory true;
              description
                "Name to identify a validation-state";
            }
          }
          list nexthop-weight {
            key "choice-ident choice-value weight";
            ordered-by user;
            description
              "Weight of the gateway";
            leaf choice-ident {
              type enumeration {
                enum "equal";
                enum "greater-than";
                enum "less-than";
                enum "greater-than-equal";
                enum "less-than-equal";
              }
            }
            leaf choice-value {
              type string;
            }
            leaf weight {
              type union {
                type string {
                  pattern "<.*>|$.*";
                }
                type uint32 {
                  range "1 .. 65535";
                }
              }
              description
                "Weight of the gateway";
            }
            uses apply-advanced;
            choice weight_type {
              case case_1 {
                leaf all-nexthop {
                  type empty;
                  description
                    "All the gateway weight should be matched";
                }
              }
            }
          }
          list nexthop-ecmp {
            key "choice-ident choice-value ecmp";
            ordered-by user;
            description
              "Qualify nexthop equal cost multipath gateways";
            leaf choice-ident {
              type enumeration {
                enum "equal";
                enum "greater-than";
                enum "less-than";
                enum "greater-than-equal";
                enum "less-than-equal";
              }
            }
            leaf choice-value {
              type string;
            }
            leaf ecmp {
              type union {
                type string {
                  pattern "<.*>|$.*";
                }
                type uint32 {
                  range "1 .. 512";
                }
              }
              description
                "Number of equal cost multipath gateways";
            }
            uses apply-advanced;
          }
          leaf metric {
            type union {
              type uint32;
              type string {
                pattern "<.*>|$.*";
              }
            }
            description
              "Metric value";
          }
          leaf metric2 {
            type union {
              type uint32;
              type string {
                pattern "<.*>|$.*";
              }
            }
            description
              "Metric value 2";
          }
          leaf metric3 {
            type union {
              type uint32;
              type string {
                pattern "<.*>|$.*";
              }
            }
            description
              "Metric value 3";
          }
          leaf metric4 {
            type union {
              type uint32;
              type string {
                pattern "<.*>|$.*";
              }
            }
            description
              "Metric value 4";
          }
          leaf-list tag {
            type union {
              type uint32;
              type string {
                pattern "<.*>|$.*";
              }
            }
            ordered-by user;
            description
              "Tag string";
          }
          leaf-list tag2 {
            type union {
              type uint32;
              type string {
                pattern "<.*>|$.*";
              }
            }
            ordered-by user;
            description
              "Tag string 2";
          }
          leaf preference {
            type union {
              type uint32;
              type string {
                pattern "<.*>|$.*";
              }
            }
            description
              "Preference value";
          }
          leaf preference2 {
            type union {
              type uint32;
              type string {
                pattern "<.*>|$.*";
              }
            }
            description
              "Preference value 2";
          }
          leaf color {
            type union {
              type uint32;
              type string {
                pattern "<.*>|$.*";
              }
            }
            description
              "Color (preference) value";
          }
          leaf color2 {
            type union {
              type uint32;
              type string {
                pattern "<.*>|$.*";
              }
            }
            description
              "Color (preference) value 2";
          }
          leaf local-preference {
            type union {
              type uint32;
              type string {
                pattern "<.*>|$.*";
              }
            }
            description
              "Local preference associated with a route";
          }
          leaf-list policy {
            type jt:policy-algebra;
            ordered-by user;
            description
              "Name of policy to evaluate";
          }
          choice lsp-name-type {
            case case_1 {
              leaf lsp {
                type string;
                description
                  "Label switched path name";
              }
            }
            case case_2 {
              leaf lsp-regex {
                type string;
                description
                  "Label switched path name regular expression";
              }
            }
          }
          container source-routing-path {
            presence "enable source-routing-path";
            description
              "Spring-te lsp policy attributes";
            leaf name-regex {
              type string;
              description
                "Spring-te lsp name regex";
            }
            leaf dest {
              type jt:ipaddr;
              description
                "Spring-te lsp IPV4/IPV6 destination without color";
            }
            leaf origin {
              type jt:ipaddr;
              description
                "Spring-te lsp origin address";
            }
            leaf tunnel-source {
              type enumeration {
                enum "pcep" {
                  description
                    "Spring-te lsp src pcep";
                }
                enum "bgp" {
                  description
                    "Spring-te lsp src bgp";
                }
              }
              description
                "Spring-te lsp source protocol";
            }
            leaf route-distinguisher {
              type union {
                type uint32;
                type string {
                  pattern "<.*>|$.*";
                }
              }
              description
                "Spring-te lsp route distinguisher";
            }
            leaf color {
              type union {
                type uint32;
                type string {
                  pattern "<.*>|$.*";
                }
              }
              description
                "Spring-te lsp color";
            }
          }
        }
        container then {
          description
            "Actions to take if 'from' and 'to' conditions match";
          uses apply-advanced;
          container metric {
            description
              "Metric value";
            uses apply-advanced;
            choice metric_action {
              case case_1 {
                leaf metric {
                  type union {
                    type uint32;
                    type string {
                      pattern "<.*>|$.*";
                    }
                  }
                }
              }
              case case_2 {
                leaf add {
                  type union {
                    type uint32;
                    type string {
                      pattern "<.*>|$.*";
                    }
                  }
                  description
                    "Add constant to attribute";
                }
              }
              case case_3 {
                leaf subtract {
                  type union {
                    type uint32;
                    type string {
                      pattern "<.*>|$.*";
                    }
                  }
                  description
                    "Subtract constant from attribute";
                }
              }
              case case_4 {
                container igp {
                  presence "enable igp";
                  description
                    "Track the IGP metric (BGP only)";
                  leaf metric_offset {
                    type union {
                      type int32;
                      type string {
                        pattern "<.*>|$.*";
                      }
                    }
                    description
                      "Metric offset for MED";
                  }
                }
              }
              case case_5 {
                container minimum-igp {
                  presence "enable minimum-igp";
                  description
                    "Track the minimum IGP metric (BGP only)";
                  leaf metric_offset {
                    type union {
                      type int32;
                      type string {
                        pattern "<.*>|$.*";
                      }
                    }
                    description
                      "Metric offset for MED";
                  }
                }
              }
              case case_6 {
                container expression {
                  description
                    "Calculate value based on route metric and metric2";
                  uses metric_expression_type;
                }
              }
              case case_7 {
                leaf aigp {
                  type empty;
                  description
                    "Use aigp, if it exists, to set the IGP metric";
                }
              }
              case case_8 {
                container effective-aigp {
                  presence "enable effective-aigp";
                  description
                    "Track the effective AIGP metric (BGP only)";
                  leaf metric_offset {
                    type union {
                      type int32;
                      type string {
                        pattern "<.*>|$.*";
                      }
                    }
                    description
                      "Metric offset for MED";
                  }
                }
              }
              case case_9 {
                container minimum-effective-aigp {
                  presence "enable minimum-effective-aigp";
                  description
                    "Track the minimum effective AIGP metric (BGP only)";
                  leaf metric_offset {
                    type union {
                      type int32;
                      type string {
                        pattern "<.*>|$.*";
                      }
                    }
                    description
                      "Metric offset for MED";
                  }
                }
              }
            }
          }
          container metric2 {
            description
              "Metric value 2";
            uses apply-advanced;
            choice metric_action {
              case case_1 {
                leaf metric2 {
                  type union {
                    type uint32;
                    type string {
                      pattern "<.*>|$.*";
                    }
                  }
                }
              }
              case case_2 {
                leaf add {
                  type union {
                    type uint32;
                    type string {
                      pattern "<.*>|$.*";
                    }
                  }
                  description
                    "Add constant to attribute";
                }
              }
              case case_3 {
                leaf subtract {
                  type union {
                    type uint32;
                    type string {
                      pattern "<.*>|$.*";
                    }
                  }
                  description
                    "Subtract constant from attribute";
                }
              }
            }
          }
          container metric3 {
            description
              "Metric value 3";
            uses apply-advanced;
            choice metric_action {
              case case_1 {
                leaf metric3 {
                  type union {
                    type uint32;
                    type string {
                      pattern "<.*>|$.*";
                    }
                  }
                }
              }
              case case_2 {
                leaf add {
                  type union {
                    type uint32;
                    type string {
                      pattern "<.*>|$.*";
                    }
                  }
                  description
                    "Add constant to attribute";
                }
              }
              case case_3 {
                leaf subtract {
                  type union {
                    type uint32;
                    type string {
                      pattern "<.*>|$.*";
                    }
                  }
                  description
                    "Subtract constant from attribute";
                }
              }
            }
          }
          container metric4 {
            description
              "Metric value 4";
            uses apply-advanced;
            choice metric_action {
              case case_1 {
                leaf metric4 {
                  type union {
                    type uint32;
                    type string {
                      pattern "<.*>|$.*";
                    }
                  }
                }
              }
              case case_2 {
                leaf add {
                  type union {
                    type uint32;
                    type string {
                      pattern "<.*>|$.*";
                    }
                  }
                  description
                    "Add constant to attribute";
                }
              }
              case case_3 {
                leaf subtract {
                  type union {
                    type uint32;
                    type string {
                      pattern "<.*>|$.*";
                    }
                  }
                  description
                    "Subtract constant from attribute";
                }
              }
            }
          }
          container tag {
            description
              "Tag string";
            uses apply-advanced;
            choice metric_action {
              case case_1 {
                leaf tag {
                  type union {
                    type uint32;
                    type string {
                      pattern "<.*>|$.*";
                    }
                  }
                }
              }
              case case_2 {
                leaf add {
                  type union {
                    type uint32;
                    type string {
                      pattern "<.*>|$.*";
                    }
                  }
                  description
                    "Add constant to attribute";
                }
              }
              case case_3 {
                leaf subtract {
                  type union {
                    type uint32;
                    type string {
                      pattern "<.*>|$.*";
                    }
                  }
                  description
                    "Subtract constant from attribute";
                }
              }
            }
          }
          container tag2 {
            description
              "Tag string 2";
            uses apply-advanced;
            choice metric_action {
              case case_1 {
                leaf tag2 {
                  type union {
                    type uint32;
                    type string {
                      pattern "<.*>|$.*";
                    }
                  }
                }
              }
              case case_2 {
                leaf add {
                  type union {
                    type uint32;
                    type string {
                      pattern "<.*>|$.*";
                    }
                  }
                  description
                    "Add constant to attribute";
                }
              }
              case case_3 {
                leaf subtract {
                  type union {
                    type uint32;
                    type string {
                      pattern "<.*>|$.*";
                    }
                  }
                  description
                    "Subtract constant from attribute";
                }
              }
            }
          }
          container preference {
            description
              "Preference value";
            uses apply-advanced;
            choice metric_action {
              case case_1 {
                leaf preference {
                  type union {
                    type uint32;
                    type string {
                      pattern "<.*>|$.*";
                    }
                  }
                }
              }
              case case_2 {
                leaf add {
                  type union {
                    type uint32;
                    type string {
                      pattern "<.*>|$.*";
                    }
                  }
                  description
                    "Add constant to attribute";
                }
              }
              case case_3 {
                leaf subtract {
                  type union {
                    type uint32;
                    type string {
                      pattern "<.*>|$.*";
                    }
                  }
                  description
                    "Subtract constant from attribute";
                }
              }
            }
          }
          container preference2 {
            description
              "Preference value 2";
            uses apply-advanced;
            choice metric_action {
              case case_1 {
                leaf preference2 {
                  type union {
                    type uint32;
                    type string {
                      pattern "<.*>|$.*";
                    }
                  }
                }
              }
              case case_2 {
                leaf add {
                  type union {
                    type uint32;
                    type string {
                      pattern "<.*>|$.*";
                    }
                  }
                  description
                    "Add constant to attribute";
                }
              }
              case case_3 {
                leaf subtract {
                  type union {
                    type uint32;
                    type string {
                      pattern "<.*>|$.*";
                    }
                  }
                  description
                    "Subtract constant from attribute";
                }
              }
            }
          }
          container color {
            description
              "Color (preference) value";
            uses apply-advanced;
            choice metric_action {
              case case_1 {
                leaf color {
                  type union {
                    type uint32;
                    type string {
                      pattern "<.*>|$.*";
                    }
                  }
                }
              }
              case case_2 {
                leaf add {
                  type union {
                    type uint32;
                    type string {
                      pattern "<.*>|$.*";
                    }
                  }
                  description
                    "Add constant to attribute";
                }
              }
              case case_3 {
                leaf subtract {
                  type union {
                    type uint32;
                    type string {
                      pattern "<.*>|$.*";
                    }
                  }
                  description
                    "Subtract constant from attribute";
                }
              }
            }
          }
          container color2 {
            description
              "Color (preference) value 2";
            uses apply-advanced;
            choice metric_action {
              case case_1 {
                leaf color2 {
                  type union {
                    type uint32;
                    type string {
                      pattern "<.*>|$.*";
                    }
                  }
                }
              }
              case case_2 {
                leaf add {
                  type union {
                    type uint32;
                    type string {
                      pattern "<.*>|$.*";
                    }
                  }
                  description
                    "Add constant to attribute";
                }
              }
              case case_3 {
                leaf subtract {
                  type union {
                    type uint32;
                    type string {
                      pattern "<.*>|$.*";
                    }
                  }
                  description
                    "Subtract constant from attribute";
                }
              }
            }
          }
          container local-preference {
            description
              "Local preference associated with a route";
            uses apply-advanced;
            choice metric_action {
              case case_1 {
                leaf local-preference {
                  type union {
                    type uint32;
                    type string {
                      pattern "<.*>|$.*";
                    }
                  }
                }
              }
              case case_2 {
                leaf add {
                  type union {
                    type uint32;
                    type string {
                      pattern "<.*>|$.*";
                    }
                  }
                  description
                    "Add constant to attribute";
                }
              }
              case case_3 {
                leaf subtract {
                  type union {
                    type uint32;
                    type string {
                      pattern "<.*>|$.*";
                    }
                  }
                  description
                    "Subtract constant from attribute";
                }
              }
            }
          }
          container credibility {
            description
              "TED credibility value for entries from BGP-TE";
            uses apply-advanced;
            choice metric_action {
              case case_1 {
                leaf credibility {
                  type union {
                    type uint32;
                    type string {
                      pattern "<.*>|$.*";
                    }
                  }
                }
              }
              case case_2 {
                leaf add {
                  type union {
                    type uint32;
                    type string {
                      pattern "<.*>|$.*";
                    }
                  }
                  description
                    "Add constant to attribute";
                }
              }
              case case_3 {
                leaf subtract {
                  type union {
                    type uint32;
                    type string {
                      pattern "<.*>|$.*";
                    }
                  }
                  description
                    "Subtract constant from attribute";
                }
              }
            }
          }
          leaf priority {
            type enumeration {
              enum "high" {
                description
                  "Set priority to high";
              }
              enum "medium" {
                description
                  "Set priority to medium";
              }
              enum "low" {
                description
                  "Set priority to low";
              }
            }
            description
              "Set priority for route installation";
          }
          container prefix-segment {
            description
              "Set prefix segment attributes";
            uses apply-advanced;
            list algorithm {
              key "name";
              max-elements 15;
              description
                "Set prefix segment attributes for strict/flex algorithm ";
              leaf name {
                type union {
                  type string {
                    pattern "<.*>|$.*";
                  }
                  type uint32 {
                    range "1 .. 255";
                  }
                }
                mandatory true;
                description
                  "Set prefix segment for strict/flex algorithm";
              }
              leaf index {
                type union {
                  type string {
                    pattern "<.*>|$.*";
                  }
                  type uint32 {
                    range "0 .. 1048575";
                  }
                }
                mandatory true;
                description
                  "Set prefix segment index id";
              }
              leaf node-segment {
                type empty;
                description
                  "Set node segment flag for this prefix segment";
              }
            }
            leaf index {
              type union {
                type string {
                  pattern "<.*>|$.*";
                }
                type uint32 {
                  range "0 .. 1048575";
                }
              }
              description
                "Set prefix segment index id";
            }
            leaf node-segment {
              type empty;
              description
                "Set node segment flag for default prefix segment";
            }
            leaf redistribute {
              type empty;
              description
                "Redistribute prefix-segment from route entry";
            }
          }
          leaf label-allocation {
            type enumeration {
              enum "per-table" {
                description
                  "Set per-table label allocation mode";
              }
              enum "per-nexthop" {
                description
                  "Set per-nexthop label allocation mode";
              }
              enum "per-table-localize" {
                description
                  "Set per-table-localize label allocation mode";
              }
            }
            description
              "Set label allocation mode";
          }
          container add-path {
            description
              "Set BGP add-path attributes";
            leaf send-count {
              type union {
                type string {
                  pattern "<.*>|$.*";
                }
                type uint32 {
                  range "2 .. 64";
                }
              }
              description
                "Number of add-paths sent";
            }
          }
          leaf fib-install-priority {
            type enumeration {
              enum "high" {
                description
                  "Set Fib install priority  to high";
              }
              enum "medium" {
                description
                  "Set Fib install priority to medium ";
              }
            }
            description
              "Set Fib Instalation priority of a route";
          }
          leaf validation-state {
            type enumeration {
              enum "valid" {
                description
                  "Set validaton-state to valid";
              }
              enum "invalid" {
                description
                  "Set validation-state to invalid";
              }
              enum "unknown" {
                description
                  "Set validation-state to unknown";
              }
            }
            description
              "Set validation-state of a route";
          }
          leaf origin {
            type enumeration {
              enum "igp" {
                description
                  "Path originated in the local IGP";
              }
              enum "egp" {
                description
                  "Path originated in another AS";
              }
              enum "incomplete" {
                description
                  "Path was learned by some other means";
              }
            }
            description
              "BGP path origin";
          }
          container srv6 {
            description
              "Configure SID with 128 bit address";
            leaf sid {
              type jt:ipv6addr;
              description
                "IPv6 Address";
            }
            leaf locator {
              type string;
              description
                "Name of locator";
            }
            choice locator_type {
              case case_1 {
                leaf micro-dt4-sid {
                  type empty;
                  description
                    "Micro SID type dt4";
                }
              }
              case case_2 {
                leaf micro-dt6-sid {
                  type empty;
                  description
                    "Micro SID type dt6";
                }
              }
              case case_3 {
                leaf micro-dt46-sid {
                  type empty;
                  description
                    "Micro SID type dt46";
                }
              }
            }
          }
          container aigp-originate {
            presence "enable aigp-originate";
            description
              "Originate a BGP AIGP attribute";
            leaf distance {
              type union {
                type uint32;
                type string {
                  pattern "<.*>|$.*";
                }
              }
              description
                "AIGP distance";
            }
          }
          container aigp-adjust {
            description
              "Adjust a BGP AIGP attribute";
            choice math-op {
              case case_1 {
                leaf add {
                  type empty;
                }
              }
              case case_2 {
                leaf subtract {
                  type empty;
                }
              }
              case case_3 {
                leaf multiply {
                  type empty;
                }
              }
              case case_4 {
                leaf divide {
                  type empty;
                }
              }
            }
            choice adjust-value {
              case case_1 {
                leaf user-value {
                  type union {
                    type uint64;
                    type string {
                      pattern "<.*>|$.*";
                    }
                  }
                  description
                    "Adjustment value";
                }
              }
              case case_2 {
                leaf distance-to-protocol-nexthop {
                  type empty;
                  description
                    "Metric2";
                }
              }
            }
          }
          list community {
            key "choice-ident choice-value community-name";
            ordered-by user;
            description
              "BGP community properties associated with a route";
            leaf choice-ident {
              type enumeration {
                enum "equal-literal";
                enum "set";
                enum "plus-literal";
                enum "add";
                enum "minus-literal";
                enum "delete";
              }
            }
            leaf choice-value {
              type string;
            }
            leaf community-name {
              type string;
              description
                "Name to identify a BGP community";
            }
          }
          list tunnel-attribute {
            key "choice-ident choice-value tunnel-attribute-name";
            ordered-by user;
            description
              "BGP tunnel attribute associated with a route";
            leaf choice-ident {
              type enumeration {
                enum "set";
                enum "remove";
              }
            }
            leaf choice-value {
              type string;
            }
            leaf tunnel-attribute-name {
              type string;
              description
                "Name of a tunnel attribute , or 'all'";
            }
          }
          container assisted-replication {
            presence "enable assisted-replication";
            description
              "Deterministic AR replicator knobs";
            uses apply-advanced;
            leaf-list replicator-ip {
              type jt:ipaddr;
              max-elements 1;
              description
                "Set deterministic AR replicator ip for the flow";
            }
            leaf strict {
              type empty;
              description
                "Do not use any other replicator";
            }
            leaf-list fallback-replicator-ip {
              type jt:ipaddr;
              max-elements 1;
              description
                "Set Fallback replicator-ip";
            }
          }
          leaf damping {
            type string;
            description
              "Define BGP route flap damping parameters";
          }
          container aggregate-bandwidth {
            presence "enable aggregate-bandwidth";
            description
              "Advertise aggregate outbound link bandwidth";
            uses apply-advanced;
            choice transitive-type {
              case case_1 {
                leaf transitive {
                  type empty;
                  description
                    "Transitive flag for link bandwidth";
                }
              }
              case case_2 {
                leaf non-transitive {
                  type empty;
                  description
                    "Non-Transitive flag for link bandwidth";
                }
              }
            }
            leaf divide-equal {
              type empty;
              description
                "Divide-equal";
            }
          }
          container auto-link-bandwidth {
            presence "enable auto-link-bandwidth";
            description
              "Auto sense and attach link bandwidth community";
            uses apply-advanced;
            choice transitive-type {
              case case_1 {
                leaf transitive {
                  type empty;
                  description
                    "Transitive flag for link bandwidth";
                }
              }
              case case_2 {
                leaf non-transitive {
                  type empty;
                  description
                    "Non-Transitive flag for link bandwidth";
                }
              }
            }
          }
          leaf limit-bandwidth {
            type union {
              type uint64;
              type string {
                pattern "<.*>|$.*";
              }
            }
            description
              "Limit advertised aggregate outbound link bandwidth";
          }
          leaf no-entropy-label-capability {
            type empty;
            description
              "Don't advertise entropy label capability";
          }
          leaf as-path-prepend {
            type string;
            description
              "Prepend AS numbers to an AS path (BGP only)";
          }
          container as-path-expand {
            description
              "Prepend AS numbers prior to adding local-as (BGP only)";
            choice aspath_exp_value {
              case case_1 {
                container last-as {
                  presence "enable last-as";
                  description
                    "Prepend last AS";
                  leaf count {
                    type union {
                      type string {
                        pattern "<.*>|$.*";
                      }
                      type uint32 {
                        range "1 .. 32";
                      }
                    }
                    description
                      "Repeat count";
                  }
                }
              }
              case case_2 {
                leaf aspath {
                  type string;
                  description
                    "AS path string";
                }
              }
            }
          }
          container next-hop {
            description
              "Set the address of the next-hop router";
            choice nexthop_value {
              case case_1 {
                leaf self {
                  type empty;
                  description
                    "Use a local address as the next-hop address";
                }
              }
              case case_2 {
                leaf peer-address {
                  type empty;
                  description
                    "Use the remote peer address as the next-hop address";
                }
              }
              case case_3 {
                leaf address {
                  type jt:ipaddr;
                  description
                    "Next-hop address";
                }
              }
              case case_4 {
                leaf reject {
                  type empty;
                  description
                    "Use a reject next hop";
                }
              }
              case case_5 {
                leaf discard {
                  type empty;
                  description
                    "Use a discard next hop";
                }
              }
              case case_6 {
                leaf next-table {
                  type string;
                  description
                    "Perform a forwarding lookup in the specified table";
                }
              }
            }
          }
          container install-nexthop {
            description
              "Choose the next hop to be used for forwarding";
            choice strict_type {
              case case_1 {
                leaf strict {
                  type empty;
                  description
                    "Do not use any other available next hops";
                }
              }
              case case_2 {
                leaf strict-named-lsp {
                  type empty;
                  description
                    "Do not use any other non-lsp next hops";
                }
              }
            }
            choice nexthop-value {
              case case_1 {
                leaf-list lsp {
                  type string;
                  ordered-by user;
                  description
                    "Next-hop LSP name";
                }
              }
              case case_2 {
                leaf-list lsp-regex {
                  type string;
                  ordered-by user;
                  description
                    "Next-hop LSP name regular expression";
                }
              }
              case case_3 {
                leaf-list static-lsp {
                  type string;
                  ordered-by user;
                  description
                    "Next-hop static LSP name";
                }
              }
              case case_4 {
                leaf-list static-lsp-regex {
                  type string;
                  ordered-by user;
                  description
                    "Next-hop static LSP name regular expression";
                }
              }
              case case_5 {
                leaf non-lsp-nexthop {
                  type empty;
                  description
                    "Next-hop with non-lsp";
                }
              }
              case case_6 {
                leaf non-labelled-nexthop {
                  type empty;
                  description
                    "Next-hop without tag";
                }
              }
              case case_7 {
                leaf overlay-vxlan-interfaces {
                  type empty;
                  description
                    "Next-hop for vxlan interfaces";
                }
              }
            }
            container except {
              description
                "Do not choose to install matching next hops";
              uses apply-advanced;
              choice nexthop-value {
                case case_1 {
                  leaf-list lsp {
                    type string;
                    ordered-by user;
                    description
                      "Next-hop LSP name";
                  }
                }
                case case_2 {
                  leaf-list lsp-regex {
                    type string;
                    ordered-by user;
                    description
                      "Next-hop LSP name regular expression";
                  }
                }
                case case_3 {
                  leaf-list static-lsp {
                    type string;
                    ordered-by user;
                    description
                      "Next-hop static LSP name";
                  }
                }
                case case_4 {
                  leaf-list static-lsp-regex {
                    type string;
                    ordered-by user;
                    description
                      "Next-hop static LSP name regular expression";
                  }
                }
                case case_5 {
                  leaf non-lsp-nexthop {
                    type empty;
                    description
                      "Next-hop with non-lsp";
                  }
                }
                case case_6 {
                  leaf non-labelled-nexthop {
                    type empty;
                    description
                      "Next-hop without tag";
                  }
                }
                case case_7 {
                  leaf overlay-vxlan-interfaces {
                    type empty;
                    description
                      "Next-hop for vxlan interfaces";
                  }
                }
              }
              container fallback {
                description
                  "Backup option";
                uses apply-advanced;
                choice nexthop-value {
                  case case_1 {
                    leaf-list lsp {
                      type string;
                      ordered-by user;
                      description
                        "Next-hop LSP name";
                    }
                  }
                  case case_2 {
                    leaf-list lsp-regex {
                      type string;
                      ordered-by user;
                      description
                        "Next-hop LSP name regular expression";
                    }
                  }
                  case case_3 {
                    leaf-list static-lsp {
                      type string;
                      ordered-by user;
                      description
                        "Next-hop static LSP name";
                    }
                  }
                  case case_4 {
                    leaf-list static-lsp-regex {
                      type string;
                      ordered-by user;
                      description
                        "Next-hop static LSP name regular expression";
                    }
                  }
                  case case_5 {
                    leaf non-lsp-nexthop {
                      type empty;
                      description
                        "Next-hop with non-lsp";
                    }
                  }
                  case case_6 {
                    leaf non-labelled-nexthop {
                      type empty;
                      description
                        "Next-hop without tag";
                    }
                  }
                  case case_7 {
                    leaf overlay-vxlan-interfaces {
                      type empty;
                      description
                        "Next-hop for vxlan interfaces";
                    }
                  }
                }
                container except {
                  description
                    "Do not choose to install matching next hops";
                  uses apply-advanced;
                  choice nexthop-value {
                    case case_1 {
                      leaf-list lsp {
                        type string;
                        ordered-by user;
                        description
                          "Next-hop LSP name";
                      }
                    }
                    case case_2 {
                      leaf-list lsp-regex {
                        type string;
                        ordered-by user;
                        description
                          "Next-hop LSP name regular expression";
                      }
                    }
                    case case_3 {
                      leaf-list static-lsp {
                        type string;
                        ordered-by user;
                        description
                          "Next-hop static LSP name";
                      }
                    }
                    case case_4 {
                      leaf-list static-lsp-regex {
                        type string;
                        ordered-by user;
                        description
                          "Next-hop static LSP name regular expression";
                      }
                    }
                    case case_5 {
                      leaf non-lsp-nexthop {
                        type empty;
                        description
                          "Next-hop with non-lsp";
                      }
                    }
                    case case_6 {
                      leaf non-labelled-nexthop {
                        type empty;
                        description
                          "Next-hop without tag";
                      }
                    }
                    case case_7 {
                      leaf overlay-vxlan-interfaces {
                        type empty;
                        description
                          "Next-hop for vxlan interfaces";
                      }
                    }
                  }
                }
              }
            }
            container fallback {
              description
                "Backup option ";
              uses apply-advanced;
              choice nexthop-value {
                case case_1 {
                  leaf-list lsp {
                    type string;
                    ordered-by user;
                    description
                      "Next-hop LSP name";
                  }
                }
                case case_2 {
                  leaf-list lsp-regex {
                    type string;
                    ordered-by user;
                    description
                      "Next-hop LSP name regular expression";
                  }
                }
                case case_3 {
                  leaf-list static-lsp {
                    type string;
                    ordered-by user;
                    description
                      "Next-hop static LSP name";
                  }
                }
                case case_4 {
                  leaf-list static-lsp-regex {
                    type string;
                    ordered-by user;
                    description
                      "Next-hop static LSP name regular expression";
                  }
                }
                case case_5 {
                  leaf non-lsp-nexthop {
                    type empty;
                    description
                      "Next-hop with non-lsp";
                  }
                }
                case case_6 {
                  leaf non-labelled-nexthop {
                    type empty;
                    description
                      "Next-hop without tag";
                  }
                }
                case case_7 {
                  leaf overlay-vxlan-interfaces {
                    type empty;
                    description
                      "Next-hop for vxlan interfaces";
                  }
                }
              }
              container except {
                description
                  "Do not choose to install matching next hops";
                uses apply-advanced;
                choice nexthop-value {
                  case case_1 {
                    leaf-list lsp {
                      type string;
                      ordered-by user;
                      description
                        "Next-hop LSP name";
                    }
                  }
                  case case_2 {
                    leaf-list lsp-regex {
                      type string;
                      ordered-by user;
                      description
                        "Next-hop LSP name regular expression";
                    }
                  }
                  case case_3 {
                    leaf-list static-lsp {
                      type string;
                      ordered-by user;
                      description
                        "Next-hop static LSP name";
                    }
                  }
                  case case_4 {
                    leaf-list static-lsp-regex {
                      type string;
                      ordered-by user;
                      description
                        "Next-hop static LSP name regular expression";
                    }
                  }
                  case case_5 {
                    leaf non-lsp-nexthop {
                      type empty;
                      description
                        "Next-hop with non-lsp";
                    }
                  }
                  case case_6 {
                    leaf non-labelled-nexthop {
                      type empty;
                      description
                        "Next-hop without tag";
                    }
                  }
                  case case_7 {
                    leaf overlay-vxlan-interfaces {
                      type empty;
                      description
                        "Next-hop for vxlan interfaces";
                    }
                  }
                }
              }
            }
          }
          leaf trace {
            type empty;
            description
              "Log matches to a trace file";
          }
          container external {
            presence "enable external";
            description
              "External route";
            uses apply-advanced;
            leaf type {
              type union {
                type string {
                  pattern "<.*>|$.*";
                }
                type int32 {
                  range "1 .. 2";
                }
              }
              description
                "OSPF external metric type";
            }
            leaf nssa-only {
              type empty;
              description
                "Clear P-bit on lsa type 7";
            }
          }
          container load-balance {
            description
              "Type of load balancing in forwarding table";
            choice load_balance_type {
              case case_1 {
                leaf per-packet {
                  type empty;
                  description
                    "Load balance on a per-packet basis deprecated, use per-flow instead";
                }
              }
              case case_2 {
                leaf per-flow {
                  type empty;
                  description
                    "Load balance on a per-flow basis";
                }
              }
              case case_3;
              case case_4;
              case case_5;
              case case_6;
              case case_7;
              case case_8;
              case case_9;
              case case_10;
              case case_11;
            }
          }
          container advertise-locator {
            presence "enable advertise-locator";
            description
              "Advertise SRv6 Locator";
            uses apply-advanced;
            leaf internal {
              type empty;
              description
                "Advertise locator as Interal route";
            }
          }
          leaf set-down-bit {
            type empty;
            description
              "Set down bit";
          }
          leaf analyze {
            type empty;
            description
              "Send to registered controllers for analysis";
          }
          leaf destination-class {
            type string;
            description
              "Set destination class in forwarding table";
          }
          leaf source-class {
            type string;
            description
              "Set source class in forwarding table";
          }
          leaf forwarding-class {
            type string;
            description
              "Set source or destination class in forwarding table";
          }
          container map-to-interface {
            description
              "Set output logical interface";
            choice map_to_interface_value {
              case case_1 {
                leaf self {
                  type empty;
                  description
                    "Map the interface to itself";
                }
              }
              case case_2 {
                leaf interface {
                  type union {
                    type jt:interface-name;
                    type string {
                      pattern "<.*>|$.*";
                    }
                  }
                  description
                    "Output logical interface";
                }
              }
            }
          }
          leaf-list ssm-source {
            type jt:ipaddr;
            ordered-by user;
            description
              "List of Sources for SSM mapping";
          }
          container p2mp-lsp-root {
            description
              "P2mp lsp root address";
            uses apply-advanced;
            leaf address {
              type jt:ipv4addr;
              description
                "Ipv4 root address";
            }
          }
          leaf dynamic-tunnel-attributes {
            type string;
            description
              "Choose the dynamic tunnel attributes used for forwarding";
          }
          leaf tunnel-end-point-address {
            type jt:ipaddr;
            description
              "Set tunnel end-point address of tunnel";
          }
          leaf selected-mldp-egress {
            type empty;
            description
              "This node should act as egress node for MLDP inband signalling";
          }
          leaf mhop-bfd-port {
            type empty;
            description
              "Use port number 4784 for MPLS-BFD as per RFC5884";
          }
          leaf no-backup {
            type empty;
            description
              "This prefix should not have backup";
          }
          leaf default-action {
            type enumeration {
              enum "accept" {
                description
                  "Accept a route";
              }
              enum "reject" {
                description
                  "Reject a route";
              }
            }
            description
              "Set default policy action";
          }
          leaf next {
            type enumeration {
              enum "policy" {
                description
                  "Skip to next policy filter";
              }
              enum "term" {
                description
                  "Skip to next term in a policy filter";
              }
            }
            description
              "Skip to next policy or term";
          }
          choice accept_reject {
            case case_1 {
              leaf accept {
                type empty;
                description
                  "Accept a route";
              }
            }
            case case_2 {
              leaf reject {
                type empty;
                description
                  "Reject a route";
              }
            }
          }
          container bgp-output-queue-priority {
            description
              "Set the BGP Update output queue priority.";
            choice class {
              case case_1 {
                leaf priority {
                  type union {
                    type string {
                      pattern "<.*>|$.*";
                    }
                    type uint32 {
                      range "1 .. 16";
                    }
                  }
                  description
                    "Output queue priority; higher is better";
                }
              }
              case case_2 {
                leaf expedited {
                  type empty;
                  description
                    "Expedited queue; highest priority";
                }
              }
            }
          }
          leaf multipath-resolve {
            type empty;
            description
              "Use all paths for resolution over this prefix";
          }
          leaf source-routing-path-template {
            type string;
            description
              "Spring-te template to apply";
          }
          leaf label-allocation-fallback-reject {
            type empty;
            description
              "Suppress prefix export when label allocation fails";
          }
          leaf resolution-map {
            type string;
            description
              "Set resolution map modes";
          }
          leaf ignore-service-label {
            type empty;
            description
              "Ignore service labels";
          }
          container prefix-attribute-flags {
            presence "enable prefix-attribute-flags";
            description
              "Set ISIS prefix attribute flags sub TLV";
            uses apply-advanced;
            leaf node-segment-flag {
              type empty;
              description
                "Set node segment flag ";
            }
            leaf external-prefix-flag {
              type empty;
              description
                "Set external prefix flag ";
            }
            leaf anycast-flag {
              type empty;
              description
                "Set anycast flag ";
            }
            leaf entropy-label-capability-flag {
              type empty;
              description
                "Set entropy label capability flag ";
            }
          }
          container ipv4-source-router-id {
            presence "enable ipv4-source-router-id";
            description
              "Set IPv4 source router id in advertisement";
            uses apply-advanced;
            leaf router-id {
              type jt:ipaddr;
              description
                "Specify IPv4 address";
            }
          }
          container ipv6-source-router-id {
            presence "enable ipv6-source-router-id";
            description
              "Set IPv6 source router id in advertisement";
            uses apply-advanced;
            leaf router-id {
              type jt:ipv6addr;
              description
                "Specify IPv6 address";
            }
          }
          leaf request-long-lived-ack {
            type empty;
            description
              "Advertise route after forwarding is programmed";
          }
          leaf send-withdrawal-on-route-change {
            type empty;
            description
              "Withdraw route if change is not acked from forwarding";
          }
          container slice {
            description
              "Configure Policy Slice action";
            leaf slice-name {
              type string {
                length "1 .. 64";
              }
              description
                "Slice Name";
            }
          }
          leaf filter {
            type string;
            description
              "Set firewall-filter name";
          }
          leaf strip-as-path {
            type empty;
            description
              "Remove the incoming BGP as-path and replace with local AS";
          }
          container request-acknowledgements {
            description
              "Set request acknowledgement";
            leaf nexthop-ack {
              type empty;
              description
                "Set nexthop acknowledgement ";
            }
            leaf route-ack {
              type empty;
              description
                "Set route acknowledgement ";
            }
          }
        }
      }
      container from {
        description
          "Conditions to match the source of a route";
        uses apply-advanced;
        leaf instance {
          type string;
          description
            "Routing protocol instance";
        }
        leaf instance-any {
          type empty;
          description
            "Any routing protocol instance";
        }
        leaf-list instance-list {
          type string;
          description
            "A list of routing protocol instances";
        }
        leaf-list igp-instance {
          type string;
          description
            "IGP instance";
        }
        leaf igp-instance-regex {
          type jt:regular-expression;
          description
            "IGP instance name regular expression";
        }
        leaf family {
          type enumeration {
            enum "inet" {
              description
                "IPv4 family";
            }
            enum "inet-vpn" {
              description
                "IPv4-VPN family";
            }
            enum "inet6" {
              description
                "IPv6 family";
            }
            enum "inet6-vpn" {
              description
                "IPv6-VPN family";
            }
            enum "iso-vpn" {
              description
                "ISO-VPN family";
            }
            enum "iso" {
              description
                "ISO family";
            }
            enum "evpn" {
              description
                "EVPN family";
            }
            enum "inet-mvpn" {
              description
                "IPv4 Multicast VPN family";
            }
            enum "inet6-mvpn" {
              description
                "IPv6 Multicast VPN family";
            }
            enum "inet-mdt" {
              description
                "IPv4 MDT Signaling family";
            }
            enum "route-target" {
              description
                "Local route target VPN family";
            }
            enum "traffic-engineering" {
              description
                "Traffic Engineering family";
            }
            enum "inet-srte" {
              description
                "IPv4 srtte family";
            }
            enum "inet6-srte" {
              description
                "IPv6 srte family";
            }
          }
        }
        leaf-list protocol {
          type enumeration {
            enum "aggregate" {
              description
                "Aggregate routes";
            }
            enum "bgp" {
              description
                "BGP";
            }
            enum "direct" {
              description
                "Directly connected routes";
            }
            enum "dvmrp" {
              description
                "Distance Vector Multicast Routing Protocol";
            }
            enum "isis" {
              description
                "Intermediate System-to-Intermediate System";
            }
            enum "esis" {
              description
                "End System-to-Intermediate System";
            }
            enum "l-isis" {
              description
                "Labelled ISIS";
            }
            enum "l2circuit" {
              description
                "Layer 2 circuits";
            }
            enum "l2vpn" {
              description
                "Layer 2 MPLS virtual private networks";
            }
            enum "local" {
              description
                "Local system addresses";
            }
            enum "ospf" {
              description
                "Open Shortest Path First";
            }
            enum "ospf2" {
              description
                "Open Shortest Path First Version 2";
            }
            enum "ospf3" {
              description
                "Open Shortest Path First Version 3";
            }
            enum "l-ospf" {
              description
                "Labelled OSPF";
            }
            enum "pim" {
              description
                "Protocol Independent Multicast";
            }
            enum "rip" {
              description
                "Routing Information Protocol";
            }
            enum "ripng" {
              description
                "Routing Information Protocol next generation";
            }
            enum "static" {
              description
                "Statically defined addresses";
            }
            enum "arp" {
              description
                "Addresses learned from ARP";
            }
            enum "frr" {
              description
                "Addresses created by Host Fast Re-route";
            }
            enum "mpls" {
              description
                "Multiprotocol Label Switching";
            }
            enum "ldp" {
              description
                "Label Distribution Protocol";
            }
            enum "rsvp" {
              description
                "Resource Reservation Protocol";
            }
            enum "msdp" {
              description
                "Multicast Source Discovery Protocol";
            }
            enum "route-target" {
              description
                "Local route target VPN membership";
            }
            enum "access" {
              description
                "Access server routes";
            }
            enum "access-internal" {
              description
                "Internal routes to directly connected clients";
            }
            enum "anchor" {
              description
                "Anchor routes connected to UEs";
            }
            enum "bgp-static" {
              description
                "BGP static routes";
            }
            enum "vpls" {
              description
                "Virtual Private LAN Service";
            }
            enum "evpn" {
              description
                "Ethernet VPN Service";
            }
            enum "spring-te" {
              description
                "SPRING Traffic-Engineered";
            }
            enum "bgp-ls-epe" {
              description
                "Addresses created by BGP-LS egress TE";
            }
            enum "express-segments" {
              description
                "Express-segment routes";
            }
            enum "rift" {
              description
                "RIFT routes";
            }
            enum "l2-learned-host-routing" {
              description
                "Layer2-learned host routes";
            }
            enum "srv6-isis" {
              description
                "SRV6 ISIS";
            }
            enum "ari-ts" {
              description
                "ARI TS routes";
            }
            enum "srv6" {
              description
                "Segment Routing IPv6 local route";
            }
          }
          ordered-by user;
          description
            "Protocol from which route was learned";
        }
        leaf rib {
          type string;
          description
            "Routing table";
        }
        leaf-list neighbor {
          type jt:ipaddr;
          ordered-by user;
          description
            "Neighboring router";
        }
        leaf-list next-hop {
          type jt:ipaddr;
          ordered-by user;
          description
            "Next-hop router";
        }
        leaf-list interface {
          type union {
            type jt:ipaddr-or-interface;
            type string {
              pattern "<.*>|$.*";
            }
          }
          ordered-by user;
          description
            "Interface name or address";
        }
        leaf area {
          type jt:areaid;
          description
            "OSPF area identifier";
        }
        leaf-list as-path {
          type string;
          ordered-by user;
          description
            "Name of AS path regular expression (BGP only)";
        }
        leaf-list as-path-group {
          type string;
          ordered-by user;
          description
            "Name of AS path group (BGP only)";
        }
        leaf origin {
          type enumeration {
            enum "igp" {
              description
                "Path originated in the local IGP";
            }
            enum "egp" {
              description
                "Path originated in another AS";
            }
            enum "incomplete" {
              description
                "Path was learned by some other means";
            }
          }
          description
            "BGP origin attribute";
        }
        leaf-list community {
          type string;
          ordered-by user;
          description
            "BGP community";
        }
        leaf level {
          type union {
            type uint32;
            type string {
              pattern "<.*>|$.*";
            }
          }
          description
            "IS-IS level";
        }
        container external {
          presence "enable external";
          description
            "External route";
          uses apply-advanced;
          leaf type {
            type union {
              type string {
                pattern "<.*>|$.*";
              }
              type int32 {
                range "1 .. 2";
              }
            }
            description
              "OSPF external metric type";
          }
        }
        leaf bgp-srte-discriminator {
          type union {
            type uint32;
            type string {
              pattern "<.*>|$.*";
            }
          }
          description
            "Srte discriminator";
        }
        leaf srte-color {
          type union {
            type uint32;
            type string {
              pattern "<.*>|$.*";
            }
          }
          description
            "Srte color";
        }
        leaf programmed {
          type empty;
          description
            "API-programmed route";
        }
        leaf validation-database {
          type enumeration {
            enum "valid" {
              description
                "Match for valid database validation-state";
            }
            enum "invalid" {
              description
                "Match for invalid database validation-state";
            }
            enum "unknown" {
              description
                "Match for unknown database validation-state";
            }
          }
          description
            "Name to identify a validation-state";
        }
        container validation-database-instance {
          presence "enable validation-database-instance";
          description
            "Name to identify a validation-state with DB name";
          uses apply-advanced;
          leaf database-name {
            type string;
            description
              "Route Validation Database name to be looked at";
          }
          leaf state {
            type enumeration {
              enum "valid" {
                description
                  "Match for valid database validation-state";
              }
              enum "invalid" {
                description
                  "Match for invalid database validation-state";
              }
              enum "unknown" {
                description
                  "Match for unknown database validation-state";
              }
            }
            mandatory true;
            description
              "Name to identify a validation-state";
          }
        }
        list nexthop-weight {
          key "choice-ident choice-value weight";
          ordered-by user;
          description
            "Weight of the gateway";
          leaf choice-ident {
            type enumeration {
              enum "equal";
              enum "greater-than";
              enum "less-than";
              enum "greater-than-equal";
              enum "less-than-equal";
            }
          }
          leaf choice-value {
            type string;
          }
          leaf weight {
            type union {
              type string {
                pattern "<.*>|$.*";
              }
              type uint32 {
                range "1 .. 65535";
              }
            }
            description
              "Weight of the gateway";
          }
          uses apply-advanced;
          choice weight_type {
            case case_1 {
              leaf all-nexthop {
                type empty;
                description
                  "All the gateway weight should be matched";
              }
            }
          }
        }
        list nexthop-ecmp {
          key "choice-ident choice-value ecmp";
          ordered-by user;
          description
            "Qualify nexthop equal cost multipath gateways";
          leaf choice-ident {
            type enumeration {
              enum "equal";
              enum "greater-than";
              enum "less-than";
              enum "greater-than-equal";
              enum "less-than-equal";
            }
          }
          leaf choice-value {
            type string;
          }
          leaf ecmp {
            type union {
              type string {
                pattern "<.*>|$.*";
              }
              type uint32 {
                range "1 .. 512";
              }
            }
            description
              "Number of equal cost multipath gateways";
          }
          uses apply-advanced;
        }
        leaf metric {
          type union {
            type uint32;
            type string {
              pattern "<.*>|$.*";
            }
          }
          description
            "Metric value";
        }
        leaf metric2 {
          type union {
            type uint32;
            type string {
              pattern "<.*>|$.*";
            }
          }
          description
            "Metric value 2";
        }
        leaf metric3 {
          type union {
            type uint32;
            type string {
              pattern "<.*>|$.*";
            }
          }
          description
            "Metric value 3";
        }
        leaf metric4 {
          type union {
            type uint32;
            type string {
              pattern "<.*>|$.*";
            }
          }
          description
            "Metric value 4";
        }
        leaf-list tag {
          type union {
            type uint32;
            type string {
              pattern "<.*>|$.*";
            }
          }
          ordered-by user;
          description
            "Tag string";
        }
        leaf-list tag2 {
          type union {
            type uint32;
            type string {
              pattern "<.*>|$.*";
            }
          }
          ordered-by user;
          description
            "Tag string 2";
        }
        leaf preference {
          type union {
            type uint32;
            type string {
              pattern "<.*>|$.*";
            }
          }
          description
            "Preference value";
        }
        leaf preference2 {
          type union {
            type uint32;
            type string {
              pattern "<.*>|$.*";
            }
          }
          description
            "Preference value 2";
        }
        leaf color {
          type union {
            type uint32;
            type string {
              pattern "<.*>|$.*";
            }
          }
          description
            "Color (preference) value";
        }
        leaf color2 {
          type union {
            type uint32;
            type string {
              pattern "<.*>|$.*";
            }
          }
          description
            "Color (preference) value 2";
        }
        leaf local-preference {
          type union {
            type uint32;
            type string {
              pattern "<.*>|$.*";
            }
          }
          description
            "Local preference associated with a route";
        }
        leaf-list policy {
          type jt:policy-algebra;
          ordered-by user;
          description
            "Name of policy to evaluate";
        }
        choice lsp-name-type {
          case case_1 {
            leaf lsp {
              type string;
              description
                "Label switched path name";
            }
          }
          case case_2 {
            leaf lsp-regex {
              type string;
              description
                "Label switched path name regular expression";
            }
          }
        }
        container source-routing-path {
          presence "enable source-routing-path";
          description
            "Spring-te lsp policy attributes";
          leaf name-regex {
            type string;
            description
              "Spring-te lsp name regex";
          }
          leaf dest {
            type jt:ipaddr;
            description
              "Spring-te lsp IPV4/IPV6 destination without color";
          }
          leaf origin {
            type jt:ipaddr;
            description
              "Spring-te lsp origin address";
          }
          leaf tunnel-source {
            type enumeration {
              enum "pcep" {
                description
                  "Spring-te lsp src pcep";
              }
              enum "bgp" {
                description
                  "Spring-te lsp src bgp";
              }
            }
            description
              "Spring-te lsp source protocol";
          }
          leaf route-distinguisher {
            type union {
              type uint32;
              type string {
                pattern "<.*>|$.*";
              }
            }
            description
              "Spring-te lsp route distinguisher";
          }
          leaf color {
            type union {
              type uint32;
              type string {
                pattern "<.*>|$.*";
              }
            }
            description
              "Spring-te lsp color";
          }
        }
        list route-filter {
          key "address choice-ident choice-value";
          ordered-by user;
          description
            "List of routes to match";
          uses control_route_filter_type;
        }
        list source-address-filter {
          key "address choice-ident choice-value";
          ordered-by user;
          description
            "List of source addresses to match";
          uses control_source_address_filter_type;
        }
        list prefix-list {
          key "name";
          ordered-by user;
          description
            "List of prefix-lists of routes to match";
          uses control_prefix_list_type;
        }
        list rib-list {
          key "name";
          ordered-by user;
          description
            "List of routing-tables";
          uses control_rib_list_type;
        }
        list as-path-neighbors {
          key "list-type list-name";
          ordered-by user;
          description
            "List of peer AS to match";
          uses control_as_list_type;
        }
        list as-path-origins {
          key "list-type list-name";
          ordered-by user;
          description
            "List of originating AS to match";
          uses control_as_list_type;
        }
        list as-path-transits {
          key "list-type list-name";
          ordered-by user;
          description
            "List of originating AS to match";
          uses control_as_list_type;
        }
        list prefix-list-filter {
          key "list_name choice-ident choice-value";
          ordered-by user;
          description
            "List of prefix-list-filters to match";
          uses control_prefix_list_filter_type;
        }
        list rtf-prefix-list {
          key "name";
          ordered-by user;
          description
            "List of rtf-prefix-lists of routes to match";
          uses control_rtf_prefix_list_type;
        }
        list route-filter-list {
          key "name";
          ordered-by user;
          description
            "List of route-filter-lists of routes to match";
          uses control_route_filter_list_type;
        }
        list source-address-filter-list {
          key "name";
          ordered-by user;
          description
            "List of source-address-filter-lists of routes to match";
          uses control_source_address_filter_list_type;
        }
        container multicast-scope {
          description
            "Multicast scope to match";
          choice scope-choice {
            case case_1 {
              leaf node-local {
                type empty;
                description
                  "Node-local scope";
              }
            }
            case case_2 {
              leaf link-local {
                type empty;
                description
                  "Link-local scope";
              }
            }
            case case_3 {
              leaf site-local {
                type empty;
                description
                  "Site-local scope";
              }
            }
            case case_4 {
              leaf organization-local {
                type empty;
                description
                  "Organization-local scope";
              }
            }
            case case_5 {
              leaf global {
                type empty;
                description
                  "Global scope";
              }
            }
            case case_6 {
              leaf scope_value {
                type union {
                  type string {
                    pattern "<.*>|$.*";
                  }
                  type uint32 {
                    range "0 .. 15";
                  }
                }
                description
                  "Scope value";
              }
            }
          }
          choice scope-operator {
            case case_1 {
              leaf orhigher {
                type empty;
                description
                  "Match higher values";
              }
            }
            case case_2 {
              leaf orlower {
                type empty;
                description
                  "Match lower values";
              }
            }
          }
        }
        leaf aggregate-contributor {
          type empty;
          description
            "Match more specifics of an aggregate";
        }
        leaf state {
          type enumeration {
            enum "active" {
              description
                "Active route";
            }
            enum "inactive" {
              description
                "Inactive route";
            }
          }
          description
            "Route state";
        }
        leaf-list tunnel-type {
          type enumeration {
            enum "gre" {
              description
                "GRE tunnel";
            }
            enum "udp" {
              description
                "UDP tunnel";
            }
            enum "ipip" {
              description
                "IPIP tunnel";
            }
          }
          ordered-by user;
          description
            "Tunnel type";
        }
        leaf route-type {
          type enumeration {
            enum "internal" {
              description
                "Internal route";
            }
            enum "external" {
              description
                "External route";
            }
          }
          description
            "Route type";
        }
        leaf-list nlri-route-type {
          type union {
            type string {
              pattern "<.*>|$.*";
            }
            type uint32 {
              range "1 .. 10";
            }
          }
          ordered-by user;
          description
            "Route type from NLRI";
        }
        leaf-list evpn-tag {
          type union {
            type string {
              pattern "<.*>|$.*";
            }
            type uint32 {
              range "0 .. 4294967295";
            }
          }
          ordered-by user;
          description
            "Tag in EVPN Route";
        }
        leaf-list evpn-esi {
          type string;
          ordered-by user;
          description
            "ESI in EVPN Route";
        }
        list mac-filter-list {
          key "name";
          ordered-by user;
          description
            "List of mac-filter-list macs to match";
          uses control_mac_address_filter_list_type;
        }
        leaf evpn-mac-route {
          type enumeration {
            enum "mac-only" {
              description
                "MAC route";
            }
            enum "mac-ipv4" {
              description
                "MAC IPV4 route";
            }
            enum "mac-ipv6" {
              description
                "MAC IPV6 route";
            }
          }
          description
            "EVPN Mac Route type";
        }
        leaf-list bridge-domain-id {
          type union {
            type string {
              pattern "<.*>|$.*";
            }
            type uint32 {
              range "0 .. 4294967295";
            }
          }
          ordered-by user;
          description
            "Bridge Domain Identifier (Vlan or VNI)";
        }
        leaf next-hop-type {
          type enumeration {
            enum "merged" {
              description
                "Merged next hop";
            }
          }
          description
            "Next-hop type";
        }
        leaf-list condition {
          type string;
          ordered-by user;
          description
            "Condition to match on";
        }
        list community-count {
          key "name";
          ordered-by user;
          description
            "Number of BGP communities";
          uses community_count_type;
        }
        list large-community-count {
          key "name";
          ordered-by user;
          description
            "Number of Large BGP communities";
          uses community_count_type;
        }
        list as-path-unique-count {
          key "name";
          ordered-by user;
          description
            "Number of unique BGP ASes excluding confederations";
          uses as-path-unique-count-type;
        }
        list as-path-calc-length {
          key "name";
          ordered-by user;
          description
            "Number of BGP ASes excluding confederations";
          uses as-path-calc-length-type;
        }
        container traffic-engineering {
          presence "enable traffic-engineering";
          description
            "Traffic-Engineering related parameters";
          uses apply-advanced;
          leaf-list protocol {
            type enumeration {
              enum "direct" {
                description
                  "Directly originated";
              }
              enum "ospf" {
                description
                  "OSPF originated";
              }
              enum "isis-level-1" {
                description
                  "ISIS level-1 originated";
              }
              enum "isis-level-2" {
                description
                  "ISIS level-2 originated";
              }
              enum "spring-te" {
                description
                  "SPRING-TE originated";
              }
              enum "static" {
                description
                  "Statically originated";
              }
              enum "unknown" {
                description
                  "Originated by unknown sources";
              }
            }
            ordered-by user;
            description
              "Protocol that originated the entry";
          }
          container node {
            presence "enable node";
            description
              "Node-related parameters";
            uses apply-advanced;
            leaf as {
              type string;
              description
                "AS number";
            }
            leaf node-type {
              type enumeration {
                enum "router" {
                  description
                    "Real node";
                }
                enum "pseudo-node" {
                  description
                    "Pseudo-node";
                }
              }
              description
                "Real or pseudo-node";
            }
            leaf router-id {
              type jt:ipprefix;
              description
                "IP prefix to match the router-id against";
            }
            leaf sys-id {
              type jt:sysid;
              description
                "ISO address of the node";
            }
          }
          container ipv4-prefix {
            presence "enable ipv4-prefix";
            description
              "IPV4 prefix-related parameters";
            uses apply-advanced;
            leaf as {
              type string;
              description
                "AS number";
            }
            leaf router-id {
              type jt:ipprefix;
              description
                "IP prefix to match the router-id against";
            }
            leaf prefix {
              type jt:ipprefix;
              description
                "IP prefix to match against";
            }
            leaf sys-id {
              type jt:sysid;
              description
                "ISO address of the node";
            }
          }
          container ipv6-prefix {
            presence "enable ipv6-prefix";
            description
              "IPV6 prefix related parameters";
            uses apply-advanced;
            leaf as {
              type string;
              description
                "AS number";
            }
            leaf router-id {
              type jt:ipprefix;
              description
                "IPv6 prefix to match the router-id against";
            }
            leaf prefix {
              type jt:ipv6prefix;
              description
                "IPv6 prefix to match against";
            }
            leaf sys-id {
              type jt:sysid;
              description
                "ISO address of the node";
            }
          }
          container srv6-sid {
            presence "enable srv6-sid";
            description
              "SRV6 SID related parameters";
            uses apply-advanced;
            leaf as {
              type string;
              description
                "AS number";
            }
            leaf router-id {
              type jt:ipprefix;
              description
                "SRv6 SID to match the router-id against";
            }
            leaf sid {
              type jt:ipv6addr;
              description
                "SRv6 SID to match against";
            }
            leaf sys-id {
              type jt:sysid;
              description
                "ISO address of the node";
            }
          }
          container spring-te {
            presence "enable spring-te";
            description
              "SPRING-TE policy related parameters";
            uses apply-advanced;
            leaf node-as {
              type string;
              description
                "Node AS number";
            }
            leaf router-id {
              type jt:ipprefix;
              description
                "IP prefix to match against the node for the SPRING TE policy";
            }
            leaf color {
              type union {
                type uint32;
                type string {
                  pattern "<.*>|$.*";
                }
              }
              description
                "Color of the SPRING-TE policy candidate path";
            }
            leaf discriminator {
              type union {
                type uint32;
                type string {
                  pattern "<.*>|$.*";
                }
              }
              description
                "Discriminator of the SPRING-TE policy candidate path";
            }
            leaf endpoint {
              type jt:ipaddr;
              description
                "Endpoint of the SPRING-TE policy candidate path";
            }
            leaf protocol-origin {
              type enumeration {
                enum "bgp" {
                  description
                    "SPRING-TE policy candidate path originated by BGP";
                }
                enum "cli" {
                  description
                    "SPRING-TE policy candidate path originated by cli";
                }
                enum "pcep" {
                  description
                    "SPRING-TE policy candidate path originated by PCEP";
                }
              }
              description
                "Protocol originating the SPRING-TE policy candidate path";
            }
            leaf origin-as {
              type string;
              description
                "AS number of the node creating the SPRING-TE policy candidate path";
            }
            leaf origin-addr {
              type jt:ipaddr;
              description
                "Address of the node originating the SPRING-TE policy candidate path";
            }
          }
          container link {
            presence "enable link";
            description
              "Link-related parameters";
            uses apply-advanced;
            container from {
              description
                "Specify parameter of the 'from' side";
              uses apply-advanced;
              leaf as {
                type string;
                description
                  "AS number";
              }
              leaf router-id {
                type jt:ipprefix;
                description
                  "IP prefix to match the router-id against";
              }
              leaf sys-id {
                type jt:sysid;
                description
                  "System-ID of the node";
              }
              leaf node-type {
                type enumeration {
                  enum "router" {
                    description
                      "Real node";
                  }
                  enum "pseudo-node" {
                    description
                      "Pseudo-node";
                  }
                }
                description
                  "Type of the node";
              }
              leaf link-address {
                type jt:ipprefix;
                description
                  "IP prefix to match the link address against";
              }
            }
            container to {
              description
                "Specify parameters of the 'to' side";
              uses apply-advanced;
              leaf as {
                type string;
                description
                  "AS number";
              }
              leaf router-id {
                type jt:ipprefix;
                description
                  "IP prefix to match the router-id against";
              }
              leaf sys-id {
                type jt:sysid;
                description
                  "System-ID of the node";
              }
              leaf node-type {
                type enumeration {
                  enum "router" {
                    description
                      "Real node";
                  }
                  enum "pseudo-node" {
                    description
                      "Pseudo-node";
                  }
                }
                description
                  "Type of the node";
              }
              leaf link-address {
                type jt:ipprefix;
                description
                  "IP prefix to match the link address against";
              }
            }
          }
          leaf identifier {
            type union {
              type string {
                pattern "<.*>|$.*";
              }
              type uint64 {
                range "2 .. 18446744073709551615";
              }
            }
            description
              "BGP-TE identifier";
          }
        }
        leaf-list route-distinguisher {
          type string;
          ordered-by user;
          description
            "Name of the route-distinguisher";
        }
        leaf prefix-segment {
          type empty;
          description
            "Prefix segment present in route extended data";
        }
      }
      container to {
        description
          "Conditions to match the destination of a route";
        uses apply-advanced;
        leaf instance {
          type string;
          description
            "Routing protocol instance";
        }
        leaf instance-any {
          type empty;
          description
            "Any routing protocol instance";
        }
        leaf-list instance-list {
          type string;
          description
            "A list of routing protocol instances";
        }
        leaf-list igp-instance {
          type string;
          description
            "IGP instance";
        }
        leaf igp-instance-regex {
          type jt:regular-expression;
          description
            "IGP instance name regular expression";
        }
        leaf family {
          type enumeration {
            enum "inet" {
              description
                "IPv4 family";
            }
            enum "inet-vpn" {
              description
                "IPv4-VPN family";
            }
            enum "inet6" {
              description
                "IPv6 family";
            }
            enum "inet6-vpn" {
              description
                "IPv6-VPN family";
            }
            enum "iso-vpn" {
              description
                "ISO-VPN family";
            }
            enum "iso" {
              description
                "ISO family";
            }
            enum "evpn" {
              description
                "EVPN family";
            }
            enum "inet-mvpn" {
              description
                "IPv4 Multicast VPN family";
            }
            enum "inet6-mvpn" {
              description
                "IPv6 Multicast VPN family";
            }
            enum "inet-mdt" {
              description
                "IPv4 MDT Signaling family";
            }
            enum "route-target" {
              description
                "Local route target VPN family";
            }
            enum "traffic-engineering" {
              description
                "Traffic Engineering family";
            }
            enum "inet-srte" {
              description
                "IPv4 srtte family";
            }
            enum "inet6-srte" {
              description
                "IPv6 srte family";
            }
          }
        }
        leaf-list protocol {
          type enumeration {
            enum "aggregate" {
              description
                "Aggregate routes";
            }
            enum "bgp" {
              description
                "BGP";
            }
            enum "direct" {
              description
                "Directly connected routes";
            }
            enum "dvmrp" {
              description
                "Distance Vector Multicast Routing Protocol";
            }
            enum "isis" {
              description
                "Intermediate System-to-Intermediate System";
            }
            enum "esis" {
              description
                "End System-to-Intermediate System";
            }
            enum "l-isis" {
              description
                "Labelled ISIS";
            }
            enum "l2circuit" {
              description
                "Layer 2 circuits";
            }
            enum "l2vpn" {
              description
                "Layer 2 MPLS virtual private networks";
            }
            enum "local" {
              description
                "Local system addresses";
            }
            enum "ospf" {
              description
                "Open Shortest Path First";
            }
            enum "ospf2" {
              description
                "Open Shortest Path First Version 2";
            }
            enum "ospf3" {
              description
                "Open Shortest Path First Version 3";
            }
            enum "l-ospf" {
              description
                "Labelled OSPF";
            }
            enum "pim" {
              description
                "Protocol Independent Multicast";
            }
            enum "rip" {
              description
                "Routing Information Protocol";
            }
            enum "ripng" {
              description
                "Routing Information Protocol next generation";
            }
            enum "static" {
              description
                "Statically defined addresses";
            }
            enum "arp" {
              description
                "Addresses learned from ARP";
            }
            enum "frr" {
              description
                "Addresses created by Host Fast Re-route";
            }
            enum "mpls" {
              description
                "Multiprotocol Label Switching";
            }
            enum "ldp" {
              description
                "Label Distribution Protocol";
            }
            enum "rsvp" {
              description
                "Resource Reservation Protocol";
            }
            enum "msdp" {
              description
                "Multicast Source Discovery Protocol";
            }
            enum "route-target" {
              description
                "Local route target VPN membership";
            }
            enum "access" {
              description
                "Access server routes";
            }
            enum "access-internal" {
              description
                "Internal routes to directly connected clients";
            }
            enum "anchor" {
              description
                "Anchor routes connected to UEs";
            }
            enum "bgp-static" {
              description
                "BGP static routes";
            }
            enum "vpls" {
              description
                "Virtual Private LAN Service";
            }
            enum "evpn" {
              description
                "Ethernet VPN Service";
            }
            enum "spring-te" {
              description
                "SPRING Traffic-Engineered";
            }
            enum "bgp-ls-epe" {
              description
                "Addresses created by BGP-LS egress TE";
            }
            enum "express-segments" {
              description
                "Express-segment routes";
            }
            enum "rift" {
              description
                "RIFT routes";
            }
            enum "l2-learned-host-routing" {
              description
                "Layer2-learned host routes";
            }
            enum "srv6-isis" {
              description
                "SRV6 ISIS";
            }
            enum "ari-ts" {
              description
                "ARI TS routes";
            }
            enum "srv6" {
              description
                "Segment Routing IPv6 local route";
            }
          }
          ordered-by user;
          description
            "Protocol from which route was learned";
        }
        leaf rib {
          type string;
          description
            "Routing table";
        }
        leaf-list neighbor {
          type jt:ipaddr;
          ordered-by user;
          description
            "Neighboring router";
        }
        leaf-list next-hop {
          type jt:ipaddr;
          ordered-by user;
          description
            "Next-hop router";
        }
        leaf-list interface {
          type union {
            type jt:ipaddr-or-interface;
            type string {
              pattern "<.*>|$.*";
            }
          }
          ordered-by user;
          description
            "Interface name or address";
        }
        leaf area {
          type jt:areaid;
          description
            "OSPF area identifier";
        }
        leaf-list as-path {
          type string;
          ordered-by user;
          description
            "Name of AS path regular expression (BGP only)";
        }
        leaf-list as-path-group {
          type string;
          ordered-by user;
          description
            "Name of AS path group (BGP only)";
        }
        leaf origin {
          type enumeration {
            enum "igp" {
              description
                "Path originated in the local IGP";
            }
            enum "egp" {
              description
                "Path originated in another AS";
            }
            enum "incomplete" {
              description
                "Path was learned by some other means";
            }
          }
          description
            "BGP origin attribute";
        }
        leaf-list community {
          type string;
          ordered-by user;
          description
            "BGP community";
        }
        leaf level {
          type union {
            type uint32;
            type string {
              pattern "<.*>|$.*";
            }
          }
          description
            "IS-IS level";
        }
        container external {
          presence "enable external";
          description
            "External route";
          uses apply-advanced;
          leaf type {
            type union {
              type string {
                pattern "<.*>|$.*";
              }
              type int32 {
                range "1 .. 2";
              }
            }
            description
              "OSPF external metric type";
          }
        }
        leaf bgp-srte-discriminator {
          type union {
            type uint32;
            type string {
              pattern "<.*>|$.*";
            }
          }
          description
            "Srte discriminator";
        }
        leaf srte-color {
          type union {
            type uint32;
            type string {
              pattern "<.*>|$.*";
            }
          }
          description
            "Srte color";
        }
        leaf programmed {
          type empty;
          description
            "API-programmed route";
        }
        leaf validation-database {
          type enumeration {
            enum "valid" {
              description
                "Match for valid database validation-state";
            }
            enum "invalid" {
              description
                "Match for invalid database validation-state";
            }
            enum "unknown" {
              description
                "Match for unknown database validation-state";
            }
          }
          description
            "Name to identify a validation-state";
        }
        container validation-database-instance {
          presence "enable validation-database-instance";
          description
            "Name to identify a validation-state with DB name";
          uses apply-advanced;
          leaf database-name {
            type string;
            description
              "Route Validation Database name to be looked at";
          }
          leaf state {
            type enumeration {
              enum "valid" {
                description
                  "Match for valid database validation-state";
              }
              enum "invalid" {
                description
                  "Match for invalid database validation-state";
              }
              enum "unknown" {
                description
                  "Match for unknown database validation-state";
              }
            }
            mandatory true;
            description
              "Name to identify a validation-state";
          }
        }
        list nexthop-weight {
          key "choice-ident choice-value weight";
          ordered-by user;
          description
            "Weight of the gateway";
          leaf choice-ident {
            type enumeration {
              enum "equal";
              enum "greater-than";
              enum "less-than";
              enum "greater-than-equal";
              enum "less-than-equal";
            }
          }
          leaf choice-value {
            type string;
          }
          leaf weight {
            type union {
              type string {
                pattern "<.*>|$.*";
              }
              type uint32 {
                range "1 .. 65535";
              }
            }
            description
              "Weight of the gateway";
          }
          uses apply-advanced;
          choice weight_type {
            case case_1 {
              leaf all-nexthop {
                type empty;
                description
                  "All the gateway weight should be matched";
              }
            }
          }
        }
        list nexthop-ecmp {
          key "choice-ident choice-value ecmp";
          ordered-by user;
          description
            "Qualify nexthop equal cost multipath gateways";
          leaf choice-ident {
            type enumeration {
              enum "equal";
              enum "greater-than";
              enum "less-than";
              enum "greater-than-equal";
              enum "less-than-equal";
            }
          }
          leaf choice-value {
            type string;
          }
          leaf ecmp {
            type union {
              type string {
                pattern "<.*>|$.*";
              }
              type uint32 {
                range "1 .. 512";
              }
            }
            description
              "Number of equal cost multipath gateways";
          }
          uses apply-advanced;
        }
        leaf metric {
          type union {
            type uint32;
            type string {
              pattern "<.*>|$.*";
            }
          }
          description
            "Metric value";
        }
        leaf metric2 {
          type union {
            type uint32;
            type string {
              pattern "<.*>|$.*";
            }
          }
          description
            "Metric value 2";
        }
        leaf metric3 {
          type union {
            type uint32;
            type string {
              pattern "<.*>|$.*";
            }
          }
          description
            "Metric value 3";
        }
        leaf metric4 {
          type union {
            type uint32;
            type string {
              pattern "<.*>|$.*";
            }
          }
          description
            "Metric value 4";
        }
        leaf-list tag {
          type union {
            type uint32;
            type string {
              pattern "<.*>|$.*";
            }
          }
          ordered-by user;
          description
            "Tag string";
        }
        leaf-list tag2 {
          type union {
            type uint32;
            type string {
              pattern "<.*>|$.*";
            }
          }
          ordered-by user;
          description
            "Tag string 2";
        }
        leaf preference {
          type union {
            type uint32;
            type string {
              pattern "<.*>|$.*";
            }
          }
          description
            "Preference value";
        }
        leaf preference2 {
          type union {
            type uint32;
            type string {
              pattern "<.*>|$.*";
            }
          }
          description
            "Preference value 2";
        }
        leaf color {
          type union {
            type uint32;
            type string {
              pattern "<.*>|$.*";
            }
          }
          description
            "Color (preference) value";
        }
        leaf color2 {
          type union {
            type uint32;
            type string {
              pattern "<.*>|$.*";
            }
          }
          description
            "Color (preference) value 2";
        }
        leaf local-preference {
          type union {
            type uint32;
            type string {
              pattern "<.*>|$.*";
            }
          }
          description
            "Local preference associated with a route";
        }
        leaf-list policy {
          type jt:policy-algebra;
          ordered-by user;
          description
            "Name of policy to evaluate";
        }
        choice lsp-name-type {
          case case_1 {
            leaf lsp {
              type string;
              description
                "Label switched path name";
            }
          }
          case case_2 {
            leaf lsp-regex {
              type string;
              description
                "Label switched path name regular expression";
            }
          }
        }
        container source-routing-path {
          presence "enable source-routing-path";
          description
            "Spring-te lsp policy attributes";
          leaf name-regex {
            type string;
            description
              "Spring-te lsp name regex";
          }
          leaf dest {
            type jt:ipaddr;
            description
              "Spring-te lsp IPV4/IPV6 destination without color";
          }
          leaf origin {
            type jt:ipaddr;
            description
              "Spring-te lsp origin address";
          }
          leaf tunnel-source {
            type enumeration {
              enum "pcep" {
                description
                  "Spring-te lsp src pcep";
              }
              enum "bgp" {
                description
                  "Spring-te lsp src bgp";
              }
            }
            description
              "Spring-te lsp source protocol";
          }
          leaf route-distinguisher {
            type union {
              type uint32;
              type string {
                pattern "<.*>|$.*";
              }
            }
            description
              "Spring-te lsp route distinguisher";
          }
          leaf color {
            type union {
              type uint32;
              type string {
                pattern "<.*>|$.*";
              }
            }
            description
              "Spring-te lsp color";
          }
        }
      }
      container then {
        description
          "Actions to take if 'from' and 'to' conditions match";
        uses apply-advanced;
        container metric {
          description
            "Metric value";
          uses apply-advanced;
          choice metric_action {
            case case_1 {
              leaf metric {
                type union {
                  type uint32;
                  type string {
                    pattern "<.*>|$.*";
                  }
                }
              }
            }
            case case_2 {
              leaf add {
                type union {
                  type uint32;
                  type string {
                    pattern "<.*>|$.*";
                  }
                }
                description
                  "Add constant to attribute";
              }
            }
            case case_3 {
              leaf subtract {
                type union {
                  type uint32;
                  type string {
                    pattern "<.*>|$.*";
                  }
                }
                description
                  "Subtract constant from attribute";
              }
            }
            case case_4 {
              container igp {
                presence "enable igp";
                description
                  "Track the IGP metric (BGP only)";
                leaf metric_offset {
                  type union {
                    type int32;
                    type string {
                      pattern "<.*>|$.*";
                    }
                  }
                  description
                    "Metric offset for MED";
                }
              }
            }
            case case_5 {
              container minimum-igp {
                presence "enable minimum-igp";
                description
                  "Track the minimum IGP metric (BGP only)";
                leaf metric_offset {
                  type union {
                    type int32;
                    type string {
                      pattern "<.*>|$.*";
                    }
                  }
                  description
                    "Metric offset for MED";
                }
              }
            }
            case case_6 {
              container expression {
                description
                  "Calculate value based on route metric and metric2";
                uses metric_expression_type;
              }
            }
            case case_7 {
              leaf aigp {
                type empty;
                description
                  "Use aigp, if it exists, to set the IGP metric";
              }
            }
            case case_8 {
              container effective-aigp {
                presence "enable effective-aigp";
                description
                  "Track the effective AIGP metric (BGP only)";
                leaf metric_offset {
                  type union {
                    type int32;
                    type string {
                      pattern "<.*>|$.*";
                    }
                  }
                  description
                    "Metric offset for MED";
                }
              }
            }
            case case_9 {
              container minimum-effective-aigp {
                presence "enable minimum-effective-aigp";
                description
                  "Track the minimum effective AIGP metric (BGP only)";
                leaf metric_offset {
                  type union {
                    type int32;
                    type string {
                      pattern "<.*>|$.*";
                    }
                  }
                  description
                    "Metric offset for MED";
                }
              }
            }
          }
        }
        container metric2 {
          description
            "Metric value 2";
          uses apply-advanced;
          choice metric_action {
            case case_1 {
              leaf metric2 {
                type union {
                  type uint32;
                  type string {
                    pattern "<.*>|$.*";
                  }
                }
              }
            }
            case case_2 {
              leaf add {
                type union {
                  type uint32;
                  type string {
                    pattern "<.*>|$.*";
                  }
                }
                description
                  "Add constant to attribute";
              }
            }
            case case_3 {
              leaf subtract {
                type union {
                  type uint32;
                  type string {
                    pattern "<.*>|$.*";
                  }
                }
                description
                  "Subtract constant from attribute";
              }
            }
          }
        }
        container metric3 {
          description
            "Metric value 3";
          uses apply-advanced;
          choice metric_action {
            case case_1 {
              leaf metric3 {
                type union {
                  type uint32;
                  type string {
                    pattern "<.*>|$.*";
                  }
                }
              }
            }
            case case_2 {
              leaf add {
                type union {
                  type uint32;
                  type string {
                    pattern "<.*>|$.*";
                  }
                }
                description
                  "Add constant to attribute";
              }
            }
            case case_3 {
              leaf subtract {
                type union {
                  type uint32;
                  type string {
                    pattern "<.*>|$.*";
                  }
                }
                description
                  "Subtract constant from attribute";
              }
            }
          }
        }
        container metric4 {
          description
            "Metric value 4";
          uses apply-advanced;
          choice metric_action {
            case case_1 {
              leaf metric4 {
                type union {
                  type uint32;
                  type string {
                    pattern "<.*>|$.*";
                  }
                }
              }
            }
            case case_2 {
              leaf add {
                type union {
                  type uint32;
                  type string {
                    pattern "<.*>|$.*";
                  }
                }
                description
                  "Add constant to attribute";
              }
            }
            case case_3 {
              leaf subtract {
                type union {
                  type uint32;
                  type string {
                    pattern "<.*>|$.*";
                  }
                }
                description
                  "Subtract constant from attribute";
              }
            }
          }
        }
        container tag {
          description
            "Tag string";
          uses apply-advanced;
          choice metric_action {
            case case_1 {
              leaf tag {
                type union {
                  type uint32;
                  type string {
                    pattern "<.*>|$.*";
                  }
                }
              }
            }
            case case_2 {
              leaf add {
                type union {
                  type uint32;
                  type string {
                    pattern "<.*>|$.*";
                  }
                }
                description
                  "Add constant to attribute";
              }
            }
            case case_3 {
              leaf subtract {
                type union {
                  type uint32;
                  type string {
                    pattern "<.*>|$.*";
                  }
                }
                description
                  "Subtract constant from attribute";
              }
            }
          }
        }
        container tag2 {
          description
            "Tag string 2";
          uses apply-advanced;
          choice metric_action {
            case case_1 {
              leaf tag2 {
                type union {
                  type uint32;
                  type string {
                    pattern "<.*>|$.*";
                  }
                }
              }
            }
            case case_2 {
              leaf add {
                type union {
                  type uint32;
                  type string {
                    pattern "<.*>|$.*";
                  }
                }
                description
                  "Add constant to attribute";
              }
            }
            case case_3 {
              leaf subtract {
                type union {
                  type uint32;
                  type string {
                    pattern "<.*>|$.*";
                  }
                }
                description
                  "Subtract constant from attribute";
              }
            }
          }
        }
        container preference {
          description
            "Preference value";
          uses apply-advanced;
          choice metric_action {
            case case_1 {
              leaf preference {
                type union {
                  type uint32;
                  type string {
                    pattern "<.*>|$.*";
                  }
                }
              }
            }
            case case_2 {
              leaf add {
                type union {
                  type uint32;
                  type string {
                    pattern "<.*>|$.*";
                  }
                }
                description
                  "Add constant to attribute";
              }
            }
            case case_3 {
              leaf subtract {
                type union {
                  type uint32;
                  type string {
                    pattern "<.*>|$.*";
                  }
                }
                description
                  "Subtract constant from attribute";
              }
            }
          }
        }
        container preference2 {
          description
            "Preference value 2";
          uses apply-advanced;
          choice metric_action {
            case case_1 {
              leaf preference2 {
                type union {
                  type uint32;
                  type string {
                    pattern "<.*>|$.*";
                  }
                }
              }
            }
            case case_2 {
              leaf add {
                type union {
                  type uint32;
                  type string {
                    pattern "<.*>|$.*";
                  }
                }
                description
                  "Add constant to attribute";
              }
            }
            case case_3 {
              leaf subtract {
                type union {
                  type uint32;
                  type string {
                    pattern "<.*>|$.*";
                  }
                }
                description
                  "Subtract constant from attribute";
              }
            }
          }
        }
        container color {
          description
            "Color (preference) value";
          uses apply-advanced;
          choice metric_action {
            case case_1 {
              leaf color {
                type union {
                  type uint32;
                  type string {
                    pattern "<.*>|$.*";
                  }
                }
              }
            }
            case case_2 {
              leaf add {
                type union {
                  type uint32;
                  type string {
                    pattern "<.*>|$.*";
                  }
                }
                description
                  "Add constant to attribute";
              }
            }
            case case_3 {
              leaf subtract {
                type union {
                  type uint32;
                  type string {
                    pattern "<.*>|$.*";
                  }
                }
                description
                  "Subtract constant from attribute";
              }
            }
          }
        }
        container color2 {
          description
            "Color (preference) value 2";
          uses apply-advanced;
          choice metric_action {
            case case_1 {
              leaf color2 {
                type union {
                  type uint32;
                  type string {
                    pattern "<.*>|$.*";
                  }
                }
              }
            }
            case case_2 {
              leaf add {
                type union {
                  type uint32;
                  type string {
                    pattern "<.*>|$.*";
                  }
                }
                description
                  "Add constant to attribute";
              }
            }
            case case_3 {
              leaf subtract {
                type union {
                  type uint32;
                  type string {
                    pattern "<.*>|$.*";
                  }
                }
                description
                  "Subtract constant from attribute";
              }
            }
          }
        }
        container local-preference {
          description
            "Local preference associated with a route";
          uses apply-advanced;
          choice metric_action {
            case case_1 {
              leaf local-preference {
                type union {
                  type uint32;
                  type string {
                    pattern "<.*>|$.*";
                  }
                }
              }
            }
            case case_2 {
              leaf add {
                type union {
                  type uint32;
                  type string {
                    pattern "<.*>|$.*";
                  }
                }
                description
                  "Add constant to attribute";
              }
            }
            case case_3 {
              leaf subtract {
                type union {
                  type uint32;
                  type string {
                    pattern "<.*>|$.*";
                  }
                }
                description
                  "Subtract constant from attribute";
              }
            }
          }
        }
        container credibility {
          description
            "TED credibility value for entries from BGP-TE";
          uses apply-advanced;
          choice metric_action {
            case case_1 {
              leaf credibility {
                type union {
                  type uint32;
                  type string {
                    pattern "<.*>|$.*";
                  }
                }
              }
            }
            case case_2 {
              leaf add {
                type union {
                  type uint32;
                  type string {
                    pattern "<.*>|$.*";
                  }
                }
                description
                  "Add constant to attribute";
              }
            }
            case case_3 {
              leaf subtract {
                type union {
                  type uint32;
                  type string {
                    pattern "<.*>|$.*";
                  }
                }
                description
                  "Subtract constant from attribute";
              }
            }
          }
        }
        leaf priority {
          type enumeration {
            enum "high" {
              description
                "Set priority to high";
            }
            enum "medium" {
              description
                "Set priority to medium";
            }
            enum "low" {
              description
                "Set priority to low";
            }
          }
          description
            "Set priority for route installation";
        }
        container prefix-segment {
          description
            "Set prefix segment attributes";
          uses apply-advanced;
          list algorithm {
            key "name";
            max-elements 15;
            description
              "Set prefix segment attributes for strict/flex algorithm ";
            leaf name {
              type union {
                type string {
                  pattern "<.*>|$.*";
                }
                type uint32 {
                  range "1 .. 255";
                }
              }
              mandatory true;
              description
                "Set prefix segment for strict/flex algorithm";
            }
            leaf index {
              type union {
                type string {
                  pattern "<.*>|$.*";
                }
                type uint32 {
                  range "0 .. 1048575";
                }
              }
              mandatory true;
              description
                "Set prefix segment index id";
            }
            leaf node-segment {
              type empty;
              description
                "Set node segment flag for this prefix segment";
            }
          }
          leaf index {
            type union {
              type string {
                pattern "<.*>|$.*";
              }
              type uint32 {
                range "0 .. 1048575";
              }
            }
            description
              "Set prefix segment index id";
          }
          leaf node-segment {
            type empty;
            description
              "Set node segment flag for default prefix segment";
          }
          leaf redistribute {
            type empty;
            description
              "Redistribute prefix-segment from route entry";
          }
        }
        leaf label-allocation {
          type enumeration {
            enum "per-table" {
              description
                "Set per-table label allocation mode";
            }
            enum "per-nexthop" {
              description
                "Set per-nexthop label allocation mode";
            }
            enum "per-table-localize" {
              description
                "Set per-table-localize label allocation mode";
            }
          }
          description
            "Set label allocation mode";
        }
        container add-path {
          description
            "Set BGP add-path attributes";
          leaf send-count {
            type union {
              type string {
                pattern "<.*>|$.*";
              }
              type uint32 {
                range "2 .. 64";
              }
            }
            description
              "Number of add-paths sent";
          }
        }
        leaf fib-install-priority {
          type enumeration {
            enum "high" {
              description
                "Set Fib install priority  to high";
            }
            enum "medium" {
              description
                "Set Fib install priority to medium ";
            }
          }
          description
            "Set Fib Instalation priority of a route";
        }
        leaf validation-state {
          type enumeration {
            enum "valid" {
              description
                "Set validaton-state to valid";
            }
            enum "invalid" {
              description
                "Set validation-state to invalid";
            }
            enum "unknown" {
              description
                "Set validation-state to unknown";
            }
          }
          description
            "Set validation-state of a route";
        }
        leaf origin {
          type enumeration {
            enum "igp" {
              description
                "Path originated in the local IGP";
            }
            enum "egp" {
              description
                "Path originated in another AS";
            }
            enum "incomplete" {
              description
                "Path was learned by some other means";
            }
          }
          description
            "BGP path origin";
        }
        container srv6 {
          description
            "Configure SID with 128 bit address";
          leaf sid {
            type jt:ipv6addr;
            description
              "IPv6 Address";
          }
          leaf locator {
            type string;
            description
              "Name of locator";
          }
          choice locator_type {
            case case_1 {
              leaf micro-dt4-sid {
                type empty;
                description
                  "Micro SID type dt4";
              }
            }
            case case_2 {
              leaf micro-dt6-sid {
                type empty;
                description
                  "Micro SID type dt6";
              }
            }
            case case_3 {
              leaf micro-dt46-sid {
                type empty;
                description
                  "Micro SID type dt46";
              }
            }
          }
        }
        container aigp-originate {
          presence "enable aigp-originate";
          description
            "Originate a BGP AIGP attribute";
          leaf distance {
            type union {
              type uint32;
              type string {
                pattern "<.*>|$.*";
              }
            }
            description
              "AIGP distance";
          }
        }
        container aigp-adjust {
          description
            "Adjust a BGP AIGP attribute";
          choice math-op {
            case case_1 {
              leaf add {
                type empty;
              }
            }
            case case_2 {
              leaf subtract {
                type empty;
              }
            }
            case case_3 {
              leaf multiply {
                type empty;
              }
            }
            case case_4 {
              leaf divide {
                type empty;
              }
            }
          }
          choice adjust-value {
            case case_1 {
              leaf user-value {
                type union {
                  type uint64;
                  type string {
                    pattern "<.*>|$.*";
                  }
                }
                description
                  "Adjustment value";
              }
            }
            case case_2 {
              leaf distance-to-protocol-nexthop {
                type empty;
                description
                  "Metric2";
              }
            }
          }
        }
        list community {
          key "choice-ident choice-value community-name";
          ordered-by user;
          description
            "BGP community properties associated with a route";
          leaf choice-ident {
            type enumeration {
              enum "equal-literal";
              enum "set";
              enum "plus-literal";
              enum "add";
              enum "minus-literal";
              enum "delete";
            }
          }
          leaf choice-value {
            type string;
          }
          leaf community-name {
            type string;
            description
              "Name to identify a BGP community";
          }
        }
        list tunnel-attribute {
          key "choice-ident choice-value tunnel-attribute-name";
          ordered-by user;
          description
            "BGP tunnel attribute associated with a route";
          leaf choice-ident {
            type enumeration {
              enum "set";
              enum "remove";
            }
          }
          leaf choice-value {
            type string;
          }
          leaf tunnel-attribute-name {
            type string;
            description
              "Name of a tunnel attribute , or 'all'";
          }
        }
        container assisted-replication {
          presence "enable assisted-replication";
          description
            "Deterministic AR replicator knobs";
          uses apply-advanced;
          leaf-list replicator-ip {
            type jt:ipaddr;
            max-elements 1;
            description
              "Set deterministic AR replicator ip for the flow";
          }
          leaf strict {
            type empty;
            description
              "Do not use any other replicator";
          }
          leaf-list fallback-replicator-ip {
            type jt:ipaddr;
            max-elements 1;
            description
              "Set Fallback replicator-ip";
          }
        }
        leaf damping {
          type string;
          description
            "Define BGP route flap damping parameters";
        }
        container aggregate-bandwidth {
          presence "enable aggregate-bandwidth";
          description
            "Advertise aggregate outbound link bandwidth";
          uses apply-advanced;
          choice transitive-type {
            case case_1 {
              leaf transitive {
                type empty;
                description
                  "Transitive flag for link bandwidth";
              }
            }
            case case_2 {
              leaf non-transitive {
                type empty;
                description
                  "Non-Transitive flag for link bandwidth";
              }
            }
          }
          leaf divide-equal {
            type empty;
            description
              "Divide-equal";
          }
        }
        container auto-link-bandwidth {
          presence "enable auto-link-bandwidth";
          description
            "Auto sense and attach link bandwidth community";
          uses apply-advanced;
          choice transitive-type {
            case case_1 {
              leaf transitive {
                type empty;
                description
                  "Transitive flag for link bandwidth";
              }
            }
            case case_2 {
              leaf non-transitive {
                type empty;
                description
                  "Non-Transitive flag for link bandwidth";
              }
            }
          }
        }
        leaf limit-bandwidth {
          type union {
            type uint64;
            type string {
              pattern "<.*>|$.*";
            }
          }
          description
            "Limit advertised aggregate outbound link bandwidth";
        }
        leaf no-entropy-label-capability {
          type empty;
          description
            "Don't advertise entropy label capability";
        }
        leaf as-path-prepend {
          type string;
          description
            "Prepend AS numbers to an AS path (BGP only)";
        }
        container as-path-expand {
          description
            "Prepend AS numbers prior to adding local-as (BGP only)";
          choice aspath_exp_value {
            case case_1 {
              container last-as {
                presence "enable last-as";
                description
                  "Prepend last AS";
                leaf count {
                  type union {
                    type string {
                      pattern "<.*>|$.*";
                    }
                    type uint32 {
                      range "1 .. 32";
                    }
                  }
                  description
                    "Repeat count";
                }
              }
            }
            case case_2 {
              leaf aspath {
                type string;
                description
                  "AS path string";
              }
            }
          }
        }
        container next-hop {
          description
            "Set the address of the next-hop router";
          choice nexthop_value {
            case case_1 {
              leaf self {
                type empty;
                description
                  "Use a local address as the next-hop address";
              }
            }
            case case_2 {
              leaf peer-address {
                type empty;
                description
                  "Use the remote peer address as the next-hop address";
              }
            }
            case case_3 {
              leaf address {
                type jt:ipaddr;
                description
                  "Next-hop address";
              }
            }
            case case_4 {
              leaf reject {
                type empty;
                description
                  "Use a reject next hop";
              }
            }
            case case_5 {
              leaf discard {
                type empty;
                description
                  "Use a discard next hop";
              }
            }
            case case_6 {
              leaf next-table {
                type string;
                description
                  "Perform a forwarding lookup in the specified table";
              }
            }
          }
        }
        container install-nexthop {
          description
            "Choose the next hop to be used for forwarding";
          choice strict_type {
            case case_1 {
              leaf strict {
                type empty;
                description
                  "Do not use any other available next hops";
              }
            }
            case case_2 {
              leaf strict-named-lsp {
                type empty;
                description
                  "Do not use any other non-lsp next hops";
              }
            }
          }
          choice nexthop-value {
            case case_1 {
              leaf-list lsp {
                type string;
                ordered-by user;
                description
                  "Next-hop LSP name";
              }
            }
            case case_2 {
              leaf-list lsp-regex {
                type string;
                ordered-by user;
                description
                  "Next-hop LSP name regular expression";
              }
            }
            case case_3 {
              leaf-list static-lsp {
                type string;
                ordered-by user;
                description
                  "Next-hop static LSP name";
              }
            }
            case case_4 {
              leaf-list static-lsp-regex {
                type string;
                ordered-by user;
                description
                  "Next-hop static LSP name regular expression";
              }
            }
            case case_5 {
              leaf non-lsp-nexthop {
                type empty;
                description
                  "Next-hop with non-lsp";
              }
            }
            case case_6 {
              leaf non-labelled-nexthop {
                type empty;
                description
                  "Next-hop without tag";
              }
            }
            case case_7 {
              leaf overlay-vxlan-interfaces {
                type empty;
                description
                  "Next-hop for vxlan interfaces";
              }
            }
          }
          container except {
            description
              "Do not choose to install matching next hops";
            uses apply-advanced;
            choice nexthop-value {
              case case_1 {
                leaf-list lsp {
                  type string;
                  ordered-by user;
                  description
                    "Next-hop LSP name";
                }
              }
              case case_2 {
                leaf-list lsp-regex {
                  type string;
                  ordered-by user;
                  description
                    "Next-hop LSP name regular expression";
                }
              }
              case case_3 {
                leaf-list static-lsp {
                  type string;
                  ordered-by user;
                  description
                    "Next-hop static LSP name";
                }
              }
              case case_4 {
                leaf-list static-lsp-regex {
                  type string;
                  ordered-by user;
                  description
                    "Next-hop static LSP name regular expression";
                }
              }
              case case_5 {
                leaf non-lsp-nexthop {
                  type empty;
                  description
                    "Next-hop with non-lsp";
                }
              }
              case case_6 {
                leaf non-labelled-nexthop {
                  type empty;
                  description
                    "Next-hop without tag";
                }
              }
              case case_7 {
                leaf overlay-vxlan-interfaces {
                  type empty;
                  description
                    "Next-hop for vxlan interfaces";
                }
              }
            }
            container fallback {
              description
                "Backup option";
              uses apply-advanced;
              choice nexthop-value {
                case case_1 {
                  leaf-list lsp {
                    type string;
                    ordered-by user;
                    description
                      "Next-hop LSP name";
                  }
                }
                case case_2 {
                  leaf-list lsp-regex {
                    type string;
                    ordered-by user;
                    description
                      "Next-hop LSP name regular expression";
                  }
                }
                case case_3 {
                  leaf-list static-lsp {
                    type string;
                    ordered-by user;
                    description
                      "Next-hop static LSP name";
                  }
                }
                case case_4 {
                  leaf-list static-lsp-regex {
                    type string;
                    ordered-by user;
                    description
                      "Next-hop static LSP name regular expression";
                  }
                }
                case case_5 {
                  leaf non-lsp-nexthop {
                    type empty;
                    description
                      "Next-hop with non-lsp";
                  }
                }
                case case_6 {
                  leaf non-labelled-nexthop {
                    type empty;
                    description
                      "Next-hop without tag";
                  }
                }
                case case_7 {
                  leaf overlay-vxlan-interfaces {
                    type empty;
                    description
                      "Next-hop for vxlan interfaces";
                  }
                }
              }
              container except {
                description
                  "Do not choose to install matching next hops";
                uses apply-advanced;
                choice nexthop-value {
                  case case_1 {
                    leaf-list lsp {
                      type string;
                      ordered-by user;
                      description
                        "Next-hop LSP name";
                    }
                  }
                  case case_2 {
                    leaf-list lsp-regex {
                      type string;
                      ordered-by user;
                      description
                        "Next-hop LSP name regular expression";
                    }
                  }
                  case case_3 {
                    leaf-list static-lsp {
                      type string;
                      ordered-by user;
                      description
                        "Next-hop static LSP name";
                    }
                  }
                  case case_4 {
                    leaf-list static-lsp-regex {
                      type string;
                      ordered-by user;
                      description
                        "Next-hop static LSP name regular expression";
                    }
                  }
                  case case_5 {
                    leaf non-lsp-nexthop {
                      type empty;
                      description
                        "Next-hop with non-lsp";
                    }
                  }
                  case case_6 {
                    leaf non-labelled-nexthop {
                      type empty;
                      description
                        "Next-hop without tag";
                    }
                  }
                  case case_7 {
                    leaf overlay-vxlan-interfaces {
                      type empty;
                      description
                        "Next-hop for vxlan interfaces";
                    }
                  }
                }
              }
            }
          }
          container fallback {
            description
              "Backup option ";
            uses apply-advanced;
            choice nexthop-value {
              case case_1 {
                leaf-list lsp {
                  type string;
                  ordered-by user;
                  description
                    "Next-hop LSP name";
                }
              }
              case case_2 {
                leaf-list lsp-regex {
                  type string;
                  ordered-by user;
                  description
                    "Next-hop LSP name regular expression";
                }
              }
              case case_3 {
                leaf-list static-lsp {
                  type string;
                  ordered-by user;
                  description
                    "Next-hop static LSP name";
                }
              }
              case case_4 {
                leaf-list static-lsp-regex {
                  type string;
                  ordered-by user;
                  description
                    "Next-hop static LSP name regular expression";
                }
              }
              case case_5 {
                leaf non-lsp-nexthop {
                  type empty;
                  description
                    "Next-hop with non-lsp";
                }
              }
              case case_6 {
                leaf non-labelled-nexthop {
                  type empty;
                  description
                    "Next-hop without tag";
                }
              }
              case case_7 {
                leaf overlay-vxlan-interfaces {
                  type empty;
                  description
                    "Next-hop for vxlan interfaces";
                }
              }
            }
            container except {
              description
                "Do not choose to install matching next hops";
              uses apply-advanced;
              choice nexthop-value {
                case case_1 {
                  leaf-list lsp {
                    type string;
                    ordered-by user;
                    description
                      "Next-hop LSP name";
                  }
                }
                case case_2 {
                  leaf-list lsp-regex {
                    type string;
                    ordered-by user;
                    description
                      "Next-hop LSP name regular expression";
                  }
                }
                case case_3 {
                  leaf-list static-lsp {
                    type string;
                    ordered-by user;
                    description
                      "Next-hop static LSP name";
                  }
                }
                case case_4 {
                  leaf-list static-lsp-regex {
                    type string;
                    ordered-by user;
                    description
                      "Next-hop static LSP name regular expression";
                  }
                }
                case case_5 {
                  leaf non-lsp-nexthop {
                    type empty;
                    description
                      "Next-hop with non-lsp";
                  }
                }
                case case_6 {
                  leaf non-labelled-nexthop {
                    type empty;
                    description
                      "Next-hop without tag";
                  }
                }
                case case_7 {
                  leaf overlay-vxlan-interfaces {
                    type empty;
                    description
                      "Next-hop for vxlan interfaces";
                  }
                }
              }
            }
          }
        }
        leaf trace {
          type empty;
          description
            "Log matches to a trace file";
        }
        container external {
          presence "enable external";
          description
            "External route";
          uses apply-advanced;
          leaf type {
            type union {
              type string {
                pattern "<.*>|$.*";
              }
              type int32 {
                range "1 .. 2";
              }
            }
            description
              "OSPF external metric type";
          }
          leaf nssa-only {
            type empty;
            description
              "Clear P-bit on lsa type 7";
          }
        }
        container load-balance {
          description
            "Type of load balancing in forwarding table";
          choice load_balance_type {
            case case_1 {
              leaf per-packet {
                type empty;
                description
                  "Load balance on a per-packet basis deprecated, use per-flow instead";
              }
            }
            case case_2 {
              leaf per-flow {
                type empty;
                description
                  "Load balance on a per-flow basis";
              }
            }
            case case_3;
            case case_4;
            case case_5;
            case case_6;
            case case_7;
            case case_8;
            case case_9;
            case case_10;
            case case_11;
          }
        }
        container advertise-locator {
          presence "enable advertise-locator";
          description
            "Advertise SRv6 Locator";
          uses apply-advanced;
          leaf internal {
            type empty;
            description
              "Advertise locator as Interal route";
          }
        }
        leaf set-down-bit {
          type empty;
          description
            "Set down bit";
        }
        leaf analyze {
          type empty;
          description
            "Send to registered controllers for analysis";
        }
        leaf destination-class {
          type string;
          description
            "Set destination class in forwarding table";
        }
        leaf source-class {
          type string;
          description
            "Set source class in forwarding table";
        }
        leaf forwarding-class {
          type string;
          description
            "Set source or destination class in forwarding table";
        }
        container map-to-interface {
          description
            "Set output logical interface";
          choice map_to_interface_value {
            case case_1 {
              leaf self {
                type empty;
                description
                  "Map the interface to itself";
              }
            }
            case case_2 {
              leaf interface {
                type union {
                  type jt:interface-name;
                  type string {
                    pattern "<.*>|$.*";
                  }
                }
                description
                  "Output logical interface";
              }
            }
          }
        }
        leaf-list ssm-source {
          type jt:ipaddr;
          ordered-by user;
          description
            "List of Sources for SSM mapping";
        }
        container p2mp-lsp-root {
          description
            "P2mp lsp root address";
          uses apply-advanced;
          leaf address {
            type jt:ipv4addr;
            description
              "Ipv4 root address";
          }
        }
        leaf dynamic-tunnel-attributes {
          type string;
          description
            "Choose the dynamic tunnel attributes used for forwarding";
        }
        leaf tunnel-end-point-address {
          type jt:ipaddr;
          description
            "Set tunnel end-point address of tunnel";
        }
        leaf selected-mldp-egress {
          type empty;
          description
            "This node should act as egress node for MLDP inband signalling";
        }
        leaf mhop-bfd-port {
          type empty;
          description
            "Use port number 4784 for MPLS-BFD as per RFC5884";
        }
        leaf no-backup {
          type empty;
          description
            "This prefix should not have backup";
        }
        leaf default-action {
          type enumeration {
            enum "accept" {
              description
                "Accept a route";
            }
            enum "reject" {
              description
                "Reject a route";
            }
          }
          description
            "Set default policy action";
        }
        leaf next {
          type enumeration {
            enum "policy" {
              description
                "Skip to next policy filter";
            }
            enum "term" {
              description
                "Skip to next term in a policy filter";
            }
          }
          description
            "Skip to next policy or term";
        }
        choice accept_reject {
          case case_1 {
            leaf accept {
              type empty;
              description
                "Accept a route";
            }
          }
          case case_2 {
            leaf reject {
              type empty;
              description
                "Reject a route";
            }
          }
        }
        container bgp-output-queue-priority {
          description
            "Set the BGP Update output queue priority.";
          choice class {
            case case_1 {
              leaf priority {
                type union {
                  type string {
                    pattern "<.*>|$.*";
                  }
                  type uint32 {
                    range "1 .. 16";
                  }
                }
                description
                  "Output queue priority; higher is better";
              }
            }
            case case_2 {
              leaf expedited {
                type empty;
                description
                  "Expedited queue; highest priority";
              }
            }
          }
        }
        leaf multipath-resolve {
          type empty;
          description
            "Use all paths for resolution over this prefix";
        }
        leaf source-routing-path-template {
          type string;
          description
            "Spring-te template to apply";
        }
        leaf label-allocation-fallback-reject {
          type empty;
          description
            "Suppress prefix export when label allocation fails";
        }
        leaf resolution-map {
          type string;
          description
            "Set resolution map modes";
        }
        leaf ignore-service-label {
          type empty;
          description
            "Ignore service labels";
        }
        container prefix-attribute-flags {
          presence "enable prefix-attribute-flags";
          description
            "Set ISIS prefix attribute flags sub TLV";
          uses apply-advanced;
          leaf node-segment-flag {
            type empty;
            description
              "Set node segment flag ";
          }
          leaf external-prefix-flag {
            type empty;
            description
              "Set external prefix flag ";
          }
          leaf anycast-flag {
            type empty;
            description
              "Set anycast flag ";
          }
          leaf entropy-label-capability-flag {
            type empty;
            description
              "Set entropy label capability flag ";
          }
        }
        container ipv4-source-router-id {
          presence "enable ipv4-source-router-id";
          description
            "Set IPv4 source router id in advertisement";
          uses apply-advanced;
          leaf router-id {
            type jt:ipaddr;
            description
              "Specify IPv4 address";
          }
        }
        container ipv6-source-router-id {
          presence "enable ipv6-source-router-id";
          description
            "Set IPv6 source router id in advertisement";
          uses apply-advanced;
          leaf router-id {
            type jt:ipv6addr;
            description
              "Specify IPv6 address";
          }
        }
        leaf request-long-lived-ack {
          type empty;
          description
            "Advertise route after forwarding is programmed";
        }
        leaf send-withdrawal-on-route-change {
          type empty;
          description
            "Withdraw route if change is not acked from forwarding";
        }
        container slice {
          description
            "Configure Policy Slice action";
          leaf slice-name {
            type string {
              length "1 .. 64";
            }
            description
              "Slice Name";
          }
        }
        leaf filter {
          type string;
          description
            "Set firewall-filter name";
        }
        leaf strip-as-path {
          type empty;
          description
            "Remove the incoming BGP as-path and replace with local AS";
        }
        container request-acknowledgements {
          description
            "Set request acknowledgement";
          leaf nexthop-ack {
            type empty;
            description
              "Set nexthop acknowledgement ";
          }
          leaf route-ack {
            type empty;
            description
              "Set route acknowledgement ";
          }
        }
      }
    }
    container defaults {
      description
        "Policy default behaviour";
      uses apply-advanced;
      container route-filter {
        description
          "Set route filter behaviour";
        leaf walkup {
          type empty;
          description
            "Route filter walk up enable";
        }
      }
      container asregex-optimize {
        description
          "Set AS-PATH regular expression engine optimizer";
        choice scope-choice {
          case case_1 {
            leaf optimize {
              type empty;
              description
                "Enable AS-PATH regular expression optimizer";
            }
          }
          case case_2 {
            leaf no-optimize {
              type empty;
              description
                "Disable AS-PATH regular expression optimizer";
            }
          }
        }
      }
    }
    list tunnel-attribute {
      key "name";
      ordered-by user;
      description
        "BGP tunnel attributes definition";
      leaf name {
        type string;
        description
          "Tunnel attribute name";
      }
      uses apply-advanced;
      leaf tunnel-type {
        type enumeration {
          enum "ipip" {
            description
              "Tunnel type IP-IN-IP";
          }
          enum "udp" {
            description
              "Tunnel type X-IN-UDP";
          }
        }
        mandatory true;
        description
          "Tunnel type";
      }
      leaf tunnel-color {
        type union {
          type uint32;
          type string {
            pattern "<.*>|$.*";
          }
        }
        description
          "Tunnel color";
      }
      leaf remote-end-point {
        type jt:ipaddr;
        description
          "Tunnel remote end point";
      }
    }
    list community {
      key "name";
      description
        "BGP community information";
      leaf name {
        type string;
        description
          "Name to identify BGP community";
      }
      uses apply-advanced;
      leaf invert-match {
        type empty;
        description
          "Invert the result of the community expression matching";
      }
      leaf-list members {
        type string;
        ordered-by user;
        description
          "Community members";
      }
    }
    list as-list {
      key "name";
      description
        "BGP as range list information";
      leaf name {
        type string;
        description
          "Name to identify BGP as-list";
      }
      uses apply-advanced;
      leaf-list members {
        type string;
        ordered-by user;
        description
          "Single autonomous system number or range of autonomous system numbers in plain number";
      }
    }
    list as-list-group {
      key "name";
      description
        "Group a set of as-list";
      leaf name {
        type string;
        description
          "Name to identify AS list group";
      }
      uses apply-advanced;
      list as-list {
        key "name";
        description
          "BGP as range list information";
        leaf name {
          type string;
          description
            "Name to identify BGP as-list";
        }
        uses apply-advanced;
        leaf-list members {
          type string;
          ordered-by user;
          description
            "Single autonomous system number or range of autonomous system numbers";
        }
      }
    }
    list route-distinguisher {
      key "name";
      description
        "Route-distinguisher information";
      leaf name {
        type string;
        description
          "Name to identify route-distinguisher";
      }
      uses apply-advanced;
      leaf-list members {
        type string;
        ordered-by user;
        description
          "Route distinguisher string in ( *:X ) or ( Y:* ) or (X:Y) format";
      }
    }
    list as-path {
      key "name";
      ordered-by user;
      description
        "BGP autonomous system path regular expression";
      leaf name {
        type string;
        description
          "Name to identify AS path regular expression";
      }
      uses apply-advanced;
      leaf path {
        type string;
        description
          "AS path regular expression";
      }
    }
    list as-path-group {
      key "name";
      ordered-by user;
      description
        "Group a set of AS paths";
      leaf name {
        type string;
        description
          "Name to identify AS path group";
      }
      uses apply-advanced;
      list as-path {
        key "name";
        ordered-by user;
        description
          "BGP autonomous system path regular expression";
        leaf name {
          type string;
          description
            "Name to identify AS path regular expression";
        }
        leaf path {
          type string;
          description
            "AS path regular expression";
        }
      }
    }
    list damping {
      key "name";
      ordered-by user;
      description
        "BGP route flap damping properties";
      leaf name {
        type string;
        description
          "Name to identify route flap damping parameters";
      }
      uses apply-advanced;
      choice enable-disable {
        case case_1 {
          leaf disable {
            type empty;
            description
              "Disable damping";
          }
        }
      }
      leaf half-life {
        type union {
          type string {
            pattern "<.*>|$.*";
          }
          type uint32 {
            range "1 .. 45";
          }
        }
        units "minutes";
        description
          "Decay half-life";
      }
      leaf reuse {
        type union {
          type string {
            pattern "<.*>|$.*";
          }
          type uint32 {
            range "1 .. 20000";
          }
        }
        description
          "Reuse threshold (figure-of-merit value)";
      }
      leaf suppress {
        type union {
          type string {
            pattern "<.*>|$.*";
          }
          type uint32 {
            range "1 .. 20000";
          }
        }
        description
          "Cutoff threshold (figure-of-merit value)";
      }
      leaf max-suppress {
        type union {
          type string {
            pattern "<.*>|$.*";
          }
          type uint32 {
            range "1 .. 720";
          }
        }
        units "minutes";
        description
          "Maximum hold-down time";
      }
    }
    list condition {
      key "name";
      description
        "Define a route advertisement condition";
      leaf name {
        type string;
        description
          "Name to identify Condition";
      }
      uses apply-advanced;
      choice condition_type {
        case case_1;
        case case_2 {
          container if-route-exists {
            presence "enable if-route-exists";
            description
              "Route exists in a specific routing table";
            uses apply-advanced;
            container address-family {
              presence "enable address-family";
              description
                "Indicates the address family of the route to match on";
              uses apply-advanced;
              choice address-family {
                case case_1 {
                  container inet {
                    presence "enable inet";
                    description
                      "Route to match corresponds to an inet/inet6 prefix";
                    uses apply-advanced;
                    leaf address {
                      type jt:ipprefix;
                      mandatory true;
                      description
                        "Exact address of the route";
                    }
                    leaf table {
                      type string;
                      mandatory true;
                      description
                        "Routing table in which route should exist";
                    }
                  }
                }
                case case_2 {
                  container ccc {
                    presence "enable ccc";
                    description
                      "Route to match corresponds to a ccc prefix";
                    uses apply-advanced;
                    leaf address {
                      type union {
                        type jt:interface-name;
                        type string {
                          pattern "<.*>|$.*";
                        }
                      }
                      mandatory true;
                      description
                        "Logical interface used to establish ccc route";
                    }
                    leaf table {
                      type string;
                      mandatory true;
                      description
                        "Routing table in which route should exist";
                    }
                    leaf standby {
                      type empty;
                      description
                        "Indicates if route must be in standby state to be considered a match";
                    }
                    leaf peer-unit {
                      type union {
                        type string {
                          pattern "<.*>|$.*";
                        }
                        type uint32 {
                          range "0 .. 8192";
                        }
                      }
                      description
                        "Associated LT ifl's peer-unit. Required for LT-based routes";
                    }
                  }
                }
              }
            }
            leaf address {
              type jt:ipprefix;
              description
                "Exact address of the route";
            }
            leaf table {
              type string;
              description
                "Routing table in which route should exist";
            }
          }
        }
      }
    }
    list rtf-prefix-list {
      key "name";
      description
        "Define a named set of family route target prefixes";
      leaf name {
        type string;
        description
          "RTF prefix list name";
      }
      uses apply-advanced;
      list prefix-list {
        key "name";
        uses rtf_prefix_list_items;
      }
    }
    list resolution-map {
      key "name";
      ordered-by user;
      description
        "Define a set of PNH resolution modes";
      leaf name {
        type string;
        description
          "Resolution Map name";
      }
      uses apply-advanced;
      leaf-list mode {
        type enumeration {
          enum "ip-color" {
            description
              "Colored-IP PNH Resolution Mode";
          }
          enum "color-only" {
            description
              "Color-only PNH Resolution Mode";
          }
        }
        ordered-by user;
        description
          "List of resolution modes in order that defines fallback mechanism";
      }
    }
  }

  grouping as-path-calc-length-type {
    description
      "Calculated BGP AS_PATH length per BGP rules";
    leaf name {
      type union {
        type string {
          pattern "<.*>|$.*";
        }
        type uint32 {
          range "0 .. 1024";
        }
      }
      description
        "Number of ASes";
    }
    choice count-operator {
      case case_1 {
        leaf equal {
          type empty;
          description
            "Match equal values";
        }
      }
      case case_2 {
        leaf orhigher {
          type empty;
          description
            "Match higher or equal values";
        }
      }
      case case_3 {
        leaf orlower {
          type empty;
          description
            "Match lower or equal values";
        }
      }
    }
  }

  grouping as-path-unique-count-type {
    description
      "Number of unique BGP ASes excluding confederation ASes";
    leaf name {
      type union {
        type string {
          pattern "<.*>|$.*";
        }
        type uint32 {
          range "0 .. 1024";
        }
      }
      description
        "Number of ASes";
    }
    choice count-operator {
      case case_1 {
        leaf equal {
          type empty;
          description
            "Match equal values";
        }
      }
      case case_2 {
        leaf orhigher {
          type empty;
          description
            "Match higher or equal values";
        }
      }
      case case_3 {
        leaf orlower {
          type empty;
          description
            "Match lower or equal values";
        }
      }
    }
  }

  grouping community_count_type {
    description
      "Number of BGP communities";
    leaf name {
      type union {
        type string {
          pattern "<.*>|$.*";
        }
        type uint32 {
          range "0 .. 1024";
        }
      }
      description
        "Number of communities";
    }
    choice count-operator {
      case case_1 {
        leaf equal {
          type empty;
          description
            "Match equal values";
        }
      }
      case case_2 {
        leaf orhigher {
          type empty;
          description
            "Match higher or equal\tvalues";
        }
      }
      case case_3 {
        leaf orlower {
          type empty;
          description
            "Match lower or equal values";
        }
      }
    }
  }

  grouping control_as_list_type {
    leaf list-type {
      type enumeration {
        enum "as-list" {
          description
            " Type as-list";
        }
        enum "as-list-group" {
          description
            "Type as-list-group";
        }
      }
      description
        "Type as-list or as-list-group";
    }
    leaf list-name {
      type string;
      description
        "Name of as-list or as-list-group";
    }
    uses apply-advanced;
  }

  grouping control_mac_address_filter_list_type {
    leaf name {
      type string;
      description
        "Name of mac-filter-list of macs to match";
    }
    uses apply-advanced;
  }

  grouping control_prefix_list_filter_type {
    leaf list_name {
      type string;
      description
        "Name of prefix-list of routes to match";
    }
    leaf choice-ident {
      type enumeration {
        enum "exact";
        enum "longer";
        enum "orlonger";
      }
    }
    leaf choice-value {
      type string;
    }
    uses apply-advanced;
    leaf invert-match {
      type empty;
      description
        "Invert the result of the prefix-list-filter matching";
    }
    container metric {
      description
        "Metric value";
      uses apply-advanced;
      choice metric_action {
        case case_1 {
          leaf metric {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
        case case_4 {
          container igp {
            presence "enable igp";
            description
              "Track the IGP metric (BGP only)";
            leaf metric_offset {
              type union {
                type int32;
                type string {
                  pattern "<.*>|$.*";
                }
              }
              description
                "Metric offset for MED";
            }
          }
        }
        case case_5 {
          container minimum-igp {
            presence "enable minimum-igp";
            description
              "Track the minimum IGP metric (BGP only)";
            leaf metric_offset {
              type union {
                type int32;
                type string {
                  pattern "<.*>|$.*";
                }
              }
              description
                "Metric offset for MED";
            }
          }
        }
        case case_6 {
          container expression {
            description
              "Calculate value based on route metric and metric2";
            uses metric_expression_type;
          }
        }
        case case_7 {
          leaf aigp {
            type empty;
            description
              "Use aigp, if it exists, to set the IGP metric";
          }
        }
        case case_8 {
          container effective-aigp {
            presence "enable effective-aigp";
            description
              "Track the effective AIGP metric (BGP only)";
            leaf metric_offset {
              type union {
                type int32;
                type string {
                  pattern "<.*>|$.*";
                }
              }
              description
                "Metric offset for MED";
            }
          }
        }
        case case_9 {
          container minimum-effective-aigp {
            presence "enable minimum-effective-aigp";
            description
              "Track the minimum effective AIGP metric (BGP only)";
            leaf metric_offset {
              type union {
                type int32;
                type string {
                  pattern "<.*>|$.*";
                }
              }
              description
                "Metric offset for MED";
            }
          }
        }
      }
    }
    container metric2 {
      description
        "Metric value 2";
      uses apply-advanced;
      choice metric_action {
        case case_1 {
          leaf metric2 {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container metric3 {
      description
        "Metric value 3";
      uses apply-advanced;
      choice metric_action {
        case case_1 {
          leaf metric3 {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container metric4 {
      description
        "Metric value 4";
      uses apply-advanced;
      choice metric_action {
        case case_1 {
          leaf metric4 {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container tag {
      description
        "Tag string";
      uses apply-advanced;
      choice metric_action {
        case case_1 {
          leaf tag {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container tag2 {
      description
        "Tag string 2";
      uses apply-advanced;
      choice metric_action {
        case case_1 {
          leaf tag2 {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container preference {
      description
        "Preference value";
      uses apply-advanced;
      choice metric_action {
        case case_1 {
          leaf preference {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container preference2 {
      description
        "Preference value 2";
      uses apply-advanced;
      choice metric_action {
        case case_1 {
          leaf preference2 {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container color {
      description
        "Color (preference) value";
      uses apply-advanced;
      choice metric_action {
        case case_1 {
          leaf color {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container color2 {
      description
        "Color (preference) value 2";
      uses apply-advanced;
      choice metric_action {
        case case_1 {
          leaf color2 {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container local-preference {
      description
        "Local preference associated with a route";
      uses apply-advanced;
      choice metric_action {
        case case_1 {
          leaf local-preference {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container credibility {
      description
        "TED credibility value for entries from BGP-TE";
      uses apply-advanced;
      choice metric_action {
        case case_1 {
          leaf credibility {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    leaf priority {
      type enumeration {
        enum "high" {
          description
            "Set priority to high";
        }
        enum "medium" {
          description
            "Set priority to medium";
        }
        enum "low" {
          description
            "Set priority to low";
        }
      }
      description
        "Set priority for route installation";
    }
    container prefix-segment {
      description
        "Set prefix segment attributes";
      uses apply-advanced;
      list algorithm {
        key "name";
        max-elements 15;
        description
          "Set prefix segment attributes for strict/flex algorithm ";
        leaf name {
          type union {
            type string {
              pattern "<.*>|$.*";
            }
            type uint32 {
              range "1 .. 255";
            }
          }
          mandatory true;
          description
            "Set prefix segment for strict/flex algorithm";
        }
        leaf index {
          type union {
            type string {
              pattern "<.*>|$.*";
            }
            type uint32 {
              range "0 .. 1048575";
            }
          }
          mandatory true;
          description
            "Set prefix segment index id";
        }
        leaf node-segment {
          type empty;
          description
            "Set node segment flag for this prefix segment";
        }
      }
      leaf index {
        type union {
          type string {
            pattern "<.*>|$.*";
          }
          type uint32 {
            range "0 .. 1048575";
          }
        }
        description
          "Set prefix segment index id";
      }
      leaf node-segment {
        type empty;
        description
          "Set node segment flag for default prefix segment";
      }
      leaf redistribute {
        type empty;
        description
          "Redistribute prefix-segment from route entry";
      }
    }
    leaf label-allocation {
      type enumeration {
        enum "per-table" {
          description
            "Set per-table label allocation mode";
        }
        enum "per-nexthop" {
          description
            "Set per-nexthop label allocation mode";
        }
        enum "per-table-localize" {
          description
            "Set per-table-localize label allocation mode";
        }
      }
      description
        "Set label allocation mode";
    }
    container add-path {
      description
        "Set BGP add-path attributes";
      leaf send-count {
        type union {
          type string {
            pattern "<.*>|$.*";
          }
          type uint32 {
            range "2 .. 64";
          }
        }
        description
          "Number of add-paths sent";
      }
    }
    leaf fib-install-priority {
      type enumeration {
        enum "high" {
          description
            "Set Fib install priority  to high";
        }
        enum "medium" {
          description
            "Set Fib install priority to medium ";
        }
      }
      description
        "Set Fib Instalation priority of a route";
    }
    leaf validation-state {
      type enumeration {
        enum "valid" {
          description
            "Set validaton-state to valid";
        }
        enum "invalid" {
          description
            "Set validation-state to invalid";
        }
        enum "unknown" {
          description
            "Set validation-state to unknown";
        }
      }
      description
        "Set validation-state of a route";
    }
    leaf origin {
      type enumeration {
        enum "igp" {
          description
            "Path originated in the local IGP";
        }
        enum "egp" {
          description
            "Path originated in another AS";
        }
        enum "incomplete" {
          description
            "Path was learned by some other means";
        }
      }
      description
        "BGP path origin";
    }
    container srv6 {
      description
        "Configure SID with 128 bit address";
      leaf sid {
        type jt:ipv6addr;
        description
          "IPv6 Address";
      }
      leaf locator {
        type string;
        description
          "Name of locator";
      }
      choice locator_type {
        case case_1 {
          leaf micro-dt4-sid {
            type empty;
            description
              "Micro SID type dt4";
          }
        }
        case case_2 {
          leaf micro-dt6-sid {
            type empty;
            description
              "Micro SID type dt6";
          }
        }
        case case_3 {
          leaf micro-dt46-sid {
            type empty;
            description
              "Micro SID type dt46";
          }
        }
      }
    }
    container aigp-originate {
      presence "enable aigp-originate";
      description
        "Originate a BGP AIGP attribute";
      leaf distance {
        type union {
          type uint32;
          type string {
            pattern "<.*>|$.*";
          }
        }
        description
          "AIGP distance";
      }
    }
    container aigp-adjust {
      description
        "Adjust a BGP AIGP attribute";
      choice math-op {
        case case_1 {
          leaf add {
            type empty;
          }
        }
        case case_2 {
          leaf subtract {
            type empty;
          }
        }
        case case_3 {
          leaf multiply {
            type empty;
          }
        }
        case case_4 {
          leaf divide {
            type empty;
          }
        }
      }
      choice adjust-value {
        case case_1 {
          leaf user-value {
            type union {
              type uint64;
              type string {
                pattern "<.*>|$.*";
              }
            }
            description
              "Adjustment value";
          }
        }
        case case_2 {
          leaf distance-to-protocol-nexthop {
            type empty;
            description
              "Metric2";
          }
        }
      }
    }
    list community {
      key "choice-ident choice-value community-name";
      ordered-by user;
      description
        "BGP community properties associated with a route";
      leaf choice-ident {
        type enumeration {
          enum "equal-literal";
          enum "set";
          enum "plus-literal";
          enum "add";
          enum "minus-literal";
          enum "delete";
        }
      }
      leaf choice-value {
        type string;
      }
      leaf community-name {
        type string;
        description
          "Name to identify a BGP community";
      }
    }
    list tunnel-attribute {
      key "choice-ident choice-value tunnel-attribute-name";
      ordered-by user;
      description
        "BGP tunnel attribute associated with a route";
      leaf choice-ident {
        type enumeration {
          enum "set";
          enum "remove";
        }
      }
      leaf choice-value {
        type string;
      }
      leaf tunnel-attribute-name {
        type string;
        description
          "Name of a tunnel attribute , or 'all'";
      }
    }
    container assisted-replication {
      presence "enable assisted-replication";
      description
        "Deterministic AR replicator knobs";
      uses apply-advanced;
      leaf-list replicator-ip {
        type jt:ipaddr;
        max-elements 1;
        description
          "Set deterministic AR replicator ip for the flow";
      }
      leaf strict {
        type empty;
        description
          "Do not use any other replicator";
      }
      leaf-list fallback-replicator-ip {
        type jt:ipaddr;
        max-elements 1;
        description
          "Set Fallback replicator-ip";
      }
    }
    leaf damping {
      type string;
      description
        "Define BGP route flap damping parameters";
    }
    container aggregate-bandwidth {
      presence "enable aggregate-bandwidth";
      description
        "Advertise aggregate outbound link bandwidth";
      uses apply-advanced;
      choice transitive-type {
        case case_1 {
          leaf transitive {
            type empty;
            description
              "Transitive flag for link bandwidth";
          }
        }
        case case_2 {
          leaf non-transitive {
            type empty;
            description
              "Non-Transitive flag for link bandwidth";
          }
        }
      }
      leaf divide-equal {
        type empty;
        description
          "Divide-equal";
      }
    }
    container auto-link-bandwidth {
      presence "enable auto-link-bandwidth";
      description
        "Auto sense and attach link bandwidth community";
      uses apply-advanced;
      choice transitive-type {
        case case_1 {
          leaf transitive {
            type empty;
            description
              "Transitive flag for link bandwidth";
          }
        }
        case case_2 {
          leaf non-transitive {
            type empty;
            description
              "Non-Transitive flag for link bandwidth";
          }
        }
      }
    }
    leaf limit-bandwidth {
      type union {
        type uint64;
        type string {
          pattern "<.*>|$.*";
        }
      }
      description
        "Limit advertised aggregate outbound link bandwidth";
    }
    leaf no-entropy-label-capability {
      type empty;
      description
        "Don't advertise entropy label capability";
    }
    leaf as-path-prepend {
      type string;
      description
        "Prepend AS numbers to an AS path (BGP only)";
    }
    container as-path-expand {
      description
        "Prepend AS numbers prior to adding local-as (BGP only)";
      choice aspath_exp_value {
        case case_1 {
          container last-as {
            presence "enable last-as";
            description
              "Prepend last AS";
            leaf count {
              type union {
                type string {
                  pattern "<.*>|$.*";
                }
                type uint32 {
                  range "1 .. 32";
                }
              }
              description
                "Repeat count";
            }
          }
        }
        case case_2 {
          leaf aspath {
            type string;
            description
              "AS path string";
          }
        }
      }
    }
    container next-hop {
      description
        "Set the address of the next-hop router";
      choice nexthop_value {
        case case_1 {
          leaf self {
            type empty;
            description
              "Use a local address as the next-hop address";
          }
        }
        case case_2 {
          leaf peer-address {
            type empty;
            description
              "Use the remote peer address as the next-hop address";
          }
        }
        case case_3 {
          leaf address {
            type jt:ipaddr;
            description
              "Next-hop address";
          }
        }
        case case_4 {
          leaf reject {
            type empty;
            description
              "Use a reject next hop";
          }
        }
        case case_5 {
          leaf discard {
            type empty;
            description
              "Use a discard next hop";
          }
        }
        case case_6 {
          leaf next-table {
            type string;
            description
              "Perform a forwarding lookup in the specified table";
          }
        }
      }
    }
    container install-nexthop {
      description
        "Choose the next hop to be used for forwarding";
      choice strict_type {
        case case_1 {
          leaf strict {
            type empty;
            description
              "Do not use any other available next hops";
          }
        }
        case case_2 {
          leaf strict-named-lsp {
            type empty;
            description
              "Do not use any other non-lsp next hops";
          }
        }
      }
      choice nexthop-value {
        case case_1 {
          leaf-list lsp {
            type string;
            ordered-by user;
            description
              "Next-hop LSP name";
          }
        }
        case case_2 {
          leaf-list lsp-regex {
            type string;
            ordered-by user;
            description
              "Next-hop LSP name regular expression";
          }
        }
        case case_3 {
          leaf-list static-lsp {
            type string;
            ordered-by user;
            description
              "Next-hop static LSP name";
          }
        }
        case case_4 {
          leaf-list static-lsp-regex {
            type string;
            ordered-by user;
            description
              "Next-hop static LSP name regular expression";
          }
        }
        case case_5 {
          leaf non-lsp-nexthop {
            type empty;
            description
              "Next-hop with non-lsp";
          }
        }
        case case_6 {
          leaf non-labelled-nexthop {
            type empty;
            description
              "Next-hop without tag";
          }
        }
        case case_7 {
          leaf overlay-vxlan-interfaces {
            type empty;
            description
              "Next-hop for vxlan interfaces";
          }
        }
      }
      container except {
        description
          "Do not choose to install matching next hops";
        uses apply-advanced;
        choice nexthop-value {
          case case_1 {
            leaf-list lsp {
              type string;
              ordered-by user;
              description
                "Next-hop LSP name";
            }
          }
          case case_2 {
            leaf-list lsp-regex {
              type string;
              ordered-by user;
              description
                "Next-hop LSP name regular expression";
            }
          }
          case case_3 {
            leaf-list static-lsp {
              type string;
              ordered-by user;
              description
                "Next-hop static LSP name";
            }
          }
          case case_4 {
            leaf-list static-lsp-regex {
              type string;
              ordered-by user;
              description
                "Next-hop static LSP name regular expression";
            }
          }
          case case_5 {
            leaf non-lsp-nexthop {
              type empty;
              description
                "Next-hop with non-lsp";
            }
          }
          case case_6 {
            leaf non-labelled-nexthop {
              type empty;
              description
                "Next-hop without tag";
            }
          }
          case case_7 {
            leaf overlay-vxlan-interfaces {
              type empty;
              description
                "Next-hop for vxlan interfaces";
            }
          }
        }
        container fallback {
          description
            "Backup option";
          uses apply-advanced;
          choice nexthop-value {
            case case_1 {
              leaf-list lsp {
                type string;
                ordered-by user;
                description
                  "Next-hop LSP name";
              }
            }
            case case_2 {
              leaf-list lsp-regex {
                type string;
                ordered-by user;
                description
                  "Next-hop LSP name regular expression";
              }
            }
            case case_3 {
              leaf-list static-lsp {
                type string;
                ordered-by user;
                description
                  "Next-hop static LSP name";
              }
            }
            case case_4 {
              leaf-list static-lsp-regex {
                type string;
                ordered-by user;
                description
                  "Next-hop static LSP name regular expression";
              }
            }
            case case_5 {
              leaf non-lsp-nexthop {
                type empty;
                description
                  "Next-hop with non-lsp";
              }
            }
            case case_6 {
              leaf non-labelled-nexthop {
                type empty;
                description
                  "Next-hop without tag";
              }
            }
            case case_7 {
              leaf overlay-vxlan-interfaces {
                type empty;
                description
                  "Next-hop for vxlan interfaces";
              }
            }
          }
          container except {
            description
              "Do not choose to install matching next hops";
            uses apply-advanced;
            choice nexthop-value {
              case case_1 {
                leaf-list lsp {
                  type string;
                  ordered-by user;
                  description
                    "Next-hop LSP name";
                }
              }
              case case_2 {
                leaf-list lsp-regex {
                  type string;
                  ordered-by user;
                  description
                    "Next-hop LSP name regular expression";
                }
              }
              case case_3 {
                leaf-list static-lsp {
                  type string;
                  ordered-by user;
                  description
                    "Next-hop static LSP name";
                }
              }
              case case_4 {
                leaf-list static-lsp-regex {
                  type string;
                  ordered-by user;
                  description
                    "Next-hop static LSP name regular expression";
                }
              }
              case case_5 {
                leaf non-lsp-nexthop {
                  type empty;
                  description
                    "Next-hop with non-lsp";
                }
              }
              case case_6 {
                leaf non-labelled-nexthop {
                  type empty;
                  description
                    "Next-hop without tag";
                }
              }
              case case_7 {
                leaf overlay-vxlan-interfaces {
                  type empty;
                  description
                    "Next-hop for vxlan interfaces";
                }
              }
            }
          }
        }
      }
      container fallback {
        description
          "Backup option ";
        uses apply-advanced;
        choice nexthop-value {
          case case_1 {
            leaf-list lsp {
              type string;
              ordered-by user;
              description
                "Next-hop LSP name";
            }
          }
          case case_2 {
            leaf-list lsp-regex {
              type string;
              ordered-by user;
              description
                "Next-hop LSP name regular expression";
            }
          }
          case case_3 {
            leaf-list static-lsp {
              type string;
              ordered-by user;
              description
                "Next-hop static LSP name";
            }
          }
          case case_4 {
            leaf-list static-lsp-regex {
              type string;
              ordered-by user;
              description
                "Next-hop static LSP name regular expression";
            }
          }
          case case_5 {
            leaf non-lsp-nexthop {
              type empty;
              description
                "Next-hop with non-lsp";
            }
          }
          case case_6 {
            leaf non-labelled-nexthop {
              type empty;
              description
                "Next-hop without tag";
            }
          }
          case case_7 {
            leaf overlay-vxlan-interfaces {
              type empty;
              description
                "Next-hop for vxlan interfaces";
            }
          }
        }
        container except {
          description
            "Do not choose to install matching next hops";
          uses apply-advanced;
          choice nexthop-value {
            case case_1 {
              leaf-list lsp {
                type string;
                ordered-by user;
                description
                  "Next-hop LSP name";
              }
            }
            case case_2 {
              leaf-list lsp-regex {
                type string;
                ordered-by user;
                description
                  "Next-hop LSP name regular expression";
              }
            }
            case case_3 {
              leaf-list static-lsp {
                type string;
                ordered-by user;
                description
                  "Next-hop static LSP name";
              }
            }
            case case_4 {
              leaf-list static-lsp-regex {
                type string;
                ordered-by user;
                description
                  "Next-hop static LSP name regular expression";
              }
            }
            case case_5 {
              leaf non-lsp-nexthop {
                type empty;
                description
                  "Next-hop with non-lsp";
              }
            }
            case case_6 {
              leaf non-labelled-nexthop {
                type empty;
                description
                  "Next-hop without tag";
              }
            }
            case case_7 {
              leaf overlay-vxlan-interfaces {
                type empty;
                description
                  "Next-hop for vxlan interfaces";
              }
            }
          }
        }
      }
    }
    leaf trace {
      type empty;
      description
        "Log matches to a trace file";
    }
    container external {
      presence "enable external";
      description
        "External route";
      uses apply-advanced;
      leaf type {
        type union {
          type string {
            pattern "<.*>|$.*";
          }
          type int32 {
            range "1 .. 2";
          }
        }
        description
          "OSPF external metric type";
      }
      leaf nssa-only {
        type empty;
        description
          "Clear P-bit on lsa type 7";
      }
    }
    container load-balance {
      description
        "Type of load balancing in forwarding table";
      choice load_balance_type {
        case case_1 {
          leaf per-packet {
            type empty;
            description
              "Load balance on a per-packet basis deprecated, use per-flow instead";
          }
        }
        case case_2 {
          leaf per-flow {
            type empty;
            description
              "Load balance on a per-flow basis";
          }
        }
        case case_3;
        case case_4;
        case case_5;
        case case_6;
        case case_7;
        case case_8;
        case case_9;
        case case_10;
        case case_11;
      }
    }
    container advertise-locator {
      presence "enable advertise-locator";
      description
        "Advertise SRv6 Locator";
      uses apply-advanced;
      leaf internal {
        type empty;
        description
          "Advertise locator as Interal route";
      }
    }
    leaf set-down-bit {
      type empty;
      description
        "Set down bit";
    }
    leaf analyze {
      type empty;
      description
        "Send to registered controllers for analysis";
    }
    leaf destination-class {
      type string;
      description
        "Set destination class in forwarding table";
    }
    leaf source-class {
      type string;
      description
        "Set source class in forwarding table";
    }
    leaf forwarding-class {
      type string;
      description
        "Set source or destination class in forwarding table";
    }
    container map-to-interface {
      description
        "Set output logical interface";
      choice map_to_interface_value {
        case case_1 {
          leaf self {
            type empty;
            description
              "Map the interface to itself";
          }
        }
        case case_2 {
          leaf interface {
            type union {
              type jt:interface-name;
              type string {
                pattern "<.*>|$.*";
              }
            }
            description
              "Output logical interface";
          }
        }
      }
    }
    leaf-list ssm-source {
      type jt:ipaddr;
      ordered-by user;
      description
        "List of Sources for SSM mapping";
    }
    container p2mp-lsp-root {
      description
        "P2mp lsp root address";
      uses apply-advanced;
      leaf address {
        type jt:ipv4addr;
        description
          "Ipv4 root address";
      }
    }
    leaf dynamic-tunnel-attributes {
      type string;
      description
        "Choose the dynamic tunnel attributes used for forwarding";
    }
    leaf tunnel-end-point-address {
      type jt:ipaddr;
      description
        "Set tunnel end-point address of tunnel";
    }
    leaf selected-mldp-egress {
      type empty;
      description
        "This node should act as egress node for MLDP inband signalling";
    }
    leaf mhop-bfd-port {
      type empty;
      description
        "Use port number 4784 for MPLS-BFD as per RFC5884";
    }
    leaf no-backup {
      type empty;
      description
        "This prefix should not have backup";
    }
    leaf default-action {
      type enumeration {
        enum "accept" {
          description
            "Accept a route";
        }
        enum "reject" {
          description
            "Reject a route";
        }
      }
      description
        "Set default policy action";
    }
    leaf next {
      type enumeration {
        enum "policy" {
          description
            "Skip to next policy filter";
        }
        enum "term" {
          description
            "Skip to next term in a policy filter";
        }
      }
      description
        "Skip to next policy or term";
    }
    choice accept_reject {
      case case_1 {
        leaf accept {
          type empty;
          description
            "Accept a route";
        }
      }
      case case_2 {
        leaf reject {
          type empty;
          description
            "Reject a route";
        }
      }
    }
    container bgp-output-queue-priority {
      description
        "Set the BGP Update output queue priority.";
      choice class {
        case case_1 {
          leaf priority {
            type union {
              type string {
                pattern "<.*>|$.*";
              }
              type uint32 {
                range "1 .. 16";
              }
            }
            description
              "Output queue priority; higher is better";
          }
        }
        case case_2 {
          leaf expedited {
            type empty;
            description
              "Expedited queue; highest priority";
          }
        }
      }
    }
    leaf multipath-resolve {
      type empty;
      description
        "Use all paths for resolution over this prefix";
    }
    leaf source-routing-path-template {
      type string;
      description
        "Spring-te template to apply";
    }
    leaf label-allocation-fallback-reject {
      type empty;
      description
        "Suppress prefix export when label allocation fails";
    }
    leaf resolution-map {
      type string;
      description
        "Set resolution map modes";
    }
    leaf ignore-service-label {
      type empty;
      description
        "Ignore service labels";
    }
    container prefix-attribute-flags {
      presence "enable prefix-attribute-flags";
      description
        "Set ISIS prefix attribute flags sub TLV";
      uses apply-advanced;
      leaf node-segment-flag {
        type empty;
        description
          "Set node segment flag ";
      }
      leaf external-prefix-flag {
        type empty;
        description
          "Set external prefix flag ";
      }
      leaf anycast-flag {
        type empty;
        description
          "Set anycast flag ";
      }
      leaf entropy-label-capability-flag {
        type empty;
        description
          "Set entropy label capability flag ";
      }
    }
    container ipv4-source-router-id {
      presence "enable ipv4-source-router-id";
      description
        "Set IPv4 source router id in advertisement";
      uses apply-advanced;
      leaf router-id {
        type jt:ipaddr;
        description
          "Specify IPv4 address";
      }
    }
    container ipv6-source-router-id {
      presence "enable ipv6-source-router-id";
      description
        "Set IPv6 source router id in advertisement";
      uses apply-advanced;
      leaf router-id {
        type jt:ipv6addr;
        description
          "Specify IPv6 address";
      }
    }
    leaf request-long-lived-ack {
      type empty;
      description
        "Advertise route after forwarding is programmed";
    }
    leaf send-withdrawal-on-route-change {
      type empty;
      description
        "Withdraw route if change is not acked from forwarding";
    }
    container slice {
      description
        "Configure Policy Slice action";
      leaf slice-name {
        type string {
          length "1 .. 64";
        }
        description
          "Slice Name";
      }
    }
    leaf filter {
      type string;
      description
        "Set firewall-filter name";
    }
    leaf strip-as-path {
      type empty;
      description
        "Remove the incoming BGP as-path and replace with local AS";
    }
    container request-acknowledgements {
      description
        "Set request acknowledgement";
      leaf nexthop-ack {
        type empty;
        description
          "Set nexthop acknowledgement ";
      }
      leaf route-ack {
        type empty;
        description
          "Set route acknowledgement ";
      }
    }
  }

  grouping control_prefix_list_type {
    leaf name {
      type string;
      description
        "Name of prefix-list of routes to match";
    }
    uses apply-advanced;
    leaf invert-match {
      type empty;
      description
        "Invert the result of the prefix-list matching";
    }
  }

  grouping control_rib_list_type {
    leaf name {
      type string;
      description
        "Name of rib-list";
    }
    uses apply-advanced;
  }

  grouping control_route_filter_list_type {
    leaf name {
      type string;
      description
        "Name of route-filter-list of routes to match";
    }
    uses apply-advanced;
    choice modifier {
      case case_1 {
        leaf exact {
          type empty;
          description
            "Exactly match the prefix length";
        }
      }
      case case_2 {
        leaf longer {
          type empty;
          description
            "Mask is greater than the prefix length";
        }
      }
      case case_3 {
        leaf orlonger {
          type empty;
          description
            "Mask is greater than or equal to the prefix length";
        }
      }
      case case_4 {
        leaf upto {
          type string;
          description
            "Mask falls between two prefix lengths";
        }
      }
      case case_5 {
        leaf prefix-length-range {
          type string;
          description
            "Mask falls between two prefix lengths";
        }
      }
    }
    leaf invert-match {
      type empty;
      description
        "Invert the result of the route-filter-list matching";
    }
    container metric {
      description
        "Metric value";
      uses apply-advanced;
      choice metric_action {
        case case_1 {
          leaf metric {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
        case case_4 {
          container igp {
            presence "enable igp";
            description
              "Track the IGP metric (BGP only)";
            leaf metric_offset {
              type union {
                type int32;
                type string {
                  pattern "<.*>|$.*";
                }
              }
              description
                "Metric offset for MED";
            }
          }
        }
        case case_5 {
          container minimum-igp {
            presence "enable minimum-igp";
            description
              "Track the minimum IGP metric (BGP only)";
            leaf metric_offset {
              type union {
                type int32;
                type string {
                  pattern "<.*>|$.*";
                }
              }
              description
                "Metric offset for MED";
            }
          }
        }
        case case_6 {
          container expression {
            description
              "Calculate value based on route metric and metric2";
            uses metric_expression_type;
          }
        }
        case case_7 {
          leaf aigp {
            type empty;
            description
              "Use aigp, if it exists, to set the IGP metric";
          }
        }
        case case_8 {
          container effective-aigp {
            presence "enable effective-aigp";
            description
              "Track the effective AIGP metric (BGP only)";
            leaf metric_offset {
              type union {
                type int32;
                type string {
                  pattern "<.*>|$.*";
                }
              }
              description
                "Metric offset for MED";
            }
          }
        }
        case case_9 {
          container minimum-effective-aigp {
            presence "enable minimum-effective-aigp";
            description
              "Track the minimum effective AIGP metric (BGP only)";
            leaf metric_offset {
              type union {
                type int32;
                type string {
                  pattern "<.*>|$.*";
                }
              }
              description
                "Metric offset for MED";
            }
          }
        }
      }
    }
    container metric2 {
      description
        "Metric value 2";
      uses apply-advanced;
      choice metric_action {
        case case_1 {
          leaf metric2 {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container metric3 {
      description
        "Metric value 3";
      uses apply-advanced;
      choice metric_action {
        case case_1 {
          leaf metric3 {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container metric4 {
      description
        "Metric value 4";
      uses apply-advanced;
      choice metric_action {
        case case_1 {
          leaf metric4 {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container tag {
      description
        "Tag string";
      uses apply-advanced;
      choice metric_action {
        case case_1 {
          leaf tag {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container tag2 {
      description
        "Tag string 2";
      uses apply-advanced;
      choice metric_action {
        case case_1 {
          leaf tag2 {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container preference {
      description
        "Preference value";
      uses apply-advanced;
      choice metric_action {
        case case_1 {
          leaf preference {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container preference2 {
      description
        "Preference value 2";
      uses apply-advanced;
      choice metric_action {
        case case_1 {
          leaf preference2 {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container color {
      description
        "Color (preference) value";
      uses apply-advanced;
      choice metric_action {
        case case_1 {
          leaf color {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container color2 {
      description
        "Color (preference) value 2";
      uses apply-advanced;
      choice metric_action {
        case case_1 {
          leaf color2 {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container local-preference {
      description
        "Local preference associated with a route";
      uses apply-advanced;
      choice metric_action {
        case case_1 {
          leaf local-preference {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container credibility {
      description
        "TED credibility value for entries from BGP-TE";
      uses apply-advanced;
      choice metric_action {
        case case_1 {
          leaf credibility {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    leaf priority {
      type enumeration {
        enum "high" {
          description
            "Set priority to high";
        }
        enum "medium" {
          description
            "Set priority to medium";
        }
        enum "low" {
          description
            "Set priority to low";
        }
      }
      description
        "Set priority for route installation";
    }
    container prefix-segment {
      description
        "Set prefix segment attributes";
      uses apply-advanced;
      list algorithm {
        key "name";
        max-elements 15;
        description
          "Set prefix segment attributes for strict/flex algorithm ";
        leaf name {
          type union {
            type string {
              pattern "<.*>|$.*";
            }
            type uint32 {
              range "1 .. 255";
            }
          }
          mandatory true;
          description
            "Set prefix segment for strict/flex algorithm";
        }
        leaf index {
          type union {
            type string {
              pattern "<.*>|$.*";
            }
            type uint32 {
              range "0 .. 1048575";
            }
          }
          mandatory true;
          description
            "Set prefix segment index id";
        }
        leaf node-segment {
          type empty;
          description
            "Set node segment flag for this prefix segment";
        }
      }
      leaf index {
        type union {
          type string {
            pattern "<.*>|$.*";
          }
          type uint32 {
            range "0 .. 1048575";
          }
        }
        description
          "Set prefix segment index id";
      }
      leaf node-segment {
        type empty;
        description
          "Set node segment flag for default prefix segment";
      }
      leaf redistribute {
        type empty;
        description
          "Redistribute prefix-segment from route entry";
      }
    }
    leaf label-allocation {
      type enumeration {
        enum "per-table" {
          description
            "Set per-table label allocation mode";
        }
        enum "per-nexthop" {
          description
            "Set per-nexthop label allocation mode";
        }
        enum "per-table-localize" {
          description
            "Set per-table-localize label allocation mode";
        }
      }
      description
        "Set label allocation mode";
    }
    container add-path {
      description
        "Set BGP add-path attributes";
      leaf send-count {
        type union {
          type string {
            pattern "<.*>|$.*";
          }
          type uint32 {
            range "2 .. 64";
          }
        }
        description
          "Number of add-paths sent";
      }
    }
    leaf fib-install-priority {
      type enumeration {
        enum "high" {
          description
            "Set Fib install priority  to high";
        }
        enum "medium" {
          description
            "Set Fib install priority to medium ";
        }
      }
      description
        "Set Fib Instalation priority of a route";
    }
    leaf validation-state {
      type enumeration {
        enum "valid" {
          description
            "Set validaton-state to valid";
        }
        enum "invalid" {
          description
            "Set validation-state to invalid";
        }
        enum "unknown" {
          description
            "Set validation-state to unknown";
        }
      }
      description
        "Set validation-state of a route";
    }
    leaf origin {
      type enumeration {
        enum "igp" {
          description
            "Path originated in the local IGP";
        }
        enum "egp" {
          description
            "Path originated in another AS";
        }
        enum "incomplete" {
          description
            "Path was learned by some other means";
        }
      }
      description
        "BGP path origin";
    }
    container srv6 {
      description
        "Configure SID with 128 bit address";
      leaf sid {
        type jt:ipv6addr;
        description
          "IPv6 Address";
      }
      leaf locator {
        type string;
        description
          "Name of locator";
      }
      choice locator_type {
        case case_1 {
          leaf micro-dt4-sid {
            type empty;
            description
              "Micro SID type dt4";
          }
        }
        case case_2 {
          leaf micro-dt6-sid {
            type empty;
            description
              "Micro SID type dt6";
          }
        }
        case case_3 {
          leaf micro-dt46-sid {
            type empty;
            description
              "Micro SID type dt46";
          }
        }
      }
    }
    container aigp-originate {
      presence "enable aigp-originate";
      description
        "Originate a BGP AIGP attribute";
      leaf distance {
        type union {
          type uint32;
          type string {
            pattern "<.*>|$.*";
          }
        }
        description
          "AIGP distance";
      }
    }
    container aigp-adjust {
      description
        "Adjust a BGP AIGP attribute";
      choice math-op {
        case case_1 {
          leaf add {
            type empty;
          }
        }
        case case_2 {
          leaf subtract {
            type empty;
          }
        }
        case case_3 {
          leaf multiply {
            type empty;
          }
        }
        case case_4 {
          leaf divide {
            type empty;
          }
        }
      }
      choice adjust-value {
        case case_1 {
          leaf user-value {
            type union {
              type uint64;
              type string {
                pattern "<.*>|$.*";
              }
            }
            description
              "Adjustment value";
          }
        }
        case case_2 {
          leaf distance-to-protocol-nexthop {
            type empty;
            description
              "Metric2";
          }
        }
      }
    }
    list community {
      key "choice-ident choice-value community-name";
      ordered-by user;
      description
        "BGP community properties associated with a route";
      leaf choice-ident {
        type enumeration {
          enum "equal-literal";
          enum "set";
          enum "plus-literal";
          enum "add";
          enum "minus-literal";
          enum "delete";
        }
      }
      leaf choice-value {
        type string;
      }
      leaf community-name {
        type string;
        description
          "Name to identify a BGP community";
      }
    }
    list tunnel-attribute {
      key "choice-ident choice-value tunnel-attribute-name";
      ordered-by user;
      description
        "BGP tunnel attribute associated with a route";
      leaf choice-ident {
        type enumeration {
          enum "set";
          enum "remove";
        }
      }
      leaf choice-value {
        type string;
      }
      leaf tunnel-attribute-name {
        type string;
        description
          "Name of a tunnel attribute , or 'all'";
      }
    }
    container assisted-replication {
      presence "enable assisted-replication";
      description
        "Deterministic AR replicator knobs";
      uses apply-advanced;
      leaf-list replicator-ip {
        type jt:ipaddr;
        max-elements 1;
        description
          "Set deterministic AR replicator ip for the flow";
      }
      leaf strict {
        type empty;
        description
          "Do not use any other replicator";
      }
      leaf-list fallback-replicator-ip {
        type jt:ipaddr;
        max-elements 1;
        description
          "Set Fallback replicator-ip";
      }
    }
    leaf damping {
      type string;
      description
        "Define BGP route flap damping parameters";
    }
    container aggregate-bandwidth {
      presence "enable aggregate-bandwidth";
      description
        "Advertise aggregate outbound link bandwidth";
      uses apply-advanced;
      choice transitive-type {
        case case_1 {
          leaf transitive {
            type empty;
            description
              "Transitive flag for link bandwidth";
          }
        }
        case case_2 {
          leaf non-transitive {
            type empty;
            description
              "Non-Transitive flag for link bandwidth";
          }
        }
      }
      leaf divide-equal {
        type empty;
        description
          "Divide-equal";
      }
    }
    container auto-link-bandwidth {
      presence "enable auto-link-bandwidth";
      description
        "Auto sense and attach link bandwidth community";
      uses apply-advanced;
      choice transitive-type {
        case case_1 {
          leaf transitive {
            type empty;
            description
              "Transitive flag for link bandwidth";
          }
        }
        case case_2 {
          leaf non-transitive {
            type empty;
            description
              "Non-Transitive flag for link bandwidth";
          }
        }
      }
    }
    leaf limit-bandwidth {
      type union {
        type uint64;
        type string {
          pattern "<.*>|$.*";
        }
      }
      description
        "Limit advertised aggregate outbound link bandwidth";
    }
    leaf no-entropy-label-capability {
      type empty;
      description
        "Don't advertise entropy label capability";
    }
    leaf as-path-prepend {
      type string;
      description
        "Prepend AS numbers to an AS path (BGP only)";
    }
    container as-path-expand {
      description
        "Prepend AS numbers prior to adding local-as (BGP only)";
      choice aspath_exp_value {
        case case_1 {
          container last-as {
            presence "enable last-as";
            description
              "Prepend last AS";
            leaf count {
              type union {
                type string {
                  pattern "<.*>|$.*";
                }
                type uint32 {
                  range "1 .. 32";
                }
              }
              description
                "Repeat count";
            }
          }
        }
        case case_2 {
          leaf aspath {
            type string;
            description
              "AS path string";
          }
        }
      }
    }
    container next-hop {
      description
        "Set the address of the next-hop router";
      choice nexthop_value {
        case case_1 {
          leaf self {
            type empty;
            description
              "Use a local address as the next-hop address";
          }
        }
        case case_2 {
          leaf peer-address {
            type empty;
            description
              "Use the remote peer address as the next-hop address";
          }
        }
        case case_3 {
          leaf address {
            type jt:ipaddr;
            description
              "Next-hop address";
          }
        }
        case case_4 {
          leaf reject {
            type empty;
            description
              "Use a reject next hop";
          }
        }
        case case_5 {
          leaf discard {
            type empty;
            description
              "Use a discard next hop";
          }
        }
        case case_6 {
          leaf next-table {
            type string;
            description
              "Perform a forwarding lookup in the specified table";
          }
        }
      }
    }
    container install-nexthop {
      description
        "Choose the next hop to be used for forwarding";
      choice strict_type {
        case case_1 {
          leaf strict {
            type empty;
            description
              "Do not use any other available next hops";
          }
        }
        case case_2 {
          leaf strict-named-lsp {
            type empty;
            description
              "Do not use any other non-lsp next hops";
          }
        }
      }
      choice nexthop-value {
        case case_1 {
          leaf-list lsp {
            type string;
            ordered-by user;
            description
              "Next-hop LSP name";
          }
        }
        case case_2 {
          leaf-list lsp-regex {
            type string;
            ordered-by user;
            description
              "Next-hop LSP name regular expression";
          }
        }
        case case_3 {
          leaf-list static-lsp {
            type string;
            ordered-by user;
            description
              "Next-hop static LSP name";
          }
        }
        case case_4 {
          leaf-list static-lsp-regex {
            type string;
            ordered-by user;
            description
              "Next-hop static LSP name regular expression";
          }
        }
        case case_5 {
          leaf non-lsp-nexthop {
            type empty;
            description
              "Next-hop with non-lsp";
          }
        }
        case case_6 {
          leaf non-labelled-nexthop {
            type empty;
            description
              "Next-hop without tag";
          }
        }
        case case_7 {
          leaf overlay-vxlan-interfaces {
            type empty;
            description
              "Next-hop for vxlan interfaces";
          }
        }
      }
      container except {
        description
          "Do not choose to install matching next hops";
        uses apply-advanced;
        choice nexthop-value {
          case case_1 {
            leaf-list lsp {
              type string;
              ordered-by user;
              description
                "Next-hop LSP name";
            }
          }
          case case_2 {
            leaf-list lsp-regex {
              type string;
              ordered-by user;
              description
                "Next-hop LSP name regular expression";
            }
          }
          case case_3 {
            leaf-list static-lsp {
              type string;
              ordered-by user;
              description
                "Next-hop static LSP name";
            }
          }
          case case_4 {
            leaf-list static-lsp-regex {
              type string;
              ordered-by user;
              description
                "Next-hop static LSP name regular expression";
            }
          }
          case case_5 {
            leaf non-lsp-nexthop {
              type empty;
              description
                "Next-hop with non-lsp";
            }
          }
          case case_6 {
            leaf non-labelled-nexthop {
              type empty;
              description
                "Next-hop without tag";
            }
          }
          case case_7 {
            leaf overlay-vxlan-interfaces {
              type empty;
              description
                "Next-hop for vxlan interfaces";
            }
          }
        }
        container fallback {
          description
            "Backup option";
          uses apply-advanced;
          choice nexthop-value {
            case case_1 {
              leaf-list lsp {
                type string;
                ordered-by user;
                description
                  "Next-hop LSP name";
              }
            }
            case case_2 {
              leaf-list lsp-regex {
                type string;
                ordered-by user;
                description
                  "Next-hop LSP name regular expression";
              }
            }
            case case_3 {
              leaf-list static-lsp {
                type string;
                ordered-by user;
                description
                  "Next-hop static LSP name";
              }
            }
            case case_4 {
              leaf-list static-lsp-regex {
                type string;
                ordered-by user;
                description
                  "Next-hop static LSP name regular expression";
              }
            }
            case case_5 {
              leaf non-lsp-nexthop {
                type empty;
                description
                  "Next-hop with non-lsp";
              }
            }
            case case_6 {
              leaf non-labelled-nexthop {
                type empty;
                description
                  "Next-hop without tag";
              }
            }
            case case_7 {
              leaf overlay-vxlan-interfaces {
                type empty;
                description
                  "Next-hop for vxlan interfaces";
              }
            }
          }
          container except {
            description
              "Do not choose to install matching next hops";
            uses apply-advanced;
            choice nexthop-value {
              case case_1 {
                leaf-list lsp {
                  type string;
                  ordered-by user;
                  description
                    "Next-hop LSP name";
                }
              }
              case case_2 {
                leaf-list lsp-regex {
                  type string;
                  ordered-by user;
                  description
                    "Next-hop LSP name regular expression";
                }
              }
              case case_3 {
                leaf-list static-lsp {
                  type string;
                  ordered-by user;
                  description
                    "Next-hop static LSP name";
                }
              }
              case case_4 {
                leaf-list static-lsp-regex {
                  type string;
                  ordered-by user;
                  description
                    "Next-hop static LSP name regular expression";
                }
              }
              case case_5 {
                leaf non-lsp-nexthop {
                  type empty;
                  description
                    "Next-hop with non-lsp";
                }
              }
              case case_6 {
                leaf non-labelled-nexthop {
                  type empty;
                  description
                    "Next-hop without tag";
                }
              }
              case case_7 {
                leaf overlay-vxlan-interfaces {
                  type empty;
                  description
                    "Next-hop for vxlan interfaces";
                }
              }
            }
          }
        }
      }
      container fallback {
        description
          "Backup option ";
        uses apply-advanced;
        choice nexthop-value {
          case case_1 {
            leaf-list lsp {
              type string;
              ordered-by user;
              description
                "Next-hop LSP name";
            }
          }
          case case_2 {
            leaf-list lsp-regex {
              type string;
              ordered-by user;
              description
                "Next-hop LSP name regular expression";
            }
          }
          case case_3 {
            leaf-list static-lsp {
              type string;
              ordered-by user;
              description
                "Next-hop static LSP name";
            }
          }
          case case_4 {
            leaf-list static-lsp-regex {
              type string;
              ordered-by user;
              description
                "Next-hop static LSP name regular expression";
            }
          }
          case case_5 {
            leaf non-lsp-nexthop {
              type empty;
              description
                "Next-hop with non-lsp";
            }
          }
          case case_6 {
            leaf non-labelled-nexthop {
              type empty;
              description
                "Next-hop without tag";
            }
          }
          case case_7 {
            leaf overlay-vxlan-interfaces {
              type empty;
              description
                "Next-hop for vxlan interfaces";
            }
          }
        }
        container except {
          description
            "Do not choose to install matching next hops";
          uses apply-advanced;
          choice nexthop-value {
            case case_1 {
              leaf-list lsp {
                type string;
                ordered-by user;
                description
                  "Next-hop LSP name";
              }
            }
            case case_2 {
              leaf-list lsp-regex {
                type string;
                ordered-by user;
                description
                  "Next-hop LSP name regular expression";
              }
            }
            case case_3 {
              leaf-list static-lsp {
                type string;
                ordered-by user;
                description
                  "Next-hop static LSP name";
              }
            }
            case case_4 {
              leaf-list static-lsp-regex {
                type string;
                ordered-by user;
                description
                  "Next-hop static LSP name regular expression";
              }
            }
            case case_5 {
              leaf non-lsp-nexthop {
                type empty;
                description
                  "Next-hop with non-lsp";
              }
            }
            case case_6 {
              leaf non-labelled-nexthop {
                type empty;
                description
                  "Next-hop without tag";
              }
            }
            case case_7 {
              leaf overlay-vxlan-interfaces {
                type empty;
                description
                  "Next-hop for vxlan interfaces";
              }
            }
          }
        }
      }
    }
    leaf trace {
      type empty;
      description
        "Log matches to a trace file";
    }
    container external {
      presence "enable external";
      description
        "External route";
      uses apply-advanced;
      leaf type {
        type union {
          type string {
            pattern "<.*>|$.*";
          }
          type int32 {
            range "1 .. 2";
          }
        }
        description
          "OSPF external metric type";
      }
      leaf nssa-only {
        type empty;
        description
          "Clear P-bit on lsa type 7";
      }
    }
    container load-balance {
      description
        "Type of load balancing in forwarding table";
      choice load_balance_type {
        case case_1 {
          leaf per-packet {
            type empty;
            description
              "Load balance on a per-packet basis deprecated, use per-flow instead";
          }
        }
        case case_2 {
          leaf per-flow {
            type empty;
            description
              "Load balance on a per-flow basis";
          }
        }
        case case_3;
        case case_4;
        case case_5;
        case case_6;
        case case_7;
        case case_8;
        case case_9;
        case case_10;
        case case_11;
      }
    }
    container advertise-locator {
      presence "enable advertise-locator";
      description
        "Advertise SRv6 Locator";
      uses apply-advanced;
      leaf internal {
        type empty;
        description
          "Advertise locator as Interal route";
      }
    }
    leaf set-down-bit {
      type empty;
      description
        "Set down bit";
    }
    leaf analyze {
      type empty;
      description
        "Send to registered controllers for analysis";
    }
    leaf destination-class {
      type string;
      description
        "Set destination class in forwarding table";
    }
    leaf source-class {
      type string;
      description
        "Set source class in forwarding table";
    }
    leaf forwarding-class {
      type string;
      description
        "Set source or destination class in forwarding table";
    }
    container map-to-interface {
      description
        "Set output logical interface";
      choice map_to_interface_value {
        case case_1 {
          leaf self {
            type empty;
            description
              "Map the interface to itself";
          }
        }
        case case_2 {
          leaf interface {
            type union {
              type jt:interface-name;
              type string {
                pattern "<.*>|$.*";
              }
            }
            description
              "Output logical interface";
          }
        }
      }
    }
    leaf-list ssm-source {
      type jt:ipaddr;
      ordered-by user;
      description
        "List of Sources for SSM mapping";
    }
    container p2mp-lsp-root {
      description
        "P2mp lsp root address";
      uses apply-advanced;
      leaf address {
        type jt:ipv4addr;
        description
          "Ipv4 root address";
      }
    }
    leaf dynamic-tunnel-attributes {
      type string;
      description
        "Choose the dynamic tunnel attributes used for forwarding";
    }
    leaf tunnel-end-point-address {
      type jt:ipaddr;
      description
        "Set tunnel end-point address of tunnel";
    }
    leaf selected-mldp-egress {
      type empty;
      description
        "This node should act as egress node for MLDP inband signalling";
    }
    leaf mhop-bfd-port {
      type empty;
      description
        "Use port number 4784 for MPLS-BFD as per RFC5884";
    }
    leaf no-backup {
      type empty;
      description
        "This prefix should not have backup";
    }
    leaf default-action {
      type enumeration {
        enum "accept" {
          description
            "Accept a route";
        }
        enum "reject" {
          description
            "Reject a route";
        }
      }
      description
        "Set default policy action";
    }
    leaf next {
      type enumeration {
        enum "policy" {
          description
            "Skip to next policy filter";
        }
        enum "term" {
          description
            "Skip to next term in a policy filter";
        }
      }
      description
        "Skip to next policy or term";
    }
    choice accept_reject {
      case case_1 {
        leaf accept {
          type empty;
          description
            "Accept a route";
        }
      }
      case case_2 {
        leaf reject {
          type empty;
          description
            "Reject a route";
        }
      }
    }
    container bgp-output-queue-priority {
      description
        "Set the BGP Update output queue priority.";
      choice class {
        case case_1 {
          leaf priority {
            type union {
              type string {
                pattern "<.*>|$.*";
              }
              type uint32 {
                range "1 .. 16";
              }
            }
            description
              "Output queue priority; higher is better";
          }
        }
        case case_2 {
          leaf expedited {
            type empty;
            description
              "Expedited queue; highest priority";
          }
        }
      }
    }
    leaf multipath-resolve {
      type empty;
      description
        "Use all paths for resolution over this prefix";
    }
    leaf source-routing-path-template {
      type string;
      description
        "Spring-te template to apply";
    }
    leaf label-allocation-fallback-reject {
      type empty;
      description
        "Suppress prefix export when label allocation fails";
    }
    leaf resolution-map {
      type string;
      description
        "Set resolution map modes";
    }
    leaf ignore-service-label {
      type empty;
      description
        "Ignore service labels";
    }
    container prefix-attribute-flags {
      presence "enable prefix-attribute-flags";
      description
        "Set ISIS prefix attribute flags sub TLV";
      uses apply-advanced;
      leaf node-segment-flag {
        type empty;
        description
          "Set node segment flag ";
      }
      leaf external-prefix-flag {
        type empty;
        description
          "Set external prefix flag ";
      }
      leaf anycast-flag {
        type empty;
        description
          "Set anycast flag ";
      }
      leaf entropy-label-capability-flag {
        type empty;
        description
          "Set entropy label capability flag ";
      }
    }
    container ipv4-source-router-id {
      presence "enable ipv4-source-router-id";
      description
        "Set IPv4 source router id in advertisement";
      uses apply-advanced;
      leaf router-id {
        type jt:ipaddr;
        description
          "Specify IPv4 address";
      }
    }
    container ipv6-source-router-id {
      presence "enable ipv6-source-router-id";
      description
        "Set IPv6 source router id in advertisement";
      uses apply-advanced;
      leaf router-id {
        type jt:ipv6addr;
        description
          "Specify IPv6 address";
      }
    }
    leaf request-long-lived-ack {
      type empty;
      description
        "Advertise route after forwarding is programmed";
    }
    leaf send-withdrawal-on-route-change {
      type empty;
      description
        "Withdraw route if change is not acked from forwarding";
    }
    container slice {
      description
        "Configure Policy Slice action";
      leaf slice-name {
        type string {
          length "1 .. 64";
        }
        description
          "Slice Name";
      }
    }
    leaf filter {
      type string;
      description
        "Set firewall-filter name";
    }
    leaf strip-as-path {
      type empty;
      description
        "Remove the incoming BGP as-path and replace with local AS";
    }
    container request-acknowledgements {
      description
        "Set request acknowledgement";
      leaf nexthop-ack {
        type empty;
        description
          "Set nexthop acknowledgement ";
      }
      leaf route-ack {
        type empty;
        description
          "Set route acknowledgement ";
      }
    }
  }

  grouping control_route_filter_type {
    leaf address {
      type jt:ipprefix;
      description
        "IP address or hostname";
    }
    leaf choice-ident {
      type enumeration {
        enum "exact";
        enum "longer";
        enum "orlonger";
        enum "upto";
        enum "through";
        enum "prefix-length-range";
        enum "address-mask";
      }
    }
    leaf choice-value {
      type string;
    }
    uses apply-advanced;
    container label {
      description
        "Set label for BGP LU label allocation";
      choice label_value {
        case case_1 {
          container range {
            description
              "Label range";
            choice range_value {
              case case_1 {
                leaf range {
                  type string;
                  description
                    "Label range in <start>:<end> format";
                }
              }
            }
          }
        }
        case case_2 {
          leaf label {
            type union {
              type string {
                pattern "<.*>|$.*";
              }
              type uint32 {
                range "0 .. 1048575";
              }
            }
            description
              "Label value";
          }
        }
      }
    }
    leaf get-route-range {
      type empty;
      description
        "Get the range";
    }
    container metric {
      description
        "Metric value";
      uses apply-advanced;
      choice metric_action {
        case case_1 {
          leaf metric {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
        case case_4 {
          container igp {
            presence "enable igp";
            description
              "Track the IGP metric (BGP only)";
            leaf metric_offset {
              type union {
                type int32;
                type string {
                  pattern "<.*>|$.*";
                }
              }
              description
                "Metric offset for MED";
            }
          }
        }
        case case_5 {
          container minimum-igp {
            presence "enable minimum-igp";
            description
              "Track the minimum IGP metric (BGP only)";
            leaf metric_offset {
              type union {
                type int32;
                type string {
                  pattern "<.*>|$.*";
                }
              }
              description
                "Metric offset for MED";
            }
          }
        }
        case case_6 {
          container expression {
            description
              "Calculate value based on route metric and metric2";
            uses metric_expression_type;
          }
        }
        case case_7 {
          leaf aigp {
            type empty;
            description
              "Use aigp, if it exists, to set the IGP metric";
          }
        }
        case case_8 {
          container effective-aigp {
            presence "enable effective-aigp";
            description
              "Track the effective AIGP metric (BGP only)";
            leaf metric_offset {
              type union {
                type int32;
                type string {
                  pattern "<.*>|$.*";
                }
              }
              description
                "Metric offset for MED";
            }
          }
        }
        case case_9 {
          container minimum-effective-aigp {
            presence "enable minimum-effective-aigp";
            description
              "Track the minimum effective AIGP metric (BGP only)";
            leaf metric_offset {
              type union {
                type int32;
                type string {
                  pattern "<.*>|$.*";
                }
              }
              description
                "Metric offset for MED";
            }
          }
        }
      }
    }
    container metric2 {
      description
        "Metric value 2";
      uses apply-advanced;
      choice metric_action {
        case case_1 {
          leaf metric2 {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container metric3 {
      description
        "Metric value 3";
      uses apply-advanced;
      choice metric_action {
        case case_1 {
          leaf metric3 {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container metric4 {
      description
        "Metric value 4";
      uses apply-advanced;
      choice metric_action {
        case case_1 {
          leaf metric4 {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container tag {
      description
        "Tag string";
      uses apply-advanced;
      choice metric_action {
        case case_1 {
          leaf tag {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container tag2 {
      description
        "Tag string 2";
      uses apply-advanced;
      choice metric_action {
        case case_1 {
          leaf tag2 {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container preference {
      description
        "Preference value";
      uses apply-advanced;
      choice metric_action {
        case case_1 {
          leaf preference {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container preference2 {
      description
        "Preference value 2";
      uses apply-advanced;
      choice metric_action {
        case case_1 {
          leaf preference2 {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container color {
      description
        "Color (preference) value";
      uses apply-advanced;
      choice metric_action {
        case case_1 {
          leaf color {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container color2 {
      description
        "Color (preference) value 2";
      uses apply-advanced;
      choice metric_action {
        case case_1 {
          leaf color2 {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container local-preference {
      description
        "Local preference associated with a route";
      uses apply-advanced;
      choice metric_action {
        case case_1 {
          leaf local-preference {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container credibility {
      description
        "TED credibility value for entries from BGP-TE";
      uses apply-advanced;
      choice metric_action {
        case case_1 {
          leaf credibility {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    leaf priority {
      type enumeration {
        enum "high" {
          description
            "Set priority to high";
        }
        enum "medium" {
          description
            "Set priority to medium";
        }
        enum "low" {
          description
            "Set priority to low";
        }
      }
      description
        "Set priority for route installation";
    }
    container prefix-segment {
      description
        "Set prefix segment attributes";
      uses apply-advanced;
      list algorithm {
        key "name";
        max-elements 15;
        description
          "Set prefix segment attributes for strict/flex algorithm ";
        leaf name {
          type union {
            type string {
              pattern "<.*>|$.*";
            }
            type uint32 {
              range "1 .. 255";
            }
          }
          mandatory true;
          description
            "Set prefix segment for strict/flex algorithm";
        }
        leaf index {
          type union {
            type string {
              pattern "<.*>|$.*";
            }
            type uint32 {
              range "0 .. 1048575";
            }
          }
          mandatory true;
          description
            "Set prefix segment index id";
        }
        leaf node-segment {
          type empty;
          description
            "Set node segment flag for this prefix segment";
        }
      }
      leaf index {
        type union {
          type string {
            pattern "<.*>|$.*";
          }
          type uint32 {
            range "0 .. 1048575";
          }
        }
        description
          "Set prefix segment index id";
      }
      leaf node-segment {
        type empty;
        description
          "Set node segment flag for default prefix segment";
      }
      leaf redistribute {
        type empty;
        description
          "Redistribute prefix-segment from route entry";
      }
    }
    leaf label-allocation {
      type enumeration {
        enum "per-table" {
          description
            "Set per-table label allocation mode";
        }
        enum "per-nexthop" {
          description
            "Set per-nexthop label allocation mode";
        }
        enum "per-table-localize" {
          description
            "Set per-table-localize label allocation mode";
        }
      }
      description
        "Set label allocation mode";
    }
    container add-path {
      description
        "Set BGP add-path attributes";
      leaf send-count {
        type union {
          type string {
            pattern "<.*>|$.*";
          }
          type uint32 {
            range "2 .. 64";
          }
        }
        description
          "Number of add-paths sent";
      }
    }
    leaf fib-install-priority {
      type enumeration {
        enum "high" {
          description
            "Set Fib install priority  to high";
        }
        enum "medium" {
          description
            "Set Fib install priority to medium ";
        }
      }
      description
        "Set Fib Instalation priority of a route";
    }
    leaf validation-state {
      type enumeration {
        enum "valid" {
          description
            "Set validaton-state to valid";
        }
        enum "invalid" {
          description
            "Set validation-state to invalid";
        }
        enum "unknown" {
          description
            "Set validation-state to unknown";
        }
      }
      description
        "Set validation-state of a route";
    }
    leaf origin {
      type enumeration {
        enum "igp" {
          description
            "Path originated in the local IGP";
        }
        enum "egp" {
          description
            "Path originated in another AS";
        }
        enum "incomplete" {
          description
            "Path was learned by some other means";
        }
      }
      description
        "BGP path origin";
    }
    container srv6 {
      description
        "Configure SID with 128 bit address";
      leaf sid {
        type jt:ipv6addr;
        description
          "IPv6 Address";
      }
      leaf locator {
        type string;
        description
          "Name of locator";
      }
      choice locator_type {
        case case_1 {
          leaf micro-dt4-sid {
            type empty;
            description
              "Micro SID type dt4";
          }
        }
        case case_2 {
          leaf micro-dt6-sid {
            type empty;
            description
              "Micro SID type dt6";
          }
        }
        case case_3 {
          leaf micro-dt46-sid {
            type empty;
            description
              "Micro SID type dt46";
          }
        }
      }
    }
    container aigp-originate {
      presence "enable aigp-originate";
      description
        "Originate a BGP AIGP attribute";
      leaf distance {
        type union {
          type uint32;
          type string {
            pattern "<.*>|$.*";
          }
        }
        description
          "AIGP distance";
      }
    }
    container aigp-adjust {
      description
        "Adjust a BGP AIGP attribute";
      choice math-op {
        case case_1 {
          leaf add {
            type empty;
          }
        }
        case case_2 {
          leaf subtract {
            type empty;
          }
        }
        case case_3 {
          leaf multiply {
            type empty;
          }
        }
        case case_4 {
          leaf divide {
            type empty;
          }
        }
      }
      choice adjust-value {
        case case_1 {
          leaf user-value {
            type union {
              type uint64;
              type string {
                pattern "<.*>|$.*";
              }
            }
            description
              "Adjustment value";
          }
        }
        case case_2 {
          leaf distance-to-protocol-nexthop {
            type empty;
            description
              "Metric2";
          }
        }
      }
    }
    list community {
      key "choice-ident choice-value community-name";
      ordered-by user;
      description
        "BGP community properties associated with a route";
      leaf choice-ident {
        type enumeration {
          enum "equal-literal";
          enum "set";
          enum "plus-literal";
          enum "add";
          enum "minus-literal";
          enum "delete";
        }
      }
      leaf choice-value {
        type string;
      }
      leaf community-name {
        type string;
        description
          "Name to identify a BGP community";
      }
    }
    list tunnel-attribute {
      key "choice-ident choice-value tunnel-attribute-name";
      ordered-by user;
      description
        "BGP tunnel attribute associated with a route";
      leaf choice-ident {
        type enumeration {
          enum "set";
          enum "remove";
        }
      }
      leaf choice-value {
        type string;
      }
      leaf tunnel-attribute-name {
        type string;
        description
          "Name of a tunnel attribute , or 'all'";
      }
    }
    container assisted-replication {
      presence "enable assisted-replication";
      description
        "Deterministic AR replicator knobs";
      uses apply-advanced;
      leaf-list replicator-ip {
        type jt:ipaddr;
        max-elements 1;
        description
          "Set deterministic AR replicator ip for the flow";
      }
      leaf strict {
        type empty;
        description
          "Do not use any other replicator";
      }
      leaf-list fallback-replicator-ip {
        type jt:ipaddr;
        max-elements 1;
        description
          "Set Fallback replicator-ip";
      }
    }
    leaf damping {
      type string;
      description
        "Define BGP route flap damping parameters";
    }
    container aggregate-bandwidth {
      presence "enable aggregate-bandwidth";
      description
        "Advertise aggregate outbound link bandwidth";
      uses apply-advanced;
      choice transitive-type {
        case case_1 {
          leaf transitive {
            type empty;
            description
              "Transitive flag for link bandwidth";
          }
        }
        case case_2 {
          leaf non-transitive {
            type empty;
            description
              "Non-Transitive flag for link bandwidth";
          }
        }
      }
      leaf divide-equal {
        type empty;
        description
          "Divide-equal";
      }
    }
    container auto-link-bandwidth {
      presence "enable auto-link-bandwidth";
      description
        "Auto sense and attach link bandwidth community";
      uses apply-advanced;
      choice transitive-type {
        case case_1 {
          leaf transitive {
            type empty;
            description
              "Transitive flag for link bandwidth";
          }
        }
        case case_2 {
          leaf non-transitive {
            type empty;
            description
              "Non-Transitive flag for link bandwidth";
          }
        }
      }
    }
    leaf limit-bandwidth {
      type union {
        type uint64;
        type string {
          pattern "<.*>|$.*";
        }
      }
      description
        "Limit advertised aggregate outbound link bandwidth";
    }
    leaf no-entropy-label-capability {
      type empty;
      description
        "Don't advertise entropy label capability";
    }
    leaf as-path-prepend {
      type string;
      description
        "Prepend AS numbers to an AS path (BGP only)";
    }
    container as-path-expand {
      description
        "Prepend AS numbers prior to adding local-as (BGP only)";
      choice aspath_exp_value {
        case case_1 {
          container last-as {
            presence "enable last-as";
            description
              "Prepend last AS";
            leaf count {
              type union {
                type string {
                  pattern "<.*>|$.*";
                }
                type uint32 {
                  range "1 .. 32";
                }
              }
              description
                "Repeat count";
            }
          }
        }
        case case_2 {
          leaf aspath {
            type string;
            description
              "AS path string";
          }
        }
      }
    }
    container next-hop {
      description
        "Set the address of the next-hop router";
      choice nexthop_value {
        case case_1 {
          leaf self {
            type empty;
            description
              "Use a local address as the next-hop address";
          }
        }
        case case_2 {
          leaf peer-address {
            type empty;
            description
              "Use the remote peer address as the next-hop address";
          }
        }
        case case_3 {
          leaf address {
            type jt:ipaddr;
            description
              "Next-hop address";
          }
        }
        case case_4 {
          leaf reject {
            type empty;
            description
              "Use a reject next hop";
          }
        }
        case case_5 {
          leaf discard {
            type empty;
            description
              "Use a discard next hop";
          }
        }
        case case_6 {
          leaf next-table {
            type string;
            description
              "Perform a forwarding lookup in the specified table";
          }
        }
      }
    }
    container install-nexthop {
      description
        "Choose the next hop to be used for forwarding";
      choice strict_type {
        case case_1 {
          leaf strict {
            type empty;
            description
              "Do not use any other available next hops";
          }
        }
        case case_2 {
          leaf strict-named-lsp {
            type empty;
            description
              "Do not use any other non-lsp next hops";
          }
        }
      }
      choice nexthop-value {
        case case_1 {
          leaf-list lsp {
            type string;
            ordered-by user;
            description
              "Next-hop LSP name";
          }
        }
        case case_2 {
          leaf-list lsp-regex {
            type string;
            ordered-by user;
            description
              "Next-hop LSP name regular expression";
          }
        }
        case case_3 {
          leaf-list static-lsp {
            type string;
            ordered-by user;
            description
              "Next-hop static LSP name";
          }
        }
        case case_4 {
          leaf-list static-lsp-regex {
            type string;
            ordered-by user;
            description
              "Next-hop static LSP name regular expression";
          }
        }
        case case_5 {
          leaf non-lsp-nexthop {
            type empty;
            description
              "Next-hop with non-lsp";
          }
        }
        case case_6 {
          leaf non-labelled-nexthop {
            type empty;
            description
              "Next-hop without tag";
          }
        }
        case case_7 {
          leaf overlay-vxlan-interfaces {
            type empty;
            description
              "Next-hop for vxlan interfaces";
          }
        }
      }
      container except {
        description
          "Do not choose to install matching next hops";
        uses apply-advanced;
        choice nexthop-value {
          case case_1 {
            leaf-list lsp {
              type string;
              ordered-by user;
              description
                "Next-hop LSP name";
            }
          }
          case case_2 {
            leaf-list lsp-regex {
              type string;
              ordered-by user;
              description
                "Next-hop LSP name regular expression";
            }
          }
          case case_3 {
            leaf-list static-lsp {
              type string;
              ordered-by user;
              description
                "Next-hop static LSP name";
            }
          }
          case case_4 {
            leaf-list static-lsp-regex {
              type string;
              ordered-by user;
              description
                "Next-hop static LSP name regular expression";
            }
          }
          case case_5 {
            leaf non-lsp-nexthop {
              type empty;
              description
                "Next-hop with non-lsp";
            }
          }
          case case_6 {
            leaf non-labelled-nexthop {
              type empty;
              description
                "Next-hop without tag";
            }
          }
          case case_7 {
            leaf overlay-vxlan-interfaces {
              type empty;
              description
                "Next-hop for vxlan interfaces";
            }
          }
        }
        container fallback {
          description
            "Backup option";
          uses apply-advanced;
          choice nexthop-value {
            case case_1 {
              leaf-list lsp {
                type string;
                ordered-by user;
                description
                  "Next-hop LSP name";
              }
            }
            case case_2 {
              leaf-list lsp-regex {
                type string;
                ordered-by user;
                description
                  "Next-hop LSP name regular expression";
              }
            }
            case case_3 {
              leaf-list static-lsp {
                type string;
                ordered-by user;
                description
                  "Next-hop static LSP name";
              }
            }
            case case_4 {
              leaf-list static-lsp-regex {
                type string;
                ordered-by user;
                description
                  "Next-hop static LSP name regular expression";
              }
            }
            case case_5 {
              leaf non-lsp-nexthop {
                type empty;
                description
                  "Next-hop with non-lsp";
              }
            }
            case case_6 {
              leaf non-labelled-nexthop {
                type empty;
                description
                  "Next-hop without tag";
              }
            }
            case case_7 {
              leaf overlay-vxlan-interfaces {
                type empty;
                description
                  "Next-hop for vxlan interfaces";
              }
            }
          }
          container except {
            description
              "Do not choose to install matching next hops";
            uses apply-advanced;
            choice nexthop-value {
              case case_1 {
                leaf-list lsp {
                  type string;
                  ordered-by user;
                  description
                    "Next-hop LSP name";
                }
              }
              case case_2 {
                leaf-list lsp-regex {
                  type string;
                  ordered-by user;
                  description
                    "Next-hop LSP name regular expression";
                }
              }
              case case_3 {
                leaf-list static-lsp {
                  type string;
                  ordered-by user;
                  description
                    "Next-hop static LSP name";
                }
              }
              case case_4 {
                leaf-list static-lsp-regex {
                  type string;
                  ordered-by user;
                  description
                    "Next-hop static LSP name regular expression";
                }
              }
              case case_5 {
                leaf non-lsp-nexthop {
                  type empty;
                  description
                    "Next-hop with non-lsp";
                }
              }
              case case_6 {
                leaf non-labelled-nexthop {
                  type empty;
                  description
                    "Next-hop without tag";
                }
              }
              case case_7 {
                leaf overlay-vxlan-interfaces {
                  type empty;
                  description
                    "Next-hop for vxlan interfaces";
                }
              }
            }
          }
        }
      }
      container fallback {
        description
          "Backup option ";
        uses apply-advanced;
        choice nexthop-value {
          case case_1 {
            leaf-list lsp {
              type string;
              ordered-by user;
              description
                "Next-hop LSP name";
            }
          }
          case case_2 {
            leaf-list lsp-regex {
              type string;
              ordered-by user;
              description
                "Next-hop LSP name regular expression";
            }
          }
          case case_3 {
            leaf-list static-lsp {
              type string;
              ordered-by user;
              description
                "Next-hop static LSP name";
            }
          }
          case case_4 {
            leaf-list static-lsp-regex {
              type string;
              ordered-by user;
              description
                "Next-hop static LSP name regular expression";
            }
          }
          case case_5 {
            leaf non-lsp-nexthop {
              type empty;
              description
                "Next-hop with non-lsp";
            }
          }
          case case_6 {
            leaf non-labelled-nexthop {
              type empty;
              description
                "Next-hop without tag";
            }
          }
          case case_7 {
            leaf overlay-vxlan-interfaces {
              type empty;
              description
                "Next-hop for vxlan interfaces";
            }
          }
        }
        container except {
          description
            "Do not choose to install matching next hops";
          uses apply-advanced;
          choice nexthop-value {
            case case_1 {
              leaf-list lsp {
                type string;
                ordered-by user;
                description
                  "Next-hop LSP name";
              }
            }
            case case_2 {
              leaf-list lsp-regex {
                type string;
                ordered-by user;
                description
                  "Next-hop LSP name regular expression";
              }
            }
            case case_3 {
              leaf-list static-lsp {
                type string;
                ordered-by user;
                description
                  "Next-hop static LSP name";
              }
            }
            case case_4 {
              leaf-list static-lsp-regex {
                type string;
                ordered-by user;
                description
                  "Next-hop static LSP name regular expression";
              }
            }
            case case_5 {
              leaf non-lsp-nexthop {
                type empty;
                description
                  "Next-hop with non-lsp";
              }
            }
            case case_6 {
              leaf non-labelled-nexthop {
                type empty;
                description
                  "Next-hop without tag";
              }
            }
            case case_7 {
              leaf overlay-vxlan-interfaces {
                type empty;
                description
                  "Next-hop for vxlan interfaces";
              }
            }
          }
        }
      }
    }
    leaf trace {
      type empty;
      description
        "Log matches to a trace file";
    }
    container external {
      presence "enable external";
      description
        "External route";
      uses apply-advanced;
      leaf type {
        type union {
          type string {
            pattern "<.*>|$.*";
          }
          type int32 {
            range "1 .. 2";
          }
        }
        description
          "OSPF external metric type";
      }
      leaf nssa-only {
        type empty;
        description
          "Clear P-bit on lsa type 7";
      }
    }
    container load-balance {
      description
        "Type of load balancing in forwarding table";
      choice load_balance_type {
        case case_1 {
          leaf per-packet {
            type empty;
            description
              "Load balance on a per-packet basis deprecated, use per-flow instead";
          }
        }
        case case_2 {
          leaf per-flow {
            type empty;
            description
              "Load balance on a per-flow basis";
          }
        }
        case case_3;
        case case_4;
        case case_5;
        case case_6;
        case case_7;
        case case_8;
        case case_9;
        case case_10;
        case case_11;
      }
    }
    container advertise-locator {
      presence "enable advertise-locator";
      description
        "Advertise SRv6 Locator";
      uses apply-advanced;
      leaf internal {
        type empty;
        description
          "Advertise locator as Interal route";
      }
    }
    leaf set-down-bit {
      type empty;
      description
        "Set down bit";
    }
    leaf analyze {
      type empty;
      description
        "Send to registered controllers for analysis";
    }
    leaf destination-class {
      type string;
      description
        "Set destination class in forwarding table";
    }
    leaf source-class {
      type string;
      description
        "Set source class in forwarding table";
    }
    leaf forwarding-class {
      type string;
      description
        "Set source or destination class in forwarding table";
    }
    container map-to-interface {
      description
        "Set output logical interface";
      choice map_to_interface_value {
        case case_1 {
          leaf self {
            type empty;
            description
              "Map the interface to itself";
          }
        }
        case case_2 {
          leaf interface {
            type union {
              type jt:interface-name;
              type string {
                pattern "<.*>|$.*";
              }
            }
            description
              "Output logical interface";
          }
        }
      }
    }
    leaf-list ssm-source {
      type jt:ipaddr;
      ordered-by user;
      description
        "List of Sources for SSM mapping";
    }
    container p2mp-lsp-root {
      description
        "P2mp lsp root address";
      uses apply-advanced;
      leaf address {
        type jt:ipv4addr;
        description
          "Ipv4 root address";
      }
    }
    leaf dynamic-tunnel-attributes {
      type string;
      description
        "Choose the dynamic tunnel attributes used for forwarding";
    }
    leaf tunnel-end-point-address {
      type jt:ipaddr;
      description
        "Set tunnel end-point address of tunnel";
    }
    leaf selected-mldp-egress {
      type empty;
      description
        "This node should act as egress node for MLDP inband signalling";
    }
    leaf mhop-bfd-port {
      type empty;
      description
        "Use port number 4784 for MPLS-BFD as per RFC5884";
    }
    leaf no-backup {
      type empty;
      description
        "This prefix should not have backup";
    }
    leaf default-action {
      type enumeration {
        enum "accept" {
          description
            "Accept a route";
        }
        enum "reject" {
          description
            "Reject a route";
        }
      }
      description
        "Set default policy action";
    }
    leaf next {
      type enumeration {
        enum "policy" {
          description
            "Skip to next policy filter";
        }
        enum "term" {
          description
            "Skip to next term in a policy filter";
        }
      }
      description
        "Skip to next policy or term";
    }
    choice accept_reject {
      case case_1 {
        leaf accept {
          type empty;
          description
            "Accept a route";
        }
      }
      case case_2 {
        leaf reject {
          type empty;
          description
            "Reject a route";
        }
      }
    }
    container bgp-output-queue-priority {
      description
        "Set the BGP Update output queue priority.";
      choice class {
        case case_1 {
          leaf priority {
            type union {
              type string {
                pattern "<.*>|$.*";
              }
              type uint32 {
                range "1 .. 16";
              }
            }
            description
              "Output queue priority; higher is better";
          }
        }
        case case_2 {
          leaf expedited {
            type empty;
            description
              "Expedited queue; highest priority";
          }
        }
      }
    }
    leaf multipath-resolve {
      type empty;
      description
        "Use all paths for resolution over this prefix";
    }
    leaf source-routing-path-template {
      type string;
      description
        "Spring-te template to apply";
    }
    leaf label-allocation-fallback-reject {
      type empty;
      description
        "Suppress prefix export when label allocation fails";
    }
    leaf resolution-map {
      type string;
      description
        "Set resolution map modes";
    }
    leaf ignore-service-label {
      type empty;
      description
        "Ignore service labels";
    }
    container prefix-attribute-flags {
      presence "enable prefix-attribute-flags";
      description
        "Set ISIS prefix attribute flags sub TLV";
      uses apply-advanced;
      leaf node-segment-flag {
        type empty;
        description
          "Set node segment flag ";
      }
      leaf external-prefix-flag {
        type empty;
        description
          "Set external prefix flag ";
      }
      leaf anycast-flag {
        type empty;
        description
          "Set anycast flag ";
      }
      leaf entropy-label-capability-flag {
        type empty;
        description
          "Set entropy label capability flag ";
      }
    }
    container ipv4-source-router-id {
      presence "enable ipv4-source-router-id";
      description
        "Set IPv4 source router id in advertisement";
      uses apply-advanced;
      leaf router-id {
        type jt:ipaddr;
        description
          "Specify IPv4 address";
      }
    }
    container ipv6-source-router-id {
      presence "enable ipv6-source-router-id";
      description
        "Set IPv6 source router id in advertisement";
      uses apply-advanced;
      leaf router-id {
        type jt:ipv6addr;
        description
          "Specify IPv6 address";
      }
    }
    leaf request-long-lived-ack {
      type empty;
      description
        "Advertise route after forwarding is programmed";
    }
    leaf send-withdrawal-on-route-change {
      type empty;
      description
        "Withdraw route if change is not acked from forwarding";
    }
    container slice {
      description
        "Configure Policy Slice action";
      leaf slice-name {
        type string {
          length "1 .. 64";
        }
        description
          "Slice Name";
      }
    }
    leaf filter {
      type string;
      description
        "Set firewall-filter name";
    }
    leaf strip-as-path {
      type empty;
      description
        "Remove the incoming BGP as-path and replace with local AS";
    }
    container request-acknowledgements {
      description
        "Set request acknowledgement";
      leaf nexthop-ack {
        type empty;
        description
          "Set nexthop acknowledgement ";
      }
      leaf route-ack {
        type empty;
        description
          "Set route acknowledgement ";
      }
    }
  }

  grouping control_rtf_prefix_list_type {
    description
      "RTF prefix list";
    leaf name {
      type string;
      description
        "Name of rtf-prefix-list of routes to match";
    }
    uses apply-advanced;
  }

  grouping control_source_address_filter_list_type {
    leaf name {
      type string;
      description
        "Name of source-address-filter-list of routes to match";
    }
    uses apply-advanced;
  }

  grouping control_source_address_filter_type {
    leaf address {
      type jt:ipprefix;
      description
        "IP address or hostname";
    }
    leaf choice-ident {
      type enumeration {
        enum "exact";
        enum "longer";
        enum "orlonger";
        enum "upto";
        enum "through";
        enum "prefix-length-range";
      }
    }
    leaf choice-value {
      type string;
    }
    uses apply-advanced;
    container metric {
      description
        "Metric value";
      uses apply-advanced;
      choice metric_action {
        case case_1 {
          leaf metric {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
        case case_4 {
          container igp {
            presence "enable igp";
            description
              "Track the IGP metric (BGP only)";
            leaf metric_offset {
              type union {
                type int32;
                type string {
                  pattern "<.*>|$.*";
                }
              }
              description
                "Metric offset for MED";
            }
          }
        }
        case case_5 {
          container minimum-igp {
            presence "enable minimum-igp";
            description
              "Track the minimum IGP metric (BGP only)";
            leaf metric_offset {
              type union {
                type int32;
                type string {
                  pattern "<.*>|$.*";
                }
              }
              description
                "Metric offset for MED";
            }
          }
        }
        case case_6 {
          container expression {
            description
              "Calculate value based on route metric and metric2";
            uses metric_expression_type;
          }
        }
        case case_7 {
          leaf aigp {
            type empty;
            description
              "Use aigp, if it exists, to set the IGP metric";
          }
        }
        case case_8 {
          container effective-aigp {
            presence "enable effective-aigp";
            description
              "Track the effective AIGP metric (BGP only)";
            leaf metric_offset {
              type union {
                type int32;
                type string {
                  pattern "<.*>|$.*";
                }
              }
              description
                "Metric offset for MED";
            }
          }
        }
        case case_9 {
          container minimum-effective-aigp {
            presence "enable minimum-effective-aigp";
            description
              "Track the minimum effective AIGP metric (BGP only)";
            leaf metric_offset {
              type union {
                type int32;
                type string {
                  pattern "<.*>|$.*";
                }
              }
              description
                "Metric offset for MED";
            }
          }
        }
      }
    }
    container metric2 {
      description
        "Metric value 2";
      uses apply-advanced;
      choice metric_action {
        case case_1 {
          leaf metric2 {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container metric3 {
      description
        "Metric value 3";
      uses apply-advanced;
      choice metric_action {
        case case_1 {
          leaf metric3 {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container metric4 {
      description
        "Metric value 4";
      uses apply-advanced;
      choice metric_action {
        case case_1 {
          leaf metric4 {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container tag {
      description
        "Tag string";
      uses apply-advanced;
      choice metric_action {
        case case_1 {
          leaf tag {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container tag2 {
      description
        "Tag string 2";
      uses apply-advanced;
      choice metric_action {
        case case_1 {
          leaf tag2 {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container preference {
      description
        "Preference value";
      uses apply-advanced;
      choice metric_action {
        case case_1 {
          leaf preference {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container preference2 {
      description
        "Preference value 2";
      uses apply-advanced;
      choice metric_action {
        case case_1 {
          leaf preference2 {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container color {
      description
        "Color (preference) value";
      uses apply-advanced;
      choice metric_action {
        case case_1 {
          leaf color {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container color2 {
      description
        "Color (preference) value 2";
      uses apply-advanced;
      choice metric_action {
        case case_1 {
          leaf color2 {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container local-preference {
      description
        "Local preference associated with a route";
      uses apply-advanced;
      choice metric_action {
        case case_1 {
          leaf local-preference {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container credibility {
      description
        "TED credibility value for entries from BGP-TE";
      uses apply-advanced;
      choice metric_action {
        case case_1 {
          leaf credibility {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    leaf priority {
      type enumeration {
        enum "high" {
          description
            "Set priority to high";
        }
        enum "medium" {
          description
            "Set priority to medium";
        }
        enum "low" {
          description
            "Set priority to low";
        }
      }
      description
        "Set priority for route installation";
    }
    container prefix-segment {
      description
        "Set prefix segment attributes";
      uses apply-advanced;
      list algorithm {
        key "name";
        max-elements 15;
        description
          "Set prefix segment attributes for strict/flex algorithm ";
        leaf name {
          type union {
            type string {
              pattern "<.*>|$.*";
            }
            type uint32 {
              range "1 .. 255";
            }
          }
          mandatory true;
          description
            "Set prefix segment for strict/flex algorithm";
        }
        leaf index {
          type union {
            type string {
              pattern "<.*>|$.*";
            }
            type uint32 {
              range "0 .. 1048575";
            }
          }
          mandatory true;
          description
            "Set prefix segment index id";
        }
        leaf node-segment {
          type empty;
          description
            "Set node segment flag for this prefix segment";
        }
      }
      leaf index {
        type union {
          type string {
            pattern "<.*>|$.*";
          }
          type uint32 {
            range "0 .. 1048575";
          }
        }
        description
          "Set prefix segment index id";
      }
      leaf node-segment {
        type empty;
        description
          "Set node segment flag for default prefix segment";
      }
      leaf redistribute {
        type empty;
        description
          "Redistribute prefix-segment from route entry";
      }
    }
    leaf label-allocation {
      type enumeration {
        enum "per-table" {
          description
            "Set per-table label allocation mode";
        }
        enum "per-nexthop" {
          description
            "Set per-nexthop label allocation mode";
        }
        enum "per-table-localize" {
          description
            "Set per-table-localize label allocation mode";
        }
      }
      description
        "Set label allocation mode";
    }
    container add-path {
      description
        "Set BGP add-path attributes";
      leaf send-count {
        type union {
          type string {
            pattern "<.*>|$.*";
          }
          type uint32 {
            range "2 .. 64";
          }
        }
        description
          "Number of add-paths sent";
      }
    }
    leaf fib-install-priority {
      type enumeration {
        enum "high" {
          description
            "Set Fib install priority  to high";
        }
        enum "medium" {
          description
            "Set Fib install priority to medium ";
        }
      }
      description
        "Set Fib Instalation priority of a route";
    }
    leaf validation-state {
      type enumeration {
        enum "valid" {
          description
            "Set validaton-state to valid";
        }
        enum "invalid" {
          description
            "Set validation-state to invalid";
        }
        enum "unknown" {
          description
            "Set validation-state to unknown";
        }
      }
      description
        "Set validation-state of a route";
    }
    leaf origin {
      type enumeration {
        enum "igp" {
          description
            "Path originated in the local IGP";
        }
        enum "egp" {
          description
            "Path originated in another AS";
        }
        enum "incomplete" {
          description
            "Path was learned by some other means";
        }
      }
      description
        "BGP path origin";
    }
    container srv6 {
      description
        "Configure SID with 128 bit address";
      leaf sid {
        type jt:ipv6addr;
        description
          "IPv6 Address";
      }
      leaf locator {
        type string;
        description
          "Name of locator";
      }
      choice locator_type {
        case case_1 {
          leaf micro-dt4-sid {
            type empty;
            description
              "Micro SID type dt4";
          }
        }
        case case_2 {
          leaf micro-dt6-sid {
            type empty;
            description
              "Micro SID type dt6";
          }
        }
        case case_3 {
          leaf micro-dt46-sid {
            type empty;
            description
              "Micro SID type dt46";
          }
        }
      }
    }
    container aigp-originate {
      presence "enable aigp-originate";
      description
        "Originate a BGP AIGP attribute";
      leaf distance {
        type union {
          type uint32;
          type string {
            pattern "<.*>|$.*";
          }
        }
        description
          "AIGP distance";
      }
    }
    container aigp-adjust {
      description
        "Adjust a BGP AIGP attribute";
      choice math-op {
        case case_1 {
          leaf add {
            type empty;
          }
        }
        case case_2 {
          leaf subtract {
            type empty;
          }
        }
        case case_3 {
          leaf multiply {
            type empty;
          }
        }
        case case_4 {
          leaf divide {
            type empty;
          }
        }
      }
      choice adjust-value {
        case case_1 {
          leaf user-value {
            type union {
              type uint64;
              type string {
                pattern "<.*>|$.*";
              }
            }
            description
              "Adjustment value";
          }
        }
        case case_2 {
          leaf distance-to-protocol-nexthop {
            type empty;
            description
              "Metric2";
          }
        }
      }
    }
    list community {
      key "choice-ident choice-value community-name";
      ordered-by user;
      description
        "BGP community properties associated with a route";
      leaf choice-ident {
        type enumeration {
          enum "equal-literal";
          enum "set";
          enum "plus-literal";
          enum "add";
          enum "minus-literal";
          enum "delete";
        }
      }
      leaf choice-value {
        type string;
      }
      leaf community-name {
        type string;
        description
          "Name to identify a BGP community";
      }
    }
    list tunnel-attribute {
      key "choice-ident choice-value tunnel-attribute-name";
      ordered-by user;
      description
        "BGP tunnel attribute associated with a route";
      leaf choice-ident {
        type enumeration {
          enum "set";
          enum "remove";
        }
      }
      leaf choice-value {
        type string;
      }
      leaf tunnel-attribute-name {
        type string;
        description
          "Name of a tunnel attribute , or 'all'";
      }
    }
    container assisted-replication {
      presence "enable assisted-replication";
      description
        "Deterministic AR replicator knobs";
      uses apply-advanced;
      leaf-list replicator-ip {
        type jt:ipaddr;
        max-elements 1;
        description
          "Set deterministic AR replicator ip for the flow";
      }
      leaf strict {
        type empty;
        description
          "Do not use any other replicator";
      }
      leaf-list fallback-replicator-ip {
        type jt:ipaddr;
        max-elements 1;
        description
          "Set Fallback replicator-ip";
      }
    }
    leaf damping {
      type string;
      description
        "Define BGP route flap damping parameters";
    }
    container aggregate-bandwidth {
      presence "enable aggregate-bandwidth";
      description
        "Advertise aggregate outbound link bandwidth";
      uses apply-advanced;
      choice transitive-type {
        case case_1 {
          leaf transitive {
            type empty;
            description
              "Transitive flag for link bandwidth";
          }
        }
        case case_2 {
          leaf non-transitive {
            type empty;
            description
              "Non-Transitive flag for link bandwidth";
          }
        }
      }
      leaf divide-equal {
        type empty;
        description
          "Divide-equal";
      }
    }
    container auto-link-bandwidth {
      presence "enable auto-link-bandwidth";
      description
        "Auto sense and attach link bandwidth community";
      uses apply-advanced;
      choice transitive-type {
        case case_1 {
          leaf transitive {
            type empty;
            description
              "Transitive flag for link bandwidth";
          }
        }
        case case_2 {
          leaf non-transitive {
            type empty;
            description
              "Non-Transitive flag for link bandwidth";
          }
        }
      }
    }
    leaf limit-bandwidth {
      type union {
        type uint64;
        type string {
          pattern "<.*>|$.*";
        }
      }
      description
        "Limit advertised aggregate outbound link bandwidth";
    }
    leaf no-entropy-label-capability {
      type empty;
      description
        "Don't advertise entropy label capability";
    }
    leaf as-path-prepend {
      type string;
      description
        "Prepend AS numbers to an AS path (BGP only)";
    }
    container as-path-expand {
      description
        "Prepend AS numbers prior to adding local-as (BGP only)";
      choice aspath_exp_value {
        case case_1 {
          container last-as {
            presence "enable last-as";
            description
              "Prepend last AS";
            leaf count {
              type union {
                type string {
                  pattern "<.*>|$.*";
                }
                type uint32 {
                  range "1 .. 32";
                }
              }
              description
                "Repeat count";
            }
          }
        }
        case case_2 {
          leaf aspath {
            type string;
            description
              "AS path string";
          }
        }
      }
    }
    container next-hop {
      description
        "Set the address of the next-hop router";
      choice nexthop_value {
        case case_1 {
          leaf self {
            type empty;
            description
              "Use a local address as the next-hop address";
          }
        }
        case case_2 {
          leaf peer-address {
            type empty;
            description
              "Use the remote peer address as the next-hop address";
          }
        }
        case case_3 {
          leaf address {
            type jt:ipaddr;
            description
              "Next-hop address";
          }
        }
        case case_4 {
          leaf reject {
            type empty;
            description
              "Use a reject next hop";
          }
        }
        case case_5 {
          leaf discard {
            type empty;
            description
              "Use a discard next hop";
          }
        }
        case case_6 {
          leaf next-table {
            type string;
            description
              "Perform a forwarding lookup in the specified table";
          }
        }
      }
    }
    container install-nexthop {
      description
        "Choose the next hop to be used for forwarding";
      choice strict_type {
        case case_1 {
          leaf strict {
            type empty;
            description
              "Do not use any other available next hops";
          }
        }
        case case_2 {
          leaf strict-named-lsp {
            type empty;
            description
              "Do not use any other non-lsp next hops";
          }
        }
      }
      choice nexthop-value {
        case case_1 {
          leaf-list lsp {
            type string;
            ordered-by user;
            description
              "Next-hop LSP name";
          }
        }
        case case_2 {
          leaf-list lsp-regex {
            type string;
            ordered-by user;
            description
              "Next-hop LSP name regular expression";
          }
        }
        case case_3 {
          leaf-list static-lsp {
            type string;
            ordered-by user;
            description
              "Next-hop static LSP name";
          }
        }
        case case_4 {
          leaf-list static-lsp-regex {
            type string;
            ordered-by user;
            description
              "Next-hop static LSP name regular expression";
          }
        }
        case case_5 {
          leaf non-lsp-nexthop {
            type empty;
            description
              "Next-hop with non-lsp";
          }
        }
        case case_6 {
          leaf non-labelled-nexthop {
            type empty;
            description
              "Next-hop without tag";
          }
        }
        case case_7 {
          leaf overlay-vxlan-interfaces {
            type empty;
            description
              "Next-hop for vxlan interfaces";
          }
        }
      }
      container except {
        description
          "Do not choose to install matching next hops";
        uses apply-advanced;
        choice nexthop-value {
          case case_1 {
            leaf-list lsp {
              type string;
              ordered-by user;
              description
                "Next-hop LSP name";
            }
          }
          case case_2 {
            leaf-list lsp-regex {
              type string;
              ordered-by user;
              description
                "Next-hop LSP name regular expression";
            }
          }
          case case_3 {
            leaf-list static-lsp {
              type string;
              ordered-by user;
              description
                "Next-hop static LSP name";
            }
          }
          case case_4 {
            leaf-list static-lsp-regex {
              type string;
              ordered-by user;
              description
                "Next-hop static LSP name regular expression";
            }
          }
          case case_5 {
            leaf non-lsp-nexthop {
              type empty;
              description
                "Next-hop with non-lsp";
            }
          }
          case case_6 {
            leaf non-labelled-nexthop {
              type empty;
              description
                "Next-hop without tag";
            }
          }
          case case_7 {
            leaf overlay-vxlan-interfaces {
              type empty;
              description
                "Next-hop for vxlan interfaces";
            }
          }
        }
        container fallback {
          description
            "Backup option";
          uses apply-advanced;
          choice nexthop-value {
            case case_1 {
              leaf-list lsp {
                type string;
                ordered-by user;
                description
                  "Next-hop LSP name";
              }
            }
            case case_2 {
              leaf-list lsp-regex {
                type string;
                ordered-by user;
                description
                  "Next-hop LSP name regular expression";
              }
            }
            case case_3 {
              leaf-list static-lsp {
                type string;
                ordered-by user;
                description
                  "Next-hop static LSP name";
              }
            }
            case case_4 {
              leaf-list static-lsp-regex {
                type string;
                ordered-by user;
                description
                  "Next-hop static LSP name regular expression";
              }
            }
            case case_5 {
              leaf non-lsp-nexthop {
                type empty;
                description
                  "Next-hop with non-lsp";
              }
            }
            case case_6 {
              leaf non-labelled-nexthop {
                type empty;
                description
                  "Next-hop without tag";
              }
            }
            case case_7 {
              leaf overlay-vxlan-interfaces {
                type empty;
                description
                  "Next-hop for vxlan interfaces";
              }
            }
          }
          container except {
            description
              "Do not choose to install matching next hops";
            uses apply-advanced;
            choice nexthop-value {
              case case_1 {
                leaf-list lsp {
                  type string;
                  ordered-by user;
                  description
                    "Next-hop LSP name";
                }
              }
              case case_2 {
                leaf-list lsp-regex {
                  type string;
                  ordered-by user;
                  description
                    "Next-hop LSP name regular expression";
                }
              }
              case case_3 {
                leaf-list static-lsp {
                  type string;
                  ordered-by user;
                  description
                    "Next-hop static LSP name";
                }
              }
              case case_4 {
                leaf-list static-lsp-regex {
                  type string;
                  ordered-by user;
                  description
                    "Next-hop static LSP name regular expression";
                }
              }
              case case_5 {
                leaf non-lsp-nexthop {
                  type empty;
                  description
                    "Next-hop with non-lsp";
                }
              }
              case case_6 {
                leaf non-labelled-nexthop {
                  type empty;
                  description
                    "Next-hop without tag";
                }
              }
              case case_7 {
                leaf overlay-vxlan-interfaces {
                  type empty;
                  description
                    "Next-hop for vxlan interfaces";
                }
              }
            }
          }
        }
      }
      container fallback {
        description
          "Backup option ";
        uses apply-advanced;
        choice nexthop-value {
          case case_1 {
            leaf-list lsp {
              type string;
              ordered-by user;
              description
                "Next-hop LSP name";
            }
          }
          case case_2 {
            leaf-list lsp-regex {
              type string;
              ordered-by user;
              description
                "Next-hop LSP name regular expression";
            }
          }
          case case_3 {
            leaf-list static-lsp {
              type string;
              ordered-by user;
              description
                "Next-hop static LSP name";
            }
          }
          case case_4 {
            leaf-list static-lsp-regex {
              type string;
              ordered-by user;
              description
                "Next-hop static LSP name regular expression";
            }
          }
          case case_5 {
            leaf non-lsp-nexthop {
              type empty;
              description
                "Next-hop with non-lsp";
            }
          }
          case case_6 {
            leaf non-labelled-nexthop {
              type empty;
              description
                "Next-hop without tag";
            }
          }
          case case_7 {
            leaf overlay-vxlan-interfaces {
              type empty;
              description
                "Next-hop for vxlan interfaces";
            }
          }
        }
        container except {
          description
            "Do not choose to install matching next hops";
          uses apply-advanced;
          choice nexthop-value {
            case case_1 {
              leaf-list lsp {
                type string;
                ordered-by user;
                description
                  "Next-hop LSP name";
              }
            }
            case case_2 {
              leaf-list lsp-regex {
                type string;
                ordered-by user;
                description
                  "Next-hop LSP name regular expression";
              }
            }
            case case_3 {
              leaf-list static-lsp {
                type string;
                ordered-by user;
                description
                  "Next-hop static LSP name";
              }
            }
            case case_4 {
              leaf-list static-lsp-regex {
                type string;
                ordered-by user;
                description
                  "Next-hop static LSP name regular expression";
              }
            }
            case case_5 {
              leaf non-lsp-nexthop {
                type empty;
                description
                  "Next-hop with non-lsp";
              }
            }
            case case_6 {
              leaf non-labelled-nexthop {
                type empty;
                description
                  "Next-hop without tag";
              }
            }
            case case_7 {
              leaf overlay-vxlan-interfaces {
                type empty;
                description
                  "Next-hop for vxlan interfaces";
              }
            }
          }
        }
      }
    }
    leaf trace {
      type empty;
      description
        "Log matches to a trace file";
    }
    container external {
      presence "enable external";
      description
        "External route";
      uses apply-advanced;
      leaf type {
        type union {
          type string {
            pattern "<.*>|$.*";
          }
          type int32 {
            range "1 .. 2";
          }
        }
        description
          "OSPF external metric type";
      }
      leaf nssa-only {
        type empty;
        description
          "Clear P-bit on lsa type 7";
      }
    }
    container load-balance {
      description
        "Type of load balancing in forwarding table";
      choice load_balance_type {
        case case_1 {
          leaf per-packet {
            type empty;
            description
              "Load balance on a per-packet basis deprecated, use per-flow instead";
          }
        }
        case case_2 {
          leaf per-flow {
            type empty;
            description
              "Load balance on a per-flow basis";
          }
        }
        case case_3;
        case case_4;
        case case_5;
        case case_6;
        case case_7;
        case case_8;
        case case_9;
        case case_10;
        case case_11;
      }
    }
    container advertise-locator {
      presence "enable advertise-locator";
      description
        "Advertise SRv6 Locator";
      uses apply-advanced;
      leaf internal {
        type empty;
        description
          "Advertise locator as Interal route";
      }
    }
    leaf set-down-bit {
      type empty;
      description
        "Set down bit";
    }
    leaf analyze {
      type empty;
      description
        "Send to registered controllers for analysis";
    }
    leaf destination-class {
      type string;
      description
        "Set destination class in forwarding table";
    }
    leaf source-class {
      type string;
      description
        "Set source class in forwarding table";
    }
    leaf forwarding-class {
      type string;
      description
        "Set source or destination class in forwarding table";
    }
    container map-to-interface {
      description
        "Set output logical interface";
      choice map_to_interface_value {
        case case_1 {
          leaf self {
            type empty;
            description
              "Map the interface to itself";
          }
        }
        case case_2 {
          leaf interface {
            type union {
              type jt:interface-name;
              type string {
                pattern "<.*>|$.*";
              }
            }
            description
              "Output logical interface";
          }
        }
      }
    }
    leaf-list ssm-source {
      type jt:ipaddr;
      ordered-by user;
      description
        "List of Sources for SSM mapping";
    }
    container p2mp-lsp-root {
      description
        "P2mp lsp root address";
      uses apply-advanced;
      leaf address {
        type jt:ipv4addr;
        description
          "Ipv4 root address";
      }
    }
    leaf dynamic-tunnel-attributes {
      type string;
      description
        "Choose the dynamic tunnel attributes used for forwarding";
    }
    leaf tunnel-end-point-address {
      type jt:ipaddr;
      description
        "Set tunnel end-point address of tunnel";
    }
    leaf selected-mldp-egress {
      type empty;
      description
        "This node should act as egress node for MLDP inband signalling";
    }
    leaf mhop-bfd-port {
      type empty;
      description
        "Use port number 4784 for MPLS-BFD as per RFC5884";
    }
    leaf no-backup {
      type empty;
      description
        "This prefix should not have backup";
    }
    leaf default-action {
      type enumeration {
        enum "accept" {
          description
            "Accept a route";
        }
        enum "reject" {
          description
            "Reject a route";
        }
      }
      description
        "Set default policy action";
    }
    leaf next {
      type enumeration {
        enum "policy" {
          description
            "Skip to next policy filter";
        }
        enum "term" {
          description
            "Skip to next term in a policy filter";
        }
      }
      description
        "Skip to next policy or term";
    }
    choice accept_reject {
      case case_1 {
        leaf accept {
          type empty;
          description
            "Accept a route";
        }
      }
      case case_2 {
        leaf reject {
          type empty;
          description
            "Reject a route";
        }
      }
    }
    container bgp-output-queue-priority {
      description
        "Set the BGP Update output queue priority.";
      choice class {
        case case_1 {
          leaf priority {
            type union {
              type string {
                pattern "<.*>|$.*";
              }
              type uint32 {
                range "1 .. 16";
              }
            }
            description
              "Output queue priority; higher is better";
          }
        }
        case case_2 {
          leaf expedited {
            type empty;
            description
              "Expedited queue; highest priority";
          }
        }
      }
    }
    leaf multipath-resolve {
      type empty;
      description
        "Use all paths for resolution over this prefix";
    }
    leaf source-routing-path-template {
      type string;
      description
        "Spring-te template to apply";
    }
    leaf label-allocation-fallback-reject {
      type empty;
      description
        "Suppress prefix export when label allocation fails";
    }
    leaf resolution-map {
      type string;
      description
        "Set resolution map modes";
    }
    leaf ignore-service-label {
      type empty;
      description
        "Ignore service labels";
    }
    container prefix-attribute-flags {
      presence "enable prefix-attribute-flags";
      description
        "Set ISIS prefix attribute flags sub TLV";
      uses apply-advanced;
      leaf node-segment-flag {
        type empty;
        description
          "Set node segment flag ";
      }
      leaf external-prefix-flag {
        type empty;
        description
          "Set external prefix flag ";
      }
      leaf anycast-flag {
        type empty;
        description
          "Set anycast flag ";
      }
      leaf entropy-label-capability-flag {
        type empty;
        description
          "Set entropy label capability flag ";
      }
    }
    container ipv4-source-router-id {
      presence "enable ipv4-source-router-id";
      description
        "Set IPv4 source router id in advertisement";
      uses apply-advanced;
      leaf router-id {
        type jt:ipaddr;
        description
          "Specify IPv4 address";
      }
    }
    container ipv6-source-router-id {
      presence "enable ipv6-source-router-id";
      description
        "Set IPv6 source router id in advertisement";
      uses apply-advanced;
      leaf router-id {
        type jt:ipv6addr;
        description
          "Specify IPv6 address";
      }
    }
    leaf request-long-lived-ack {
      type empty;
      description
        "Advertise route after forwarding is programmed";
    }
    leaf send-withdrawal-on-route-change {
      type empty;
      description
        "Withdraw route if change is not acked from forwarding";
    }
    container slice {
      description
        "Configure Policy Slice action";
      leaf slice-name {
        type string {
          length "1 .. 64";
        }
        description
          "Slice Name";
      }
    }
    leaf filter {
      type string;
      description
        "Set firewall-filter name";
    }
    leaf strip-as-path {
      type empty;
      description
        "Remove the incoming BGP as-path and replace with local AS";
    }
    container request-acknowledgements {
      description
        "Set request acknowledgement";
      leaf nexthop-ack {
        type empty;
        description
          "Set nexthop acknowledgement ";
      }
      leaf route-ack {
        type empty;
        description
          "Set route acknowledgement ";
      }
    }
  }

  grouping fast_lookup_tuple_list_items {
    leaf name {
      type string;
      description
        "As <destination-address>:<source-address>:<proto>:<src-port>:<dest-port>";
    }
    uses apply-advanced;
  }

  grouping juniper-protocols {
    uses apply-advanced;
    container bfd {
      description
        "Bidirectional Forwarding Detection (BFD) options";
      uses apply-advanced;
      container traceoptions {
        description
          "Trace options for BFD";
        uses apply-advanced;
        leaf no-remote-trace {
          type empty;
          description
            "Disable remote tracing";
        }
        container file {
          description
            "Trace file information";
          leaf filename {
            type string {
              length "1 .. 1024";
            }
            description
              "Name of file in which to write trace information";
          }
          leaf size {
            type string;
            description
              "Maximum trace file size";
          }
          leaf files {
            type union {
              type string {
                pattern "<.*>|$.*";
              }
              type uint32 {
                range "2 .. 1000";
              }
            }
            default "3";
            description
              "Maximum number of trace files";
          }
          choice world-readable-choice {
            leaf world-readable {
              type empty;
              description
                "Allow any user to read the log file";
            }
            leaf no-world-readable {
              type empty;
              description
                "Don't allow any user to read the log file";
            }
          }
          leaf match {
            type jt:regular-expression;
            description
              "Regular expression for lines to be logged";
          }
        }
        list flag {
          key "name";
          ordered-by user;
          description
            "Trace flag information";
          leaf name {
            type enumeration {
              enum "adjacency" {
                description
                  "Trace adjacency messages";
              }
              enum "event" {
                description
                  "Trace all events";
              }
              enum "error" {
                description
                  "Trace all errors";
              }
              enum "rtsock" {
                description
                  "Trace all rtscok messages";
              }
              enum "packet" {
                description
                  "Trace all packets";
              }
              enum "ppm-packet" {
                description
                  "Trace packet activity by periodic packet management";
              }
              enum "pipe" {
                description
                  "Trace pipe messages";
              }
              enum "pipe-detail" {
                description
                  "Trace pipe messages in detail";
              }
              enum "state" {
                description
                  "Trace state transitions";
              }
              enum "timer" {
                description
                  "Trace timer processing";
              }
              enum "nsr-synchronization" {
                description
                  "Trace NSR synchronization events";
              }
              enum "nsr-packet" {
                description
                  "Trace packet activity of NSR";
              }
              enum "issu" {
                description
                  "Trace ISSU packet activity";
              }
              enum "slow-start" {
                description
                  "Trace slow-start activity";
              }
              enum "session" {
                description
                  "Per session activity";
              }
              enum "all" {
                description
                  "Trace everything";
              }
            }
          }
        }
      }
      leaf mhop-inline-disable {
        type empty;
        description
          "Disable Inline mode for Multi Hop BFD sessions";
      }
      leaf no-issu-timer-negotiation {
        type empty;
        description
          "Disable ISSU timer negotiation";
      }
      container sbfd {
        description
          "Seamless BFD parameters";
        uses apply-advanced;
        leaf-list pool {
          type union {
            type uint32;
            type string {
              pattern "<.*>|$.*";
            }
          }
          description
            "List of seamless BFD endpoints";
        }
        list local-discriminator {
          key "name";
          ordered-by user;
          description
            "Local discriminator for seamless BFD responder";
          leaf name {
            type union {
              type string {
                pattern "<.*>|$.*";
              }
              type uint32 {
                range "1 .. 4294967295";
              }
            }
            description
              "Local discriminator for seamless BFD responder";
          }
          uses apply-advanced;
          leaf minimum-receive-interval {
            type union {
              type string {
                pattern "<.*>|$.*";
              }
              type uint32 {
                range "10 .. 255000";
              }
            }
            units "milliseconds";
            description
              "Minimum receive interval for seamless BFD responder";
          }
          leaf local-ip-address {
            type jt:ipv4addr;
            description
              "IPv4 source address";
          }
          leaf local-ipv6-address {
            type jt:ipv6addr;
            description
              "IPv6 source address";
          }
        }
        list local-discriminator-ip {
          key "name";
          ordered-by user;
          description
            "Local discriminator IP address for sBFD responder";
          leaf name {
            type jt:ipv4addr;
            description
              "Local discriminator IP address for sBFD responder";
          }
          uses apply-advanced;
          leaf minimum-receive-interval {
            type union {
              type string {
                pattern "<.*>|$.*";
              }
              type uint32 {
                range "10 .. 255000";
              }
            }
            units "milliseconds";
            description
              "Minimum receive interval for seamless BFD responder";
          }
          leaf local-ip-address {
            type jt:ipv4addr;
            description
              "IPv4 source address";
          }
        }
      }
    }
    container bgp {
      description
        "BGP options";
      uses juniper-protocols-bgp;
    }
    container vrrp {
      description
        "VRRP options";
      uses apply-advanced;
      leaf version-3 {
        type empty;
        description
          "VRRPv3 conformance";
      }
    }
    container evpn {
      description
        "Configuration EVPN default routing instance";
      uses apply-advanced;
      container traceoptions {
        description
          "Trace options for Layer 2 VPNs";
        uses apply-advanced;
        container file {
          description
            "Trace file options";
          leaf filename {
            type string {
              length "1 .. 1024";
            }
            description
              "Name of file in which to write trace information";
          }
          leaf replace {
            type empty;
            status deprecated;
            description
              "Replace trace file rather than appending to it";
          }
          leaf size {
            type string;
            description
              "Maximum trace file size";
          }
          leaf files {
            type union {
              type string {
                pattern "<.*>|$.*";
              }
              type uint32 {
                range "2 .. 1000";
              }
            }
            default "10";
            description
              "Maximum number of trace files";
          }
          leaf no-stamp {
            type empty;
            status deprecated;
            description
              "Do not timestamp trace file";
          }
          choice world-readable-choice {
            leaf world-readable {
              type empty;
              description
                "Allow any user to read the log file";
            }
            leaf no-world-readable {
              type empty;
              description
                "Don't allow any user to read the log file";
            }
          }
        }
        list flag {
          key "name";
          ordered-by user;
          description
            "Tracing parameters";
          leaf name {
            type enumeration {
              enum "error" {
                description
                  "Trace errors";
              }
              enum "topology" {
                description
                  "Trace Layer 2 VPN, VPLS and EVPN topology changes";
              }
              enum "nlri" {
                description
                  "Trace Layer 2 VPN, VPLS and EVPN remote site advertisements";
              }
              enum "connections" {
                description
                  "Trace Layer 2 VPN and VPLS connections";
              }
              enum "automatic-site" {
                description
                  "Trace VPLS automatic site state";
              }
              enum "oam" {
                description
                  "Trace OAM messages";
              }
              enum "mac-database" {
                description
                  "Trace MAC route database in a EVPN instance";
              }
              enum "nsr" {
                description
                  "Trace NSR in a EVPN instance";
              }
              enum "egress-protection" {
                description
                  "Trace Edge Protection messages";
              }
              enum "instance" {
                description
                  "Evpn instance related messages";
              }
              enum "interface" {
                description
                  "Interface related messages";
              }
              enum "l2aldsync" {
                description
                  "Messages related to EVPN-L2ALD communication";
              }
              enum "p2mp" {
                description
                  "P2MP messages";
              }
              enum "esi" {
                description
                  "Evpn ethernet segment related messages";
              }
              enum "mcsn" {
                description
                  "Evpn multicast snooping related messages";
              }
              enum "vpws" {
                description
                  "VPWS messages";
              }
              enum "irb" {
                description
                  "Integrated routing bridging messages";
              }
              enum "ar" {
                description
                  "Assisted-replication messages";
              }
              enum "etree" {
                description
                  "Evpn etree messages";
              }
              enum "kernel" {
                description
                  "Messages related to rpd-kernel communication";
              }
              enum "bd" {
                description
                  "Evpn bridge domain messages";
              }
              enum "pbb" {
                description
                  "Evpn provider backbone bridging messages";
              }
              enum "infra" {
                description
                  "Messages related to infrastructure in evpn";
              }
              enum "pfxdb" {
                description
                  "Type-5 related messages";
              }
              enum "peg-df" {
                description
                  "PIM EVPN Gateway DF-Election related messages";
              }
              enum "gbptagdb" {
                description
                  "Trace message related to gbptagdb";
              }
              enum "route" {
                description
                  "Trace routing information";
              }
              enum "normal" {
                description
                  "Trace normal events";
              }
              enum "general" {
                description
                  "Trace general events";
              }
              enum "state" {
                description
                  "Trace state transitions";
              }
              enum "policy" {
                description
                  "Trace policy processing";
              }
              enum "task" {
                description
                  "Trace routing protocol task processing";
              }
              enum "timer" {
                description
                  "Trace routing protocol timer processing";
              }
              enum "all" {
                description
                  "Trace everything";
              }
            }
          }
          leaf send {
            type empty;
            description
              "Trace transmitted packets";
          }
          leaf receive {
            type empty;
            description
              "Trace received packets";
          }
          leaf detail {
            type empty;
            description
              "Trace detailed information";
          }
          leaf disable {
            type empty;
            description
              "Disable this trace flag";
          }
        }
      }
      leaf mac-history {
        type union {
          type string {
            pattern "<.*>|$.*";
          }
          type uint16 {
            range "0 .. 255";
          }
        }
        description
          "Number of history entries to be maitained per mac";
      }
      leaf peg-df-election-history {
        type union {
          type string {
            pattern "<.*>|$.*";
          }
          type uint16 {
            range "0 .. 255";
          }
        }
        description
          "Number of DF Election history entries to be maintained per PEG BD";
      }
      leaf oism-core-route-history {
        type union {
          type string {
            pattern "<.*>|$.*";
          }
          type uint16 {
            range "0 .. 255";
          }
        }
        description
          "Number of history entries to be maintained per OISM Core Route";
      }
      leaf interface-history {
        type union {
          type string {
            pattern "<.*>|$.*";
          }
          type uint16 {
            range "0 .. 255";
          }
        }
        description
          "Number of history entries to be maintained per EVPN interface";
      }
      leaf core-isolation-delay-response {
        type union {
          type string {
            pattern "<.*>|$.*";
          }
          type uint32 {
            range "0 .. 255";
          }
        }
        description
          "Delay core-isolation response (seconds)";
      }
      leaf mac-ip-limit {
        type union {
          type string {
            pattern "<.*>|$.*";
          }
          type uint32 {
            range "1 .. 5000";
          }
        }
        description
          "Maximum number of IPs that can be learned on a MAC, default is 200";
      }
      list mac-list {
        key "name";
        description
          "Configure MAC lists";
        leaf name {
          type string {
            length "1 .. 128";
          }
          description
            "List name";
        }
        uses apply-advanced;
        leaf-list mac-address {
          type jt:mac-addr;
          description
            "MAC address";
        }
      }
      container mac-mobility {
        description
          "MAC mobility settings";
        uses apply-advanced;
        leaf no-sequence-numbers {
          type empty;
          description
            "Don't use sequence numbers for MAC mobility";
        }
      }
      leaf no-core-isolation {
        type empty;
        description
          "Disable EVPN Core isolation";
      }
      leaf leave-sync-route-oldstyle {
        type empty;
        description
          "Originate leave sync route oldstyle";
      }
      leaf-list interconnect-multihoming-peer-gateways {
        type jt:ipaddr;
        max-elements 64;
        description
          "Configure multihoming peer gateway VTEP IPv4 addresses";
      }
      leaf-list interconnect-multihoming-peer-v6-gateways {
        type jt:ipv6addr;
        max-elements 64;
        description
          "Configure multihoming peer gateway VTEP IPv6 addresses";
      }
      leaf advertise-evpn-esi-routes {
        type empty;
        description
          "Advertise AD/ES routes considering instance ifl status";
      }
      leaf-list static-multihoming-peer {
        type jt:ipaddr;
        max-elements 64;
        description
          "Configure static multihoming peer VTEP IPv4 addresses";
      }
      leaf-list static-multihoming-peer-v6 {
        type jt:ipv6addr;
        max-elements 64;
        description
          "Configure static multihoming peer VTEP IPv6 addresses";
      }
      container node-detection {
        presence "enable node-detection";
        description
          "Node detection";
        uses apply-advanced;
        leaf next-hop {
          type union {
            type jt:interface-unit;
            type string {
              pattern "<.*>|$.*";
            }
          }
          description
            "Next-hop identifier to which to map";
        }
        leaf action {
          type enumeration {
            enum "laser-off" {
              description
                "Will trigger laser-off on core-isolation";
            }
            enum "trigger-node-isolation" {
              description
                "Will trigger link-down on core-isolation";
            }
          }
          description
            "Isolation action";
        }
        container bfd-liveness-detection {
          description
            "Bidirectional Forwarding Detection (BFD) options";
          uses apply-advanced;
          leaf version {
            type enumeration {
              enum "0" {
                description
                  "BFD version 0 (deprecated)";
              }
              enum "1" {
                description
                  "BFD version 1";
              }
              enum "automatic" {
                description
                  "Choose BFD version automatically";
              }
            }
            default "automatic";
            description
              "BFD protocol version number";
          }
          leaf minimum-interval {
            type union {
              type string {
                pattern "<.*>|$.*";
              }
              type uint32 {
                range "1 .. 255000";
              }
            }
            units "milliseconds";
            description
              "Minimum transmit and receive interval";
          }
          leaf minimum-transmit-interval {
            type union {
              type string {
                pattern "<.*>|$.*";
              }
              type uint32 {
                range "1 .. 255000";
              }
            }
            units "milliseconds";
            status deprecated;
            description
              "Minimum transmit interval";
          }
          leaf minimum-receive-interval {
            type union {
              type string {
                pattern "<.*>|$.*";
              }
              type uint32 {
                range "1 .. 255000";
              }
            }
            units "milliseconds";
            description
              "Minimum receive interval";
          }
          leaf multiplier {
            type union {
              type string {
                pattern "<.*>|$.*";
              }
              type uint32 {
                range "1 .. 255";
              }
            }
            default "3";
            description
              "Detection time multiplier";
          }
          leaf inline-disable {
            type empty;
            description
              "Disable inline mode for this BFD session";
          }
          leaf pdu-size {
            type union {
              type string {
                pattern "<.*>|$.*";
              }
              type uint32 {
                range "24 .. 16000";
              }
            }
            default "24";
            description
              "BFD transport protocol payload size";
          }
          choice adaptation-choice {
            case case_1 {
              leaf no-adaptation {
                type empty;
                description
                  "Disable adaptation";
              }
            }
          }
          container transmit-interval {
            description
              "Transmit-interval options";
            uses apply-advanced;
            leaf minimum-interval {
              type union {
                type string {
                  pattern "<.*>|$.*";
                }
                type uint32 {
                  range "1 .. 255000";
                }
              }
              units "milliseconds";
              description
                "Minimum transmit interval";
            }
            leaf threshold {
              type union {
                type uint32;
                type string {
                  pattern "<.*>|$.*";
                }
              }
              units "milliseconds";
              description
                "High transmit interval triggering a trap";
            }
          }
          container detection-time {
            description
              "Detection-time options";
            uses apply-advanced;
            leaf threshold {
              type union {
                type uint32;
                type string {
                  pattern "<.*>|$.*";
                }
              }
              units "milliseconds";
              description
                "High detection-time triggering a trap";
            }
          }
          leaf neighbor {
            type jt:ipaddr;
            description
              "BFD neighbor address";
          }
        }
      }
    }
    container router-advertisement {
      description
        "IPv6 router advertisement options";
      uses apply-advanced;
      container traceoptions {
        description
          "Trace options for router advertisement";
        uses apply-advanced;
        container file {
          description
            "Trace file options";
          leaf filename {
            type string {
              length "1 .. 1024";
            }
            description
              "Name of file in which to write trace information";
          }
          leaf replace {
            type empty;
            status deprecated;
            description
              "Replace trace file rather than appending to it";
          }
          leaf size {
            type string;
            description
              "Maximum trace file size";
          }
          leaf files {
            type union {
              type string {
                pattern "<.*>|$.*";
              }
              type uint32 {
                range "2 .. 1000";
              }
            }
            default "10";
            description
              "Maximum number of trace files";
          }
          leaf no-stamp {
            type empty;
            status deprecated;
            description
              "Do not timestamp trace file";
          }
          choice world-readable-choice {
            leaf world-readable {
              type empty;
              description
                "Allow any user to read the log file";
            }
            leaf no-world-readable {
              type empty;
              description
                "Don't allow any user to read the log file";
            }
          }
        }
        list flag {
          key "name";
          ordered-by user;
          description
            "Tracing parameters";
          leaf name {
            type enumeration {
              enum "route" {
                description
                  "Trace routing information";
              }
              enum "normal" {
                description
                  "Trace normal events";
              }
              enum "general" {
                description
                  "Trace general events";
              }
              enum "state" {
                description
                  "Trace state transitions";
              }
              enum "policy" {
                description
                  "Trace policy processing";
              }
              enum "task" {
                description
                  "Trace routing protocol task processing";
              }
              enum "timer" {
                description
                  "Trace routing protocol timer processing";
              }
              enum "all" {
                description
                  "Trace everything";
              }
            }
          }
        }
      }
      list interface {
        key "name";
        ordered-by user;
        description
          "Interfaces on which to configure router advertisement";
        leaf name {
          type string;
        }
        uses apply-advanced;
      }
    }
    container router-discovery {
      description
        "ICMP router discovery options";
      uses juniper-protocols-router-discovery;
    }
    container isis {
      description
        "IS-IS options";
      uses juniper-protocols-isis;
    }
    list isis-instance {
      key "name";
      ordered-by user;
      description
        "Multi-instance IS-IS configuration";
      leaf name {
        type string;
        description
          "IS-IS instance name";
      }
      leaf link-state-instance-id {
        type union {
          type string {
            pattern "<.*>|$.*";
          }
          type uint64 {
            range "1 .. 65535";
          }
        }
        description
          "Link State Instance Identifier";
      }
      uses apply-advanced;
      list interface {
        key "name";
        description
          "Interface configuration";
        leaf name {
          type union {
            type jt:interface-name;
            type string {
              pattern "<.*>|$.*";
            }
          }
          description
            "Interface name";
        }
        uses apply-advanced;
        container ldp-synchronization {
          presence "enable ldp-synchronization";
          description
            "Advertise maximum metric until LDP is operational";
          uses ldp-sync-obj;
        }
        list level {
          key "name";
          ordered-by user;
          description
            "Configure levels on this interface";
          leaf name {
            type union {
              type string {
                pattern "<.*>|$.*";
              }
              type uint32 {
                range "1 .. 2";
              }
            }
            description
              "IS-IS level number";
          }
          uses apply-advanced;
          leaf te-metric {
            type union {
              type string {
                pattern "<.*>|$.*";
              }
              type uint32 {
                range "0 .. 16777215";
              }
            }
            description
              "Traffic engineering metric";
          }
          leaf no-advertise-adjacency-segment {
            type empty;
            description
              "Do not advertise an adjacency segment for this level";
          }
          container ipv4-adjacency-segment {
            description
              "Configure ipv4 adjacency segment";
            uses apply-advanced;
            container protected {
              description
                "Adjacency SID is eligible for protection";
              choice adjsid-type {
                case case_1 {
                  container index {
                    description
                      "Adjacency SID indexed from SRGB";
                    leaf index-number {
                      type union {
                        type string {
                          pattern "<.*>|$.*";
                        }
                        type uint32 {
                          range "0 .. 1048575";
                        }
                      }
                    }
                  }
                }
                case case_2 {
                  leaf label {
                    type union {
                      type string {
                        pattern "<.*>|$.*";
                      }
                      type uint32 {
                        range "16 .. 1048575";
                      }
                    }
                    description
                      "Adjacency SID from static label pool";
                  }
                }
                case case_3 {
                  leaf dynamic {
                    type empty;
                    description
                      "Dynamically allocate an adjacency segment";
                  }
                }
              }
            }
            container unprotected {
              description
                "Adjacency SID uneligible for protection";
              choice adjsid-type {
                case case_1 {
                  container index {
                    description
                      "Adjacency SID indexed from SRGB";
                    leaf index-number {
                      type union {
                        type string {
                          pattern "<.*>|$.*";
                        }
                        type uint32 {
                          range "0 .. 1048575";
                        }
                      }
                    }
                  }
                }
                case case_2 {
                  leaf label {
                    type union {
                      type string {
                        pattern "<.*>|$.*";
                      }
                      type uint32 {
                        range "16 .. 1048575";
                      }
                    }
                    description
                      "Adjacency SID from static label pool";
                  }
                }
                case case_3 {
                  leaf dynamic {
                    type empty;
                    description
                      "Dynamically allocate an adjacency segment";
                  }
                }
              }
            }
          }
          container ipv6-adjacency-segment {
            description
              "Configure ipv6 adjacency segment";
            uses apply-advanced;
            container protected {
              description
                "Adjacency SID is eligible for protection";
              choice adjsid-type {
                case case_1 {
                  container index {
                    description
                      "Adjacency SID indexed from SRGB";
                    leaf index-number {
                      type union {
                        type string {
                          pattern "<.*>|$.*";
                        }
                        type uint32 {
                          range "0 .. 1048575";
                        }
                      }
                    }
                  }
                }
                case case_2 {
                  leaf label {
                    type union {
                      type string {
                        pattern "<.*>|$.*";
                      }
                      type uint32 {
                        range "16 .. 1048575";
                      }
                    }
                    description
                      "Adjacency SID from static label pool";
                  }
                }
                case case_3 {
                  leaf dynamic {
                    type empty;
                    description
                      "Dynamically allocate an adjacency segment";
                  }
                }
              }
            }
            container unprotected {
              description
                "Adjacency SID uneligible for protection";
              choice adjsid-type {
                case case_1 {
                  container index {
                    description
                      "Adjacency SID indexed from SRGB";
                    leaf index-number {
                      type union {
                        type string {
                          pattern "<.*>|$.*";
                        }
                        type uint32 {
                          range "0 .. 1048575";
                        }
                      }
                    }
                  }
                }
                case case_2 {
                  leaf label {
                    type union {
                      type string {
                        pattern "<.*>|$.*";
                      }
                      type uint32 {
                        range "16 .. 1048575";
                      }
                    }
                    description
                      "Adjacency SID from static label pool";
                  }
                }
                case case_3 {
                  leaf dynamic {
                    type empty;
                    description
                      "Dynamically allocate an adjacency segment";
                  }
                }
              }
            }
          }
          container srv6-adjacency-segment {
            description
              "Configure srv6 adjacency segment";
            uses apply-advanced;
            container unprotected {
              presence "enable unprotected";
              description
                "SRv6 Adjacency segment is uneligible for protection";
              uses apply-advanced;
              list locator {
                key "name";
                ordered-by user;
                description
                  "Locator to bind SRv6 adjacency segment";
                leaf name {
                  type string;
                  mandatory true;
                  description
                    "Locator name";
                }
                uses apply-advanced;
                list end-x-sid {
                  key "name";
                  ordered-by user;
                  description
                    "Endpoint 128 bit address";
                  leaf name {
                    type jt:ipv6addr;
                  }
                  uses apply-advanced;
                }
                container micro-adjacency-sid {
                  presence "enable micro-adjacency-sid";
                  description
                    "Micro-adjacency-SID";
                  uses apply-advanced;
                  leaf static-sid {
                    type union {
                      type uint32;
                      type string {
                        pattern "<.*>|$.*";
                      }
                    }
                    description
                      "Static micro-adjacency-SID";
                  }
                }
                container dynamic-end-x-sid {
                  presence "enable dynamic-end-x-sid";
                  description
                    "Allocate end-x-SID dynamically";
                  uses apply-advanced;
                  container flavor {
                    presence "enable flavor";
                    description
                      "Configure end-x-SID flavor";
                    uses apply-advanced;
                    leaf psp {
                      type empty;
                      description
                        "Penultimate segment pop of the SRH";
                    }
                    leaf usp {
                      type empty;
                      description
                        "Ultimate segment pop of the SRH";
                    }
                    leaf usd {
                      type empty;
                      description
                        "Ultimate segment decapsulation";
                    }
                  }
                }
              }
            }
          }
          list lan-neighbor {
            key "name";
            ordered-by user;
            description
              "Configuration specific to a LAN neighbor";
            leaf name {
              type jt:sysid;
              description
                "Neighbor's sysid";
            }
            uses apply-advanced;
            container ipv4-adjacency-segment {
              description
                "Configure ipv4 adjacency segment";
              uses apply-advanced;
              container protected {
                description
                  "Adjacency SID is eligible for protection";
                choice adjsid-type {
                  case case_1 {
                    container index {
                      description
                        "Adjacency SID indexed from SRGB";
                      leaf index-number {
                        type union {
                          type string {
                            pattern "<.*>|$.*";
                          }
                          type uint32 {
                            range "0 .. 1048575";
                          }
                        }
                      }
                    }
                  }
                  case case_2 {
                    leaf label {
                      type union {
                        type string {
                          pattern "<.*>|$.*";
                        }
                        type uint32 {
                          range "16 .. 1048575";
                        }
                      }
                      description
                        "Adjacency SID from static label pool";
                    }
                  }
                  case case_3 {
                    leaf dynamic {
                      type empty;
                      description
                        "Dynamically allocate an adjacency segment";
                    }
                  }
                }
              }
              container unprotected {
                description
                  "Adjacency SID uneligible for protection";
                choice adjsid-type {
                  case case_1 {
                    container index {
                      description
                        "Adjacency SID indexed from SRGB";
                      leaf index-number {
                        type union {
                          type string {
                            pattern "<.*>|$.*";
                          }
                          type uint32 {
                            range "0 .. 1048575";
                          }
                        }
                      }
                    }
                  }
                  case case_2 {
                    leaf label {
                      type union {
                        type string {
                          pattern "<.*>|$.*";
                        }
                        type uint32 {
                          range "16 .. 1048575";
                        }
                      }
                      description
                        "Adjacency SID from static label pool";
                    }
                  }
                  case case_3 {
                    leaf dynamic {
                      type empty;
                      description
                        "Dynamically allocate an adjacency segment";
                    }
                  }
                }
              }
            }
            container ipv6-adjacency-segment {
              description
                "Configure ipv6 adjacency segment";
              uses apply-advanced;
              container protected {
                description
                  "Adjacency SID is eligible for protection";
                choice adjsid-type {
                  case case_1 {
                    container index {
                      description
                        "Adjacency SID indexed from SRGB";
                      leaf index-number {
                        type union {
                          type string {
                            pattern "<.*>|$.*";
                          }
                          type uint32 {
                            range "0 .. 1048575";
                          }
                        }
                      }
                    }
                  }
                  case case_2 {
                    leaf label {
                      type union {
                        type string {
                          pattern "<.*>|$.*";
                        }
                        type uint32 {
                          range "16 .. 1048575";
                        }
                      }
                      description
                        "Adjacency SID from static label pool";
                    }
                  }
                  case case_3 {
                    leaf dynamic {
                      type empty;
                      description
                        "Dynamically allocate an adjacency segment";
                    }
                  }
                }
              }
              container unprotected {
                description
                  "Adjacency SID uneligible for protection";
                choice adjsid-type {
                  case case_1 {
                    container index {
                      description
                        "Adjacency SID indexed from SRGB";
                      leaf index-number {
                        type union {
                          type string {
                            pattern "<.*>|$.*";
                          }
                          type uint32 {
                            range "0 .. 1048575";
                          }
                        }
                      }
                    }
                  }
                  case case_2 {
                    leaf label {
                      type union {
                        type string {
                          pattern "<.*>|$.*";
                        }
                        type uint32 {
                          range "16 .. 1048575";
                        }
                      }
                      description
                        "Adjacency SID from static label pool";
                    }
                  }
                  case case_3 {
                    leaf dynamic {
                      type empty;
                      description
                        "Dynamically allocate an adjacency segment";
                    }
                  }
                }
              }
            }
            container srv6-adjacency-segment {
              description
                "Configure srv6 adjacency segment";
              uses apply-advanced;
              container unprotected {
                presence "enable unprotected";
                description
                  "SRv6 Adjacency segment is uneligible for protection";
                uses apply-advanced;
                list locator {
                  key "name";
                  ordered-by user;
                  description
                    "Locator to bind SRv6 adjacency segment";
                  leaf name {
                    type string;
                    mandatory true;
                    description
                      "Locator name";
                  }
                  uses apply-advanced;
                  list end-x-sid {
                    key "name";
                    ordered-by user;
                    description
                      "Endpoint 128 bit address";
                    leaf name {
                      type jt:ipv6addr;
                    }
                    uses apply-advanced;
                    container flavor {
                      presence "enable flavor";
                      description
                        "Configure end-x-SID flavor";
                      uses apply-advanced;
                      leaf psp {
                        type empty;
                        description
                          "Penultimate segment pop of the SRH";
                      }
                      leaf usp {
                        type empty;
                        description
                          "Ultimate segment pop of the SRH";
                      }
                      leaf usd {
                        type empty;
                        description
                          "Ultimate segment decapsulation";
                      }
                    }
                  }
                  container micro-adjacency-sid {
                    presence "enable micro-adjacency-sid";
                    description
                      "Micro-adjacency-SID";
                    uses apply-advanced;
                    leaf static-sid {
                      type union {
                        type uint32;
                        type string {
                          pattern "<.*>|$.*";
                        }
                      }
                      description
                        "Static micro-adjacency-SID";
                    }
                  }
                  container dynamic-end-x-sid {
                    presence "enable dynamic-end-x-sid";
                    description
                      "Allocate end-x-SID dynamically";
                    uses apply-advanced;
                    container flavor {
                      presence "enable flavor";
                      description
                        "Configure end-x-SID flavor";
                      uses apply-advanced;
                      leaf psp {
                        type empty;
                        description
                          "Penultimate segment pop of the SRH";
                      }
                      leaf usp {
                        type empty;
                        description
                          "Ultimate segment pop of the SRH";
                      }
                      leaf usd {
                        type empty;
                        description
                          "Ultimate segment decapsulation";
                      }
                    }
                  }
                }
              }
            }
          }
          container post-convergence-lfa {
            presence "enable post-convergence-lfa";
            description
              "Configure backup along post convergence on this interface";
            uses apply-advanced;
          }
          choice enable-disable {
            case case_1 {
              leaf disable {
                type empty;
                description
                  "Disable IS-IS for this level";
              }
            }
          }
          leaf metric {
            type union {
              type string {
                pattern "<.*>|$.*";
              }
              type uint32 {
                range "0 .. 16777215";
              }
            }
            description
              "Metric for this level";
          }
          leaf ipv4-multicast-metric {
            type union {
              type string {
                pattern "<.*>|$.*";
              }
              type uint32 {
                range "0 .. 16777215";
              }
            }
            description
              "IPv4 multicast metric for this level";
          }
          leaf ipv6-unicast-metric {
            type union {
              type string {
                pattern "<.*>|$.*";
              }
              type uint32 {
                range "0 .. 16777215";
              }
            }
            description
              "IPv6 unicast metric for this level";
          }
          leaf ipv6-multicast-metric {
            type union {
              type string {
                pattern "<.*>|$.*";
              }
              type uint32 {
                range "0 .. 16777215";
              }
            }
            description
              "IPv6 multicast metric for this level";
          }
          list topology {
            key "name";
            ordered-by user;
            description
              "Topology specific attributes";
            leaf name {
              type enumeration {
                enum "default" {
                  description
                    "Default topology";
                }
                enum "ipv4-multicast" {
                  description
                    "IPv4 multicast topology";
                }
                enum "ipv6-unicast" {
                  description
                    "IPv6 unicast topology";
                }
                enum "ipv6-multicast" {
                  description
                    "IPv6 multicast topology";
                }
              }
              description
                "Topology name";
            }
            uses apply-advanced;
            leaf metric {
              type union {
                type string {
                  pattern "<.*>|$.*";
                }
                type uint32 {
                  range "0 .. 16777215";
                }
              }
              description
                "Topology metric";
            }
            container bandwidth-based-metrics {
              description
                "Configure bandwidth based metrics";
              uses apply-advanced;
              list bandwidth {
                key "name";
                description
                  "Bandwidth threshold";
                leaf name {
                  type string;
                }
                leaf metric {
                  type union {
                    type string {
                      pattern "<.*>|$.*";
                    }
                    type uint32 {
                      range "0 .. 16777215";
                    }
                  }
                  mandatory true;
                  description
                    "Metric associated with specified bandwidth";
                }
              }
            }
          }
          leaf authentication-key {
            type jt:unreadable;
            status deprecated;
            description
              "Authentication key (password)";
          }
          leaf authentication-type {
            type enumeration {
              enum "md5" {
                status deprecated;
                description
                  "MD5 authentication";
              }
              enum "simple" {
                status deprecated;
                description
                  "Simple password authentication";
              }
            }
            status deprecated;
            description
              "Authentication type";
          }
          leaf hello-authentication-key {
            type jt:unreadable;
            description
              "Authentication key (password) for hello packets";
          }
          leaf hello-authentication-type {
            type enumeration {
              enum "md5" {
                description
                  "MD5 authentication";
              }
              enum "simple" {
                description
                  "Simple password authentication";
              }
            }
            description
              "Authentication type for hello packets";
          }
          leaf hello-authentication-key-chain {
            type string {
              length "1 .. 128";
            }
            description
              "Key chain name";
          }
          leaf hello-interval {
            type union {
              type string {
                pattern "<.*>|$.*";
              }
              type uint32 {
                range "1 .. 21845";
              }
            }
            units "seconds";
            description
              "Interval between hello packet transmissions";
          }
          leaf hold-time {
            type union {
              type string {
                pattern "<.*>|$.*";
              }
              type uint32 {
                range "1 .. 65535";
              }
            }
            units "seconds";
            description
              "Time after which neighbors think the interface is down";
          }
          leaf priority {
            type union {
              type string {
                pattern "<.*>|$.*";
              }
              type uint32 {
                range "0 .. 127";
              }
            }
            description
              "Designated router election priority";
          }
          container flood-reflector {
            presence "enable flood-reflector";
            description
              "Configure interface as flood-reflector";
            uses apply-advanced;
            leaf cluster-id {
              type union {
                type string {
                  pattern "<.*>|$.*";
                }
                type uint32 {
                  range "1 .. 4294967295";
                }
              }
              description
                "Cluster-ID";
            }
          }
          container passive {
            presence "enable passive";
            description
              "Do not run IS-IS at this level, but advertise it";
            uses apply-advanced;
            leaf remote-node-iso {
              type jt:sysid;
              description
                "ISO System-ID of the remote node";
            }
            leaf remote-node-id {
              type jt:ipv4addr;
              description
                "Remote address of the link";
            }
          }
          leaf strict-bfd-old {
            type empty;
            description
              "Enable strict bfd over this interface";
          }
        }
        leaf delay-metric {
          type union {
            type string {
              pattern "<.*>|$.*";
            }
            type uint32 {
              range "0 .. 16777215";
            }
          }
          units "microseconds";
          description
            "Delay metric";
        }
        container delay-measurement {
          presence "enable delay-measurement";
          description
            "Enable delay measurement";
          uses apply-advanced;
          leaf probe-interval {
            type union {
              type string {
                pattern "<.*>|$.*";
              }
              type uint32 {
                range "1 .. 255";
              }
            }
            units "seconds";
            description
              "Probe interval";
          }
          leaf probe-count {
            type union {
              type string {
                pattern "<.*>|$.*";
              }
              type uint32 {
                range "1 .. 15";
              }
            }
            description
              "Probe count";
          }
          container normalize {
            description
              "Normalize Measured Link Delay";
            leaf interval {
              type union {
                type string {
                  pattern "<.*>|$.*";
                }
                type uint32 {
                  range "1 .. 5000000";
                }
              }
              units "microseconds";
              mandatory true;
              description
                "The value of the normalized interval in microseconds.";
            }
            leaf offset {
              type union {
                type string {
                  pattern "<.*>|$.*";
                }
                type uint32 {
                  range "1 .. 5000000";
                }
              }
              units "microseconds";
              mandatory true;
              description
                "The value of the normalized offset in microseconds (Must be < normalized interval).";
            }
          }
          container advertisement {
            description
              "Delay advertisement";
            uses apply-advanced;
            container periodic {
              description
                "Periodic advertisement parameters";
              uses apply-advanced;
              leaf threshold {
                type union {
                  type string {
                    pattern "<.*>|$.*";
                  }
                  type uint32 {
                    range "0 .. 100";
                  }
                }
                units "percentage";
                description
                  "Threshold";
              }
              leaf interval {
                type union {
                  type string {
                    pattern "<.*>|$.*";
                  }
                  type uint32 {
                    range "30 .. 3600";
                  }
                }
                units "seconds";
                description
                  "Interval";
              }
            }
            container accelerated {
              presence "enable accelerated";
              description
                "Accelerated advertisement parameters";
              uses apply-advanced;
              leaf threshold {
                type union {
                  type string {
                    pattern "<.*>|$.*";
                  }
                  type uint32 {
                    range "0 .. 100";
                  }
                }
                units "percentage";
                description
                  "Threshold";
              }
            }
          }
        }
        leaf no-advertise-adjacency-segment {
          type empty;
          description
            "Do not advertise an adjacency segment for this interface";
        }
        choice protection-type {
          case case_1 {
            leaf link-protection {
              type empty;
              description
                "Protect interface from link faults only";
            }
          }
          case case_2 {
            leaf node-link-protection {
              type empty;
              description
                "Protect interface from both link and node faults";
            }
          }
        }
        leaf no-eligible-backup {
          type empty;
          description
            "Not eligible for backup traffic from protected interfaces";
        }
        leaf no-eligible-remote-backup {
          type empty;
          description
            "Not eligible for Remote-LFA backup traffic from protected interfaces";
        }
        container link-degradation-threshold {
          presence "enable link-degradation-threshold";
          description
            "Link up and down thresholds (in %) for proactive link protection";
          leaf link-down {
            type union {
              type string {
                pattern "<.*>|$.*";
              }
              type uint32 {
                range "0 .. 100";
              }
            }
            mandatory true;
            description
              "Signal degradation threshold above which link marked down";
          }
          leaf link-up {
            type union {
              type string {
                pattern "<.*>|$.*";
              }
              type uint32 {
                range "0 .. 100";
              }
            }
            mandatory true;
            description
              "Signal degradation threshold below which link is marked up.";
          }
        }
        choice enable-disable {
          case case_1 {
            leaf disable {
              type empty;
              description
                "Disable IS-IS on this interface";
            }
          }
        }
        leaf authentication-key {
          type jt:unreadable;
          status deprecated;
          description
            "Authentication key (password)";
        }
        leaf authentication-type {
          type enumeration {
            enum "md5" {
              status deprecated;
              description
                "MD5 authentication";
            }
            enum "simple" {
              status deprecated;
              description
                "Simple password authentication";
            }
          }
          status deprecated;
          description
            "Authentication type";
        }
        leaf flood-group {
          type string;
          description
            "ISO Area that this interface should send LSPs to";
        }
        leaf hello-authentication-key {
          type jt:unreadable;
          status deprecated;
          description
            "Authentication key (password) for hello packets";
        }
        leaf hello-authentication-type {
          type enumeration {
            enum "md5" {
              status deprecated;
              description
                "MD5 authentication";
            }
            enum "simple" {
              status deprecated;
              description
                "Simple password authentication";
            }
          }
          status deprecated;
          description
            "Authentication type for hello packets";
        }
        leaf hello-padding-type {
          type enumeration {
            enum "strict" {
              description
                "Padding for all adjacency states";
            }
            enum "adaptive" {
              description
                "Padding until state of neighbor adjacency is 'up'";
            }
            enum "loose" {
              description
                "Padding until state of adjacency is 'initializing'";
            }
            enum "disable" {
              description
                "Do not add any padding for hello packets";
            }
          }
          default "loose";
          description
            "Type of padding for hello packets";
        }
        leaf interface-group-holddown-delay {
          type union {
            type string {
              pattern "<.*>|$.*";
            }
            type uint32 {
              range "0 .. 60";
            }
          }
          units "seconds";
          description
            "Time to wait before including in BBM calculation";
        }
        leaf max-hello-size {
          type union {
            type string {
              pattern "<.*>|$.*";
            }
            type uint32 {
              range "512 .. 16000";
            }
          }
          description
            "Maximum size allowed for ISIS Hello PDUs";
        }
        leaf lsp-interval {
          type union {
            type string {
              pattern "<.*>|$.*";
            }
            type uint32 {
              range "1 .. 1000";
            }
          }
          units "milliseconds";
          default "100";
          description
            "Interval between LSP transmissions";
        }
        container csnp-interval {
          description
            "Rate of CSN packets (for LAN interfaces only)";
          choice csnp_interval_option {
            case case_1 {
              leaf csnp-interval-number {
                type union {
                  type string {
                    pattern "<.*>|$.*";
                  }
                  type uint32 {
                    range "1 .. 65535";
                  }
                }
                units "seconds";
                description
                  "Interval between CSN packets";
              }
            }
            case case_2 {
              leaf disable {
                type empty;
                description
                  "Do not send CSN packets on this interface";
              }
            }
          }
        }
        container strict-dual-isis {
          presence "enable strict-dual-isis";
          description
            "Enable dual isis if spf computation is required for both ipv4 and ipv6 family";
          uses apply-advanced;
          leaf holdown {
            type union {
              type string {
                pattern "<.*>|$.*";
              }
              type uint32 {
                range "1 .. 65535";
              }
            }
            default "12";
            status deprecated;
            description
              "Time to wait for ipv4 and ipv6 connectivity";
          }
          leaf holddown {
            type union {
              type string {
                pattern "<.*>|$.*";
              }
              type uint32 {
                range "1 .. 65535";
              }
            }
            default "12";
            description
              "Time to wait for ipv4 and ipv6 connectivity";
          }
        }
        container mesh-group {
          description
            "Add the interface to a mesh group";
          choice mesh_group_option {
            case case_1 {
              leaf mesh-group-number {
                type union {
                  type uint32;
                  type string {
                    pattern "<.*>|$.*";
                  }
                }
                description
                  "Mesh group number for this interface";
              }
            }
            case case_2 {
              leaf blocked {
                type empty;
                description
                  "Do not flood new LSPs on this interface";
              }
            }
          }
        }
        leaf point-to-point {
          type empty;
          description
            "Treat interface as point to point";
        }
        container passive {
          presence "enable passive";
          description
            "Do not run IS-IS, but advertise it";
          uses apply-advanced;
          leaf remote-node-iso {
            type jt:sysid;
            description
              "ISO System-ID of the remote node";
          }
          leaf remote-node-id {
            type jt:ipv4addr;
            description
              "Remote address of the link";
          }
        }
        leaf checksum {
          type empty;
          description
            "Enable checksum for packets on this interface";
        }
        leaf no-unicast-topology {
          type empty;
          description
            "Do not include this interface in the unicast topology";
        }
        leaf no-ipv4-multicast {
          type empty;
          description
            "Do not include this interface in the IPv4 multicast topology";
        }
        leaf no-ipv6-unicast {
          type empty;
          description
            "Do not include this interface in the IPv6 unicast topology";
        }
        leaf no-ipv6-multicast {
          type empty;
          description
            "Do not include this interface in the IPv6 multicast topology";
        }
        leaf no-adjacency-down-notification {
          type empty;
          description
            "Do not inform other protocols about adjacency down events";
        }
        container bfd-liveness-detection {
          status deprecated;
          description
            "Bidirectional Forwarding Detection options";
          uses apply-advanced;
          leaf version {
            type enumeration {
              enum "0" {
                description
                  "BFD version 0 (deprecated)";
              }
              enum "1" {
                description
                  "BFD version 1";
              }
              enum "automatic" {
                description
                  "Choose BFD version automatically";
              }
            }
            default "automatic";
            description
              "BFD protocol version number";
          }
          leaf minimum-interval {
            type union {
              type string {
                pattern "<.*>|$.*";
              }
              type uint32 {
                range "1 .. 255000";
              }
            }
            units "milliseconds";
            description
              "Minimum transmit and receive interval";
          }
          leaf minimum-transmit-interval {
            type union {
              type string {
                pattern "<.*>|$.*";
              }
              type uint32 {
                range "1 .. 255000";
              }
            }
            units "milliseconds";
            status deprecated;
            description
              "Minimum transmit interval";
          }
          leaf minimum-receive-interval {
            type union {
              type string {
                pattern "<.*>|$.*";
              }
              type uint32 {
                range "1 .. 255000";
              }
            }
            units "milliseconds";
            description
              "Minimum receive interval";
          }
          leaf multiplier {
            type union {
              type string {
                pattern "<.*>|$.*";
              }
              type uint32 {
                range "1 .. 255";
              }
            }
            default "3";
            description
              "Detection time multiplier";
          }
          leaf inline-disable {
            type empty;
            description
              "Disable inline mode for this BFD session";
          }
          leaf pdu-size {
            type union {
              type string {
                pattern "<.*>|$.*";
              }
              type uint32 {
                range "24 .. 16000";
              }
            }
            default "24";
            description
              "BFD transport protocol payload size";
          }
          choice adaptation-choice {
            case case_1 {
              leaf no-adaptation {
                type empty;
                description
                  "Disable adaptation";
              }
            }
          }
          container transmit-interval {
            description
              "Transmit-interval options";
            uses apply-advanced;
            leaf minimum-interval {
              type union {
                type string {
                  pattern "<.*>|$.*";
                }
                type uint32 {
                  range "1 .. 255000";
                }
              }
              units "milliseconds";
              description
                "Minimum transmit interval";
            }
            leaf threshold {
              type union {
                type uint32;
                type string {
                  pattern "<.*>|$.*";
                }
              }
              units "milliseconds";
              description
                "High transmit interval triggering a trap";
            }
          }
          container detection-time {
            description
              "Detection-time options";
            uses apply-advanced;
            leaf threshold {
              type union {
                type uint32;
                type string {
                  pattern "<.*>|$.*";
                }
              }
              units "milliseconds";
              description
                "High detection-time triggering a trap";
            }
          }
          container authentication {
            description
              "Authentication options";
            uses apply-advanced;
            leaf key-chain {
              type string;
              description
                "Key chain name";
            }
            leaf algorithm {
              type enumeration {
                enum "simple-password" {
                  description
                    "Simple password";
                }
                enum "keyed-md5" {
                  description
                    "Keyed message Digest 5";
                }
                enum "meticulous-keyed-md5" {
                  description
                    "Meticulous keyed message Digest 5";
                }
                enum "keyed-sha-1" {
                  description
                    "Keyed secure hash algorithm (SHA1) ";
                }
                enum "meticulous-keyed-sha-1" {
                  description
                    "Meticulous keyed secure hash algorithm (SHA1) ";
                }
              }
              description
                "Algorithm name";
            }
            leaf loose-check {
              type empty;
              description
                "Verify authentication only if authentication is negotiated";
            }
          }
        }
        list family {
          key "name";
          ordered-by user;
          description
            "Address family specific interface attributes";
          leaf name {
            type enumeration {
              enum "inet" {
                description
                  "IPv4 family";
              }
              enum "inet6" {
                description
                  "IPv6 family";
              }
            }
          }
          uses apply-advanced;
          container bfd-liveness-detection {
            description
              "Bidirectional Forwarding Detection options";
            uses apply-advanced;
            leaf version {
              type enumeration {
                enum "0" {
                  description
                    "BFD version 0 (deprecated)";
                }
                enum "1" {
                  description
                    "BFD version 1";
                }
                enum "automatic" {
                  description
                    "Choose BFD version automatically";
                }
              }
              default "automatic";
              description
                "BFD protocol version number";
            }
            leaf minimum-interval {
              type union {
                type string {
                  pattern "<.*>|$.*";
                }
                type uint32 {
                  range "1 .. 255000";
                }
              }
              units "milliseconds";
              description
                "Minimum transmit and receive interval";
            }
            leaf minimum-transmit-interval {
              type union {
                type string {
                  pattern "<.*>|$.*";
                }
                type uint32 {
                  range "1 .. 255000";
                }
              }
              units "milliseconds";
              status deprecated;
              description
                "Minimum transmit interval";
            }
            leaf minimum-receive-interval {
              type union {
                type string {
                  pattern "<.*>|$.*";
                }
                type uint32 {
                  range "1 .. 255000";
                }
              }
              units "milliseconds";
              description
                "Minimum receive interval";
            }
            leaf multiplier {
              type union {
                type string {
                  pattern "<.*>|$.*";
                }
                type uint32 {
                  range "1 .. 255";
                }
              }
              default "3";
              description
                "Detection time multiplier";
            }
            leaf inline-disable {
              type empty;
              description
                "Disable inline mode for this BFD session";
            }
            leaf pdu-size {
              type union {
                type string {
                  pattern "<.*>|$.*";
                }
                type uint32 {
                  range "24 .. 16000";
                }
              }
              default "24";
              description
                "BFD transport protocol payload size";
            }
            choice adaptation-choice {
              case case_1 {
                leaf no-adaptation {
                  type empty;
                  description
                    "Disable adaptation";
                }
              }
            }
            container transmit-interval {
              description
                "Transmit-interval options";
              uses apply-advanced;
              leaf minimum-interval {
                type union {
                  type string {
                    pattern "<.*>|$.*";
                  }
                  type uint32 {
                    range "1 .. 255000";
                  }
                }
                units "milliseconds";
                description
                  "Minimum transmit interval";
              }
              leaf threshold {
                type union {
                  type uint32;
                  type string {
                    pattern "<.*>|$.*";
                  }
                }
                units "milliseconds";
                description
                  "High transmit interval triggering a trap";
              }
            }
            container detection-time {
              description
                "Detection-time options";
              uses apply-advanced;
              leaf threshold {
                type union {
                  type uint32;
                  type string {
                    pattern "<.*>|$.*";
                  }
                }
                units "milliseconds";
                description
                  "High detection-time triggering a trap";
              }
            }
            container authentication {
              description
                "Authentication options";
              uses apply-advanced;
              leaf key-chain {
                type string;
                description
                  "Key chain name";
              }
              leaf algorithm {
                type enumeration {
                  enum "simple-password" {
                    description
                      "Simple password";
                  }
                  enum "keyed-md5" {
                    description
                      "Keyed message Digest 5";
                  }
                  enum "meticulous-keyed-md5" {
                    description
                      "Meticulous keyed message Digest 5";
                  }
                  enum "keyed-sha-1" {
                    description
                      "Keyed secure hash algorithm (SHA1) ";
                  }
                  enum "meticulous-keyed-sha-1" {
                    description
                      "Meticulous keyed secure hash algorithm (SHA1) ";
                  }
                }
                description
                  "Algorithm name";
              }
              leaf loose-check {
                type empty;
                description
                  "Verify authentication only if authentication is negotiated";
              }
            }
            container echo {
              description
                "Echo mode parameters";
              uses apply-advanced;
              leaf minimum-interval {
                type union {
                  type string {
                    pattern "<.*>|$.*";
                  }
                  type uint32 {
                    range "100 .. 255000";
                  }
                }
                units "milliseconds";
                description
                  "Minimum transmit and receive interval";
              }
            }
            container echo-lite {
              description
                "Echo-lite more parameters";
              uses apply-advanced;
              leaf minimum-interval {
                type union {
                  type string {
                    pattern "<.*>|$.*";
                  }
                  type uint32 {
                    range "100 .. 255000";
                  }
                }
                units "milliseconds";
                description
                  "Minimum transmit and receive interval";
              }
            }
            leaf holddown-interval {
              type union {
                type string {
                  pattern "<.*>|$.*";
                }
                type uint32 {
                  range "0 .. 255000";
                }
              }
              units "milliseconds";
              description
                "Time to hold the session-UP notification to the client";
            }
          }
        }
        leaf strict-bfd {
          type empty;
          description
            "Enable strict bfd over this interface";
        }
      }
      list bier-sub-domain {
        key "name";
        description
          "Configuration of bier subdomain";
        leaf name {
          type union {
            type uint8;
            type string {
              pattern "<.*>|$.*";
            }
          }
          description
            "Enable bier subdomain id";
        }
      }
      container prefix-unreachable {
        presence "enable prefix-unreachable";
        description
          "Configure unreachable prefix advertisement parameters";
        uses apply-advanced;
        container originator {
          description
            "Parameters for originating unreachable prefix advertisements";
          uses apply-advanced;
          leaf unplanned-lifetime {
            type union {
              type string {
                pattern "<.*>|$.*";
              }
              type uint32 {
                range "30 .. 65535";
              }
            }
            units "seconds";
            description
              "Lifetime of unplanned UPA";
          }
          leaf metric {
            type union {
              type string {
                pattern "<.*>|$.*";
              }
              type uint32 {
                range "4261412865 .. 4294967295";
              }
            }
            description
              "Metric value of unplanned UPA";
          }
          leaf max-advertisements {
            type union {
              type string {
                pattern "<.*>|$.*";
              }
              type uint32 {
                range "1 .. 10000";
              }
            }
            description
              "Maximum UPAs that can be originated at any point of time";
          }
        }
        leaf use-only-for-leaking {
          type empty;
          description
            "Do not use this UPA route for resolution";
        }
      }
      container source-packet-routing {
        presence "enable source-packet-routing";
        description
          "Enable Source Packet Routing (SPRING)";
        uses apply-advanced;
        container adjacency-segment {
          description
            "Configure attributes for Adjacency Segments in SPRING";
          uses apply-advanced;
          leaf hold-time {
            type union {
              type string {
                pattern "<.*>|$.*";
              }
              type uint32 {
                range "180000 .. 900000";
              }
            }
            description
              "Duration(ms) for which adjacency segments will be retained after isolating from an interface";
          }
        }
        container udp-tunneling {
          description
            "Enable SR over UDP feature";
          uses apply-advanced;
          leaf encapsulation {
            type empty;
            description
              "Enable UDP Tunnel Encapsulation";
          }
          leaf decapsulation {
            type empty;
            description
              "Enable UDP Tunnel decapsulation";
          }
        }
        container srgb {
          description
            "Set the SRGB global block in SPRING";
          leaf start-label {
            type union {
              type string {
                pattern "<.*>|$.*";
              }
              type uint32 {
                range "16 .. 1048575";
              }
            }
            description
              "Start range for SRGB label block";
          }
          leaf index-range {
            type union {
              type string {
                pattern "<.*>|$.*";
              }
              type uint32 {
                range "32 .. 1048559";
              }
            }
            description
              "Index to the SRGB start label block";
          }
        }
        container node-segment {
          description
            "Enable support for Node segments in SPRING";
          uses apply-advanced;
          leaf ipv4-index {
            type union {
              type string {
                pattern "<.*>|$.*";
              }
              type uint32 {
                range "0 .. 1048575";
              }
            }
            description
              "Set IPv4 Node Segment index";
          }
          leaf ipv6-index {
            type union {
              type string {
                pattern "<.*>|$.*";
              }
              type uint32 {
                range "0 .. 1048575";
              }
            }
            description
              "Set IPv6 Node Segment index";
          }
          leaf index-range {
            type union {
              type string {
                pattern "<.*>|$.*";
              }
              type uint32 {
                range "32 .. 16385";
              }
            }
            description
              "Set Range of Node Segment indices allowed";
          }
        }
        leaf-list flex-algorithm {
          type union {
            type string {
              pattern "<.*>|$.*";
            }
            type uint32 {
              range "128 .. 255";
            }
          }
          max-elements 16;
          description
            "Flex-algorithms we would like to participate in";
        }
        leaf use-flex-algorithm-metric-always {
          type empty;
          description
            "Use flex-algo prefix metric whenever available";
        }
        leaf strict-asla-based-flex-algorithm {
          type empty;
          description
            "Flex-Algorithm to ignore links not having ASLA sub-TLVs";
        }
        leaf new-capability-subtlv {
          type empty;
          description
            "Advertise all ranges in single spring capability subtlv";
        }
        leaf explicit-null {
          type empty;
          description
            "Set E and P bits in all Prefix SID advertisements";
        }
        leaf mapping-server {
          type string;
          description
            "Mapping server name";
        }
        leaf no-strict-spf {
          type empty;
          description
            " Disable strict spf algo 1 advertisement";
        }
        leaf no-binding-sid-leaking {
          type empty;
          description
            " Disable SRMS binding sid leaking";
        }
        leaf ldp-stitching {
          type empty;
          description
            "Enable SR to LDP stitching";
        }
        leaf entropy-label {
          type empty;
          description
            " Enable entropy label";
        }
        container srv6 {
          presence "enable srv6";
          description
            "Enable IPv6 Segment Routing (SRv6)";
          uses apply-advanced;
          list locator {
            key "name";
            ordered-by user;
            description
              "SRv6 Locator";
            leaf name {
              type string;
              mandatory true;
              description
                "Locator name";
            }
            uses apply-advanced;
            leaf anycast {
              type empty;
              description
                "Set A flag in the Prefix-Attribute sub-TLV";
            }
            list end-sid {
              key "name";
              ordered-by user;
              leaf name {
                type jt:ipv6addr;
              }
              uses apply-advanced;
            }
            container dynamic-end-sid {
              presence "enable dynamic-end-sid";
              description
                "Allocate end SID dynamically";
              uses apply-advanced;
              container flavor {
                presence "enable flavor";
                description
                  "Configure end-SID flavor";
                uses apply-advanced;
                leaf psp {
                  type empty;
                  description
                    "Penultimate segment pop of the SRH";
                }
                leaf usp {
                  type empty;
                  description
                    "Ultimate segment pop of the SRH";
                }
                leaf usd {
                  type empty;
                  description
                    "Ultimate segment decapsulation";
                }
              }
            }
            leaf micro-node-sid {
              type empty;
              description
                "Program and advertise micro-node-SID";
            }
          }
        }
      }
      list level {
        key "name";
        ordered-by user;
        description
          "Configure global level attributes";
        leaf name {
          type union {
            type string {
              pattern "<.*>|$.*";
            }
            type uint32 {
              range "1 .. 2";
            }
          }
          description
            "IS-IS level number";
        }
        uses apply-advanced;
        leaf labeled-preference {
          type union {
            type uint32;
            type string {
              pattern "<.*>|$.*";
            }
          }
          description
            "Preference of labeled IS-IS routes";
        }
        leaf srv6-preference {
          type union {
            type uint32;
            type string {
              pattern "<.*>|$.*";
            }
          }
          description
            "Preference of SRV6 IS-IS routes";
        }
        leaf flex-algorithm-preference {
          type union {
            type uint32;
            type string {
              pattern "<.*>|$.*";
            }
          }
          description
            "Preference of flex-algorithm L-ISIS routes";
        }
        container source-packet-routing {
          presence "enable source-packet-routing";
          description
            "Enable Source Packet Routing (SPRING)";
          uses apply-advanced;
          choice enable-disable {
            case case_1 {
              leaf disable {
                type empty;
                description
                  "Disable Source Packet Routing on this level";
              }
            }
          }
          leaf srms-preference {
            type union {
              type string {
                pattern "<.*>|$.*";
              }
              type uint32 {
                range "0 .. 255";
              }
            }
            description
              "Set SRMS preference value";
          }
        }
        choice enable-disable {
          case case_1 {
            leaf disable {
              type empty;
              description
                "Disable IS-IS on this level";
            }
          }
        }
        leaf authentication-key {
          type jt:unreadable;
          description
            "Authentication key (password)";
        }
        leaf authentication-type {
          type enumeration {
            enum "md5" {
              description
                "MD5 authentication";
            }
            enum "simple" {
              description
                "Simple password authentication";
            }
          }
          description
            "Authentication type";
        }
        leaf purge-originator {
          type enumeration {
            enum "self" {
              description
                "Add POI only for self-originated purge LSPs";
            }
            enum "empty" {
              description
                "Add POI for purge LSPs who do not have POI information";
            }
          }
          description
            "Add Purge Originator information";
        }
        leaf no-hello-authentication {
          type empty;
          description
            "Disable authentication for hello packets";
        }
        leaf no-csnp-authentication {
          type empty;
          description
            "Disable authentication for CSN packets";
        }
        leaf no-psnp-authentication {
          type empty;
          description
            "Disable authentication for PSN packets";
        }
        leaf no-lsp-authentication {
          type empty;
          description
            "Disable authentication for LSP packets";
        }
        leaf authentication-key-chain {
          type string {
            length "1 .. 128";
          }
          description
            "Key chain name";
        }
        leaf wide-metrics-only {
          type empty;
          description
            "Generate wide metrics only";
        }
        leaf preference {
          type union {
            type uint32;
            type string {
              pattern "<.*>|$.*";
            }
          }
          description
            "Preference of internal routes";
        }
        leaf external-preference {
          type union {
            type uint32;
            type string {
              pattern "<.*>|$.*";
            }
          }
          description
            "Preference of external routes";
        }
        leaf prefix-export-limit {
          type union {
            type string {
              pattern "<.*>|$.*";
            }
            type uint32 {
              range "0 .. 4294967295";
            }
          }
          description
            "Maximum number of external prefixes that can be exported";
        }
        leaf max-lsp-size {
          type union {
            type string {
              pattern "<.*>|$.*";
            }
            type uint32 {
              range "512 .. 9192";
            }
          }
          description
            "Maximum size allowed for LSPs";
        }
        container flood-reflector {
          description
            "Enable flood-reflector";
          uses apply-advanced;
          choice flood-reflector-choice {
            case case_1 {
              container reflector {
                description
                  "Configure this as a flood-reflector";
                uses apply-advanced;
                leaf cluster-id {
                  type union {
                    type string {
                      pattern "<.*>|$.*";
                    }
                    type uint32 {
                      range "1 .. 4294967295";
                    }
                  }
                  mandatory true;
                  description
                    "Cluster-ID";
                }
              }
            }
            case case_2 {
              leaf client {
                type empty;
                description
                  "Configure interface as flood-reflector client";
              }
            }
          }
        }
      }
      list interface-group {
        key "name";
        description
          "Interface grouping configuration";
        leaf name {
          type string;
          description
            "Interface group name";
        }
        uses apply-advanced;
        list level {
          key "name";
          ordered-by user;
          description
            "Configure levels on this interface-group";
          leaf name {
            type union {
              type string {
                pattern "<.*>|$.*";
              }
              type uint32 {
                range "1 .. 2";
              }
            }
            description
              "IS-IS level number";
          }
          uses apply-advanced;
          container ipv4-adjacency-segment {
            description
              "Configure ipv4 adjacency segment";
            uses apply-advanced;
            container protected {
              description
                "Adjacency SID is eligible for protection";
              choice adjsid-type {
                case case_1 {
                  container index {
                    description
                      "Adjacency SID indexed from SRGB";
                    leaf index-number {
                      type union {
                        type string {
                          pattern "<.*>|$.*";
                        }
                        type uint32 {
                          range "0 .. 1048575";
                        }
                      }
                    }
                  }
                }
                case case_2 {
                  leaf label {
                    type union {
                      type string {
                        pattern "<.*>|$.*";
                      }
                      type uint32 {
                        range "16 .. 1048575";
                      }
                    }
                    description
                      "Adjacency SID from static label pool";
                  }
                }
                case case_3 {
                  leaf dynamic {
                    type empty;
                    description
                      "Dynamically allocate an adjacency segment";
                  }
                }
              }
            }
            container unprotected {
              description
                "Adjacency SID uneligible for protection";
              choice adjsid-type {
                case case_1 {
                  container index {
                    description
                      "Adjacency SID indexed from SRGB";
                    leaf index-number {
                      type union {
                        type string {
                          pattern "<.*>|$.*";
                        }
                        type uint32 {
                          range "0 .. 1048575";
                        }
                      }
                    }
                  }
                }
                case case_2 {
                  leaf label {
                    type union {
                      type string {
                        pattern "<.*>|$.*";
                      }
                      type uint32 {
                        range "16 .. 1048575";
                      }
                    }
                    description
                      "Adjacency SID from static label pool";
                  }
                }
                case case_3 {
                  leaf dynamic {
                    type empty;
                    description
                      "Dynamically allocate an adjacency segment";
                  }
                }
              }
            }
          }
          container ipv6-adjacency-segment {
            description
              "Configure ipv6 adjacency segment";
            uses apply-advanced;
            container protected {
              description
                "Adjacency SID is eligible for protection";
              choice adjsid-type {
                case case_1 {
                  container index {
                    description
                      "Adjacency SID indexed from SRGB";
                    leaf index-number {
                      type union {
                        type string {
                          pattern "<.*>|$.*";
                        }
                        type uint32 {
                          range "0 .. 1048575";
                        }
                      }
                    }
                  }
                }
                case case_2 {
                  leaf label {
                    type union {
                      type string {
                        pattern "<.*>|$.*";
                      }
                      type uint32 {
                        range "16 .. 1048575";
                      }
                    }
                    description
                      "Adjacency SID from static label pool";
                  }
                }
                case case_3 {
                  leaf dynamic {
                    type empty;
                    description
                      "Dynamically allocate an adjacency segment";
                  }
                }
              }
            }
            container unprotected {
              description
                "Adjacency SID uneligible for protection";
              choice adjsid-type {
                case case_1 {
                  container index {
                    description
                      "Adjacency SID indexed from SRGB";
                    leaf index-number {
                      type union {
                        type string {
                          pattern "<.*>|$.*";
                        }
                        type uint32 {
                          range "0 .. 1048575";
                        }
                      }
                    }
                  }
                }
                case case_2 {
                  leaf label {
                    type union {
                      type string {
                        pattern "<.*>|$.*";
                      }
                      type uint32 {
                        range "16 .. 1048575";
                      }
                    }
                    description
                      "Adjacency SID from static label pool";
                  }
                }
                case case_3 {
                  leaf dynamic {
                    type empty;
                    description
                      "Dynamically allocate an adjacency segment";
                  }
                }
              }
            }
          }
          list topology {
            key "name";
            ordered-by user;
            description
              "Topology specific attributes";
            leaf name {
              type enumeration {
                enum "default" {
                  description
                    "Default topology";
                }
                enum "ipv4-multicast" {
                  description
                    "IPv4 multicast topology";
                }
                enum "ipv6-unicast" {
                  description
                    "IPv6 unicast topology";
                }
                enum "ipv6-multicast" {
                  description
                    "IPv6 multicast topology";
                }
              }
              description
                "Topology name";
            }
            uses apply-advanced;
            leaf metric {
              type union {
                type string {
                  pattern "<.*>|$.*";
                }
                type uint32 {
                  range "0 .. 16777215";
                }
              }
              description
                "Topology metric";
            }
            container bandwidth-based-metrics {
              description
                "Configure bandwidth based metrics";
              uses apply-advanced;
              list bandwidth {
                key "name";
                description
                  "Bandwidth threshold";
                leaf name {
                  type string;
                }
                leaf metric {
                  type union {
                    type string {
                      pattern "<.*>|$.*";
                    }
                    type uint32 {
                      range "0 .. 16777215";
                    }
                  }
                  mandatory true;
                  description
                    "Metric associated with specified bandwidth";
                }
              }
            }
          }
        }
        container link-group-protection {
          description
            "Configure link group protection";
          uses apply-advanced;
          leaf minimum-bandwidth {
            type string;
            description
              "Minimum bandwidth to carry traffic";
          }
          leaf revert-bandwidth {
            type string;
            description
              "Revert bandwidth to carry traffic";
          }
        }
        list interface {
          key "name";
          description
            "List interfaces for this group";
          leaf name {
            type union {
              type jt:interface-name;
              type string {
                pattern "<.*>|$.*";
              }
            }
            description
              "Interface name";
          }
          uses apply-advanced;
          leaf weight {
            type union {
              type string {
                pattern "<.*>|$.*";
              }
              type uint32 {
                range "1 .. 255";
              }
            }
            description
              "Interface weight for adjacency set";
          }
        }
      }
      container spf-options {
        description
          "Configure SPF attributes";
        uses apply-advanced;
        container microloop-avoidance {
          description
            "Configure microloop avoidance mechanisms";
          uses apply-advanced;
          container post-convergence-path {
            presence "enable post-convergence-path";
            description
              "Temporarily install post-convergence path for routes potentially affected by microloops";
            uses apply-advanced;
            leaf delay {
              type union {
                type string {
                  pattern "<.*>|$.*";
                }
                type uint32 {
                  range "500 .. 60000";
                }
              }
              units "milliseconds";
              description
                "Time after which temporary post-convergence paths are removed";
            }
            leaf maximum-labels {
              type union {
                type string {
                  pattern "<.*>|$.*";
                }
                type uint32 {
                  range "2 .. 8";
                }
              }
              description
                "Set maximum number of label supported for Micro-Loop-Avoidance calculations";
            }
            leaf maximum-srv6-sids {
              type union {
                type string {
                  pattern "<.*>|$.*";
                }
                type uint32 {
                  range "2 .. 12";
                }
              }
              description
                "Set maximum number of SRV6 SIDs supported for Micro-Loop-Avoidance calculations";
            }
          }
        }
        leaf delay {
          type union {
            type string {
              pattern "<.*>|$.*";
            }
            type uint32 {
              range "50 .. 1000";
            }
          }
          units "milliseconds";
          description
            "Time to wait before running an SPF";
        }
        leaf holddown {
          type union {
            type string {
              pattern "<.*>|$.*";
            }
            type uint32 {
              range "1000 .. 10000";
            }
          }
          units "milliseconds";
          description
            "Time to hold down before running an SPF";
        }
        leaf rapid-runs {
          type union {
            type string {
              pattern "<.*>|$.*";
            }
            type uint32 {
              range "1 .. 5";
            }
          }
          description
            "Number of rapid SPF runs before SPF holddown";
        }
        container multipath {
          description
            "Configure multipath options";
          uses apply-advanced;
          container weighted {
            description
              "Weighted multipath options";
            uses apply-advanced;
            leaf one-hop {
              type empty;
              description
                "Enable load balancing on onehop multipath based on interface bandwidth";
            }
          }
        }
      }
      container traceoptions {
        description
          "Trace options for IS-IS";
        uses apply-advanced;
        container file {
          description
            "Trace file options";
          leaf filename {
            type string {
              length "1 .. 1024";
            }
            description
              "Name of file in which to write trace information";
          }
          leaf replace {
            type empty;
            status deprecated;
            description
              "Replace trace file rather than appending to it";
          }
          leaf size {
            type string;
            description
              "Maximum trace file size";
          }
          leaf files {
            type union {
              type string {
                pattern "<.*>|$.*";
              }
              type uint32 {
                range "2 .. 1000";
              }
            }
            default "10";
            description
              "Maximum number of trace files";
          }
          leaf no-stamp {
            type empty;
            status deprecated;
            description
              "Do not timestamp trace file";
          }
          choice world-readable-choice {
            leaf world-readable {
              type empty;
              description
                "Allow any user to read the log file";
            }
            leaf no-world-readable {
              type empty;
              description
                "Don't allow any user to read the log file";
            }
          }
        }
        list flag {
          key "name";
          ordered-by user;
          description
            "Tracing parameters";
          leaf name {
            type enumeration {
              enum "post-convergence-lfa" {
                description
                  "Trace post-convergence-lfa related events";
              }
              enum "error" {
                description
                  "Trace errored packets";
              }
              enum "spf" {
                description
                  "Trace SPF events";
              }
              enum "packets" {
                description
                  "Trace IS-IS packets";
              }
              enum "hello" {
                description
                  "Trace hello packets";
              }
              enum "lsp" {
                description
                  "Trace link-state packets";
              }
              enum "psn" {
                description
                  "Trace partial sequence number (PSN) packets";
              }
              enum "csn" {
                description
                  "Trace complete sequence number (CSN) packets";
              }
              enum "layer2-map" {
                description
                  "Trace ARP/ND kernel state manipulation";
              }
              enum "lsp-generation" {
                description
                  "Trace LSP generation";
              }
              enum "graceful-restart" {
                description
                  "Trace graceful restart events";
              }
              enum "ldp-synchronization" {
                description
                  "Trace synchronization between IS-IS and LDP";
              }
              enum "nsr-synchronization" {
                description
                  "Trace NSR synchronization events";
              }
              enum "spring" {
                description
                  "Trace source packet routing";
              }
              enum "prefix-sid" {
                description
                  "Trace source packet routing, prefix-sids";
              }
              enum "flex-algorithm" {
                description
                  "Trace flex-algorithm related events";
              }
              enum "adj-sid" {
                description
                  "Trace adj-sid related events";
              }
              enum "route" {
                description
                  "Trace routing information";
              }
              enum "normal" {
                description
                  "Trace normal events";
              }
              enum "general" {
                description
                  "Trace general events";
              }
              enum "state" {
                description
                  "Trace state transitions";
              }
              enum "policy" {
                description
                  "Trace policy processing";
              }
              enum "task" {
                description
                  "Trace routing protocol task processing";
              }
              enum "timer" {
                description
                  "Trace routing protocol timer processing";
              }
              enum "srv6" {
                description
                  "Trace srv6 related events";
              }
              enum "rmopd" {
                description
                  "Trace rmopd interactions";
              }
              enum "mapping-server" {
                description
                  "Trace mapping server related events";
              }
              enum "prefix-unreachable" {
                description
                  "Trace unreachable prefix advertisement related events";
              }
              enum "all" {
                description
                  "Trace everything";
              }
            }
          }
          leaf send {
            type empty;
            description
              "Trace transmitted packets";
          }
          leaf receive {
            type empty;
            description
              "Trace received packets";
          }
          leaf detail {
            type empty;
            description
              "Trace detailed information";
          }
          leaf disable {
            type empty;
            description
              "Disable this trace flag";
          }
        }
      }
      container backup-spf-options {
        description
          "Configure backup SPF attributes";
        uses apply-advanced;
        container remote-backup-calculation {
          presence "enable remote-backup-calculation";
          description
            "Calculate Remote LFA backup nexthops";
          uses apply-advanced;
        }
        container use-post-convergence-lfa {
          presence "enable use-post-convergence-lfa";
          description
            "Calculate Post Convergence Backup Nexthops";
          uses apply-advanced;
          leaf maximum-labels {
            type union {
              type string {
                pattern "<.*>|$.*";
              }
              type uint32 {
                range "2 .. 8";
              }
            }
            description
              "Set maximum number of label supported for post convergence path calculations";
          }
          leaf maximum-srv6-sids {
            type union {
              type string {
                pattern "<.*>|$.*";
              }
              type uint32 {
                range "2 .. 12";
              }
            }
            description
              "Set maximum number of SRV6 SIDs for post convergence path calculations";
          }
        }
        container use-source-packet-routing {
          presence "enable use-source-packet-routing";
          description
            "Use SPRING routed paths for protection";
          uses apply-advanced;
        }
        leaf per-prefix-calculation {
          type empty;
          description
            "Calculate backup nexthops for non-best prefix originators";
        }
        leaf node-link-degradation {
          type empty;
          description
            "Degrade to link protection when nodelink protection not available";
        }
      }
      list context-identifier {
        key "name";
        ordered-by user;
        description
          "Configuration for advertisement of a context-identifier ";
        leaf name {
          type jt:ipprefix;
          description
            "Context identifier range";
        }
        uses apply-advanced;
        list level {
          key "name";
          ordered-by user;
          description
            "Configure global level attributes";
          leaf name {
            type union {
              type string {
                pattern "<.*>|$.*";
              }
              type uint32 {
                range "1 .. 2";
              }
            }
            description
              "IS-IS level number";
          }
          uses apply-advanced;
          choice enable-disable {
            case case_1 {
              leaf disable {
                type empty;
                description
                  "Disable advertisements to this level";
              }
            }
          }
        }
      }
      choice enable-disable {
        case case_1 {
          leaf disable {
            type empty;
            description
              "Disable IS-IS";
          }
        }
      }
      leaf-list export {
        type jt:policy-algebra;
        ordered-by user;
        description
          "Export policy";
      }
      leaf-list import {
        type jt:policy-algebra;
        ordered-by user;
        description
          "Import policy";
      }
      leaf reference-bandwidth {
        type string;
        description
          "Bandwidth for calculating metric defaults";
      }
      leaf job-stats {
        type empty;
        description
          "Collect job statistics";
      }
      leaf lsp-lifetime {
        type union {
          type string {
            pattern "<.*>|$.*";
          }
          type uint32 {
            range "350 .. 65535";
          }
        }
        units "seconds";
        description
          "Lifetime of LSPs";
      }
      leaf max-lsp-size {
        type union {
          type string {
            pattern "<.*>|$.*";
          }
          type uint32 {
            range "512 .. 9192";
          }
        }
        default "1492";
        description
          "Maximum size allowed for LSPs";
      }
      leaf max-hello-size {
        type union {
          type string {
            pattern "<.*>|$.*";
          }
          type uint32 {
            range "512 .. 16000";
          }
        }
        default "1492";
        description
          "Maximum size allowed for ISIS Hello PDUs";
      }
      leaf max-snp-size {
        type union {
          type string {
            pattern "<.*>|$.*";
          }
          type uint32 {
            range "512 .. 1400";
          }
        }
        default "1400";
        description
          "Maximum size allowed for Sequence Number (Complete/Partial) PDUs";
      }
      leaf spf-delay {
        type union {
          type string {
            pattern "<.*>|$.*";
          }
          type uint32 {
            range "50 .. 120000";
          }
        }
        units "milliseconds";
        status deprecated;
        description
          "Time to wait before running an SPF";
      }
      leaf authentication-key {
        type jt:unreadable;
        status deprecated;
        description
          "Authentication key (password)";
      }
      leaf authentication-type {
        type enumeration {
          enum "md5" {
            status deprecated;
            description
              "MD5 authentication";
          }
          enum "simple" {
            status deprecated;
            description
              "Simple password authentication";
          }
        }
        status deprecated;
        description
          "Authentication type";
      }
      leaf loose-authentication-check {
        type empty;
        description
          "Verify authentication only if PDU has authentication TLV";
      }
      leaf max-areas {
        type union {
          type string {
            pattern "<.*>|$.*";
          }
          type uint32 {
            range "3 .. 64";
          }
        }
        default "3";
        description
          "Maximum number of advertised Areas";
      }
      leaf no-authentication-check {
        type empty;
        description
          "Disable authentication checking";
      }
      leaf no-ipv4-routing {
        type empty;
        description
          "Disable IPv4 routing";
      }
      leaf no-ipv6-routing {
        type empty;
        description
          "Disable IPv6 routing";
      }
      leaf no-adjacency-holddown {
        type empty;
        description
          "Disable adjacency hold down";
      }
      leaf multicast-topology {
        type empty;
        status deprecated;
        description
          "Enable multicast topology";
      }
      leaf ignore-attached-bit {
        type empty;
        description
          "Ignore the attached bit in Level 1 LSPs";
      }
      container rib-group {
        description
          "Routing table group for importing IS-IS routes";
        uses rib_group_type;
      }
      container no-external-export {
        description
          "No external export";
        uses apply-advanced;
        list protocol {
          key "name";
          ordered-by user;
          description
            "Protocol parameters";
          leaf name {
            type enumeration {
              enum "bgp" {
                description
                  "BGP";
              }
              enum "ospf" {
                description
                  "OSPF";
              }
              enum "isis" {
                description
                  "ISIS";
              }
              enum "l-isis" {
                description
                  "Labelled ISIS";
              }
              enum "l-ospf" {
                description
                  "Labelled OSPF";
              }
              enum "static" {
                description
                  "Static";
              }
            }
          }
        }
      }
      container strict-dual-isis {
        presence "enable strict-dual-isis";
        description
          "Enable dual isis if spf computation is required for both ipv4 and ipv6 family";
        uses apply-advanced;
        leaf holdown {
          type union {
            type string {
              pattern "<.*>|$.*";
            }
            type uint32 {
              range "1 .. 65535";
            }
          }
          default "12";
          status deprecated;
          description
            "Time to wait for ipv4 and ipv6 connectivity";
        }
        leaf holddown {
          type union {
            type string {
              pattern "<.*>|$.*";
            }
            type uint32 {
              range "1 .. 65535";
            }
          }
          default "12";
          description
            "Time to wait for ipv4 and ipv6 connectivity";
        }
      }
      container topologies {
        description
          "Enable topologies";
        uses apply-advanced;
        leaf ipv4-multicast {
          type empty;
          description
            "Enable IPv4-multicast topology";
        }
        leaf ipv6-unicast {
          type empty;
          description
            "Enable IPv6-unicast topology";
        }
        leaf ipv6-multicast {
          type empty;
          description
            "Enable IPv6-multicast topology";
        }
      }
      container overload {
        presence "enable overload";
        description
          "Set the overload bit (no transit traffic)";
        uses apply-advanced;
        leaf timeout {
          type union {
            type string {
              pattern "<.*>|$.*";
            }
            type uint32 {
              range "60 .. 3600";
            }
          }
          units "seconds";
          description
            "Time after which overload bit is reset";
        }
        leaf advertise-high-metrics {
          type empty;
          description
            "Advertise high metrics instead of setting the overload bit";
        }
        leaf allow-route-leaking {
          type empty;
          description
            "Allow routes to be leaked when overload is configured";
        }
        leaf internal-prefixes {
          type empty;
          description
            "Allow internal prefixes to be advertised with high metric";
        }
        leaf external-prefixes {
          type empty;
          description
            "Allow external prefixes to be advertised with high metric";
        }
      }
      container dynamic-overload {
        description
          "Set the dynamic overload options";
        uses apply-advanced;
        leaf no-overload-on-prefix-export-limit {
          type empty;
          description
            "Do not set overload bit when prefix export limit is reached";
        }
        leaf auto-recovery {
          type empty;
          description
            "Enable Auto recovery to recover from dynamic overload state";
        }
      }
      container graceful-restart {
        description
          "IS-IS graceful restart options";
        choice enable-disable {
          case case_1 {
            leaf disable {
              type empty;
              description
                "Disable graceful restart";
            }
          }
        }
        leaf helper-disable {
          type empty;
          description
            "Disable graceful restart helper capability";
        }
        leaf restart-duration {
          type union {
            type string {
              pattern "<.*>|$.*";
            }
            type uint32 {
              range "30 .. 300";
            }
          }
          units "seconds";
          description
            "Maximum time for graceful restart to finish";
        }
      }
      list net {
        key "name";
        description
          "Assign Network Entity Title (NET) configuration";
        leaf name {
          type jt:isoaddr;
          description
            "Assign Network Entity Title (NET) address to an IS-IS router";
        }
      }
      leaf rfc7775-compliance {
        type empty;
        description
          "RFC 7775 compliance for up/down bit and prefix attribute sub-tlv";
      }
    }
    container l2circuit {
      description
        "Configuration for Layer 2 circuits over MPLS";
      uses apply-advanced;
      container traceoptions {
        description
          "Trace options for Layer 2 circuits";
        uses apply-advanced;
        container file {
          description
            "Trace file options";
          leaf filename {
            type string {
              length "1 .. 1024";
            }
            description
              "Name of file in which to write trace information";
          }
          leaf replace {
            type empty;
            status deprecated;
            description
              "Replace trace file rather than appending to it";
          }
          leaf size {
            type string;
            description
              "Maximum trace file size";
          }
          leaf files {
            type union {
              type string {
                pattern "<.*>|$.*";
              }
              type uint32 {
                range "2 .. 1000";
              }
            }
            default "10";
            description
              "Maximum number of trace files";
          }
          leaf no-stamp {
            type empty;
            status deprecated;
            description
              "Do not timestamp trace file";
          }
          choice world-readable-choice {
            leaf world-readable {
              type empty;
              description
                "Allow any user to read the log file";
            }
            leaf no-world-readable {
              type empty;
              description
                "Don't allow any user to read the log file";
            }
          }
        }
        list flag {
          key "name";
          ordered-by user;
          description
            "Tracing parameters";
          leaf name {
            type enumeration {
              enum "error" {
                description
                  "Trace errors";
              }
              enum "topology" {
                description
                  "Trace Layer 2 circuit topology changes";
              }
              enum "fec" {
                description
                  "Trace Layer 2 circuit VC FEC advertisements";
              }
              enum "connections" {
                description
                  "Trace Layer 2 circuit connections";
              }
              enum "oam" {
                description
                  "Trace Layer 2 circuit OAM messages";
              }
              enum "egress-protection" {
                description
                  "Trace Layer 2 circuit egress protection messages";
              }
              enum "auto-sensing" {
                description
                  "Trace Layer 2 circuit PW auto-sensing";
              }
              enum "sdb" {
                description
                  "Trace SDB";
              }
              enum "route" {
                description
                  "Trace routing information";
              }
              enum "normal" {
                description
                  "Trace normal events";
              }
              enum "general" {
                description
                  "Trace general events";
              }
              enum "state" {
                description
                  "Trace state transitions";
              }
              enum "policy" {
                description
                  "Trace policy processing";
              }
              enum "task" {
                description
                  "Trace routing protocol task processing";
              }
              enum "timer" {
                description
                  "Trace routing protocol timer processing";
              }
              enum "all" {
                description
                  "Trace everything";
              }
            }
          }
          leaf send {
            type empty;
            description
              "Trace transmitted packets";
          }
          leaf receive {
            type empty;
            description
              "Trace received packets";
          }
          leaf detail {
            type empty;
            description
              "Trace detailed information";
          }
          leaf disable {
            type empty;
            description
              "Disable this trace flag";
          }
        }
      }
      list neighbor {
        key "name";
        ordered-by user;
        description
          "List of Layer 2 circuits to this neighbor";
        leaf name {
          type jt:ipv4addr;
          description
            "Neighbor ID";
        }
        uses apply-advanced;
        list interface {
          key "name";
          ordered-by user;
          description
            "Interface forming the Layer 2 circuit";
          leaf name {
            type union {
              type jt:interface-name;
              type string {
                pattern "<.*>|$.*";
              }
            }
            description
              "Interface name";
          }
          uses apply-advanced;
          container static {
            presence "enable static";
            description
              "Configuration of static Pseudowire";
            uses apply-advanced;
            leaf incoming-label {
              type union {
                type string {
                  pattern "<.*>|$.*";
                }
                type uint32 {
                  range "16 .. 1048575";
                }
              }
              mandatory true;
              description
                "Layer 2 circuit incoming static label";
            }
            leaf outgoing-label {
              type union {
                type string {
                  pattern "<.*>|$.*";
                }
                type uint32 {
                  range "16 .. 1048575";
                }
              }
              mandatory true;
              description
                "Layer 2 circuit outgoing static label";
            }
            leaf send-oam {
              type empty;
              description
                "Turn on sending of l2ckt ping";
            }
          }
          leaf psn-tunnel-endpoint {
            type jt:ipv4addr;
            description
              "Endpoint of the transport tunnel on the remote PE";
          }
          leaf protect-interface {
            type union {
              type jt:interface-name;
              type string {
                pattern "<.*>|$.*";
              }
            }
            description
              "Name of protect interface";
          }
          leaf virtual-circuit-id {
            type union {
              type string {
                pattern "<.*>|$.*";
              }
              type uint32 {
                range "1 .. 4294967295";
              }
            }
            mandatory true;
            description
              "Identifier for this Layer 2 circuit";
          }
          leaf description {
            type string;
            description
              "Text description of Layer 2 circuit";
          }
          choice control-word-choice {
            leaf control-word {
              type empty;
              description
                "Add control word to the Layer 2 encapsulation";
            }
            leaf no-control-word {
              type empty;
              description
                "Don't add control word to the Layer 2 encapsulation";
            }
          }
          leaf community {
            type string;
            description
              "Community associated with this Layer 2 circuit";
          }
          leaf mtu {
            type union {
              type string {
                pattern "<.*>|$.*";
              }
              type uint32 {
                range "512 .. 65535";
              }
            }
            description
              "MTU to be advertised for this Layer 2 circuit";
          }
          leaf ignore-encapsulation-mismatch {
            type empty;
            description
              "Allow different encapsulation types on local and remote end";
          }
          leaf ignore-mtu-mismatch {
            type empty;
            description
              "Allow different MTUs on interfaces";
          }
          leaf send-ip-addr-list-tlv {
            type empty;
            description
              "Send IP ADDR LIST TLV to remote side";
          }
          container pseudowire-status-tlv {
            presence "enable pseudowire-status-tlv";
            description
              "Send pseudowire status TLV";
            uses apply-advanced;
            leaf hot-standby-vc-on {
              type empty;
              description
                "Activate pseudowire upon arrival of 'hot-standby' status TLV message";
            }
          }
          leaf switchover-delay {
            type union {
              type string {
                pattern "<.*>|$.*";
              }
              type uint32 {
                range "0 .. 180000";
              }
            }
            units "milliseconds";
            default "10000";
            description
              "Layer 2 circuit switchover delay";
          }
          container revert-time {
            presence "enable revert-time";
            description
              "Enable pseudowire redundancy reversion";
            leaf delay {
              type union {
                type string {
                  pattern "<.*>|$.*";
                }
                type uint32 {
                  range "0 .. 3600";
                }
              }
              units "seconds";
              mandatory true;
              description
                "Reversion timer (seconds)";
            }
            leaf maximum {
              type union {
                type string {
                  pattern "<.*>|$.*";
                }
                type uint32 {
                  range "0 .. 7200";
                }
              }
              units "seconds";
              description
                "Maximum reversion interval to add over revert-time delay";
            }
          }
          list backup-neighbor {
            key "name";
            ordered-by user;
            description
              "Configuration of redundant l2circuit";
            leaf name {
              type jt:ipv4addr;
              description
                "Neighbor ID";
            }
            uses apply-advanced;
            container static {
              presence "enable static";
              description
                "Configuration of static Pseudowire";
              uses apply-advanced;
              leaf incoming-label {
                type union {
                  type string {
                    pattern "<.*>|$.*";
                  }
                  type uint32 {
                    range "16 .. 1048575";
                  }
                }
                mandatory true;
                description
                  "Layer 2 circuit incoming static label";
              }
              leaf outgoing-label {
                type union {
                  type string {
                    pattern "<.*>|$.*";
                  }
                  type uint32 {
                    range "16 .. 1048575";
                  }
                }
                mandatory true;
                description
                  "Layer 2 circuit outgoing static label";
              }
            }
            leaf virtual-circuit-id {
              type union {
                type string {
                  pattern "<.*>|$.*";
                }
                type uint32 {
                  range "1 .. 4294967295";
                }
              }
              description
                "Identifier for this Layer 2 circuit";
            }
            leaf community {
              type string;
              description
                "Community associated with this Layer 2 circuit";
            }
            leaf psn-tunnel-endpoint {
              type jt:ipv4addr;
              description
                "Endpoint of the transport tunnel on the remote PE";
            }
            leaf standby {
              type empty;
              description
                "Keep backup pseudowire in continuous standby";
            }
            leaf hot-standby {
              type empty;
              description
                "Keep backup pseudowire in continuous standby mode and ready for traffic forwarding";
            }
          }
        }
      }
      container local-switching {
        description
          "Configuration of Layer 2 circuits local switching";
        uses apply-advanced;
        list interface {
          key "name";
          ordered-by user;
          description
            "Interface forming the local Layer 2 circuit";
          leaf name {
            type union {
              type jt:interface-name;
              type string {
                pattern "<.*>|$.*";
              }
            }
            description
              "Interface name";
          }
          uses apply-advanced;
          leaf no-revert {
            type empty;
            description
              "Do not revert to primary-interface";
          }
          leaf protect-interface {
            type union {
              type jt:interface-name;
              type string {
                pattern "<.*>|$.*";
              }
            }
            description
              "Name of protect interface";
          }
          leaf connection-protection {
            type empty;
            description
              "End-2-end protection via OAM failure detection";
          }
          list neighbor {
            key "name";
            ordered-by user;
            description
              "Configuration of Layer 2 circuit";
            leaf name {
              type jt:ipv4addr;
              description
                "Neighbor ID";
            }
            uses apply-advanced;
            leaf virtual-circuit-id {
              type union {
                type string {
                  pattern "<.*>|$.*";
                }
                type uint32 {
                  range "1 .. 4294967295";
                }
              }
              mandatory true;
              description
                "Identifier for this Layer 2 circuit";
            }
            leaf community {
              type string;
              description
                "Community associated with this Layer 2 circuit";
            }
            leaf psn-tunnel-endpoint {
              type jt:ipv4addr;
              description
                "Endpoint of the transport tunnel on the neighbor PE";
            }
            leaf mtu {
              type union {
                type string {
                  pattern "<.*>|$.*";
                }
                type uint32 {
                  range "512 .. 65535";
                }
              }
              description
                "MTU to be advertised for this Layer 2 circuit";
            }
          }
          list backup-neighbor {
            key "name";
            ordered-by user;
            description
              "Configuration of redundant l2circuit";
            leaf name {
              type jt:ipv4addr;
              description
                "Backup Neighbor ID";
            }
            uses apply-advanced;
            leaf virtual-circuit-id {
              type union {
                type string {
                  pattern "<.*>|$.*";
                }
                type uint32 {
                  range "1 .. 4294967295";
                }
              }
              mandatory true;
              description
                "Identifier for this Layer 2 circuit";
            }
            leaf psn-tunnel-endpoint {
              type jt:ipv4addr;
              description
                "Endpoint of the transport tunnel on the backup neighbor PE";
            }
            leaf community {
              type string;
              description
                "Community associated with this Layer 2 circuit";
            }
            leaf mtu {
              type union {
                type string {
                  pattern "<.*>|$.*";
                }
                type uint32 {
                  range "512 .. 65535";
                }
              }
              description
                "MTU to be advertised for this Layer 2 circuit";
            }
          }
          container end-interface {
            description
              "Interface name of the other end point";
            uses apply-advanced;
            leaf interface {
              type union {
                type jt:interface-name;
                type string {
                  pattern "<.*>|$.*";
                }
              }
              description
                "Interface name";
            }
            leaf no-revert {
              type empty;
              description
                "Do not revert to primary-interface";
            }
            leaf protect-interface {
              type union {
                type jt:interface-name;
                type string {
                  pattern "<.*>|$.*";
                }
              }
              description
                "Name of protect interface";
            }
            leaf backup-interface {
              type union {
                type jt:interface-name;
                type string {
                  pattern "<.*>|$.*";
                }
              }
              description
                "Name of backup interface";
            }
          }
          leaf description {
            type string;
            description
              "Text description of Layer 2 circuit";
          }
          leaf encapsulation-type {
            type enumeration {
              enum "atm-aal5" {
                description
                  "ATM AAL/5 encapsulation";
              }
              enum "atm-cell" {
                description
                  "ATM port promiscuous mode cell encapsulation";
              }
              enum "atm-cell-port-mode" {
                description
                  "ATM port promiscuous mode cell encapsulation";
              }
              enum "atm-cell-vp-mode" {
                description
                  "ATM VP promiscuous mode cell encapsulation";
              }
              enum "atm-cell-vc-mode" {
                description
                  "ATM non-promiscuous cell encapsulation";
              }
              enum "frame-relay" {
                description
                  "Frame Relay encapsulation";
              }
              enum "ppp" {
                description
                  "PPP encapsulation";
              }
              enum "cisco-hdlc" {
                description
                  "Cisco-compatible HDLC encapsulation";
              }
              enum "ethernet-vlan" {
                description
                  "Ethernet VLAN encapsulation";
              }
              enum "ethernet" {
                description
                  "Ethernet encapsulation";
              }
              enum "interworking" {
                description
                  "Layer 2.5 interworking VPN";
              }
              enum "frame-relay-port-mode" {
                description
                  "Frame Relay port mode encapsulation";
              }
              enum "satop-t1" {
                description
                  "SATOP-T1 based Layer 2 VPN";
              }
              enum "satop-e1" {
                description
                  "SATOP-E1 based Layer 2 VPN";
              }
              enum "satop-t3" {
                description
                  "SATOP-T3 based Layer 2 VPN";
              }
              enum "satop-e3" {
                description
                  "SATOP-E3 based Layer 2 VPN";
              }
              enum "cesop" {
                description
                  "CESOP based Layer 2 VPN";
              }
            }
            description
              "Encapsulation type for VPN";
          }
          leaf ignore-encapsulation-mismatch {
            type empty;
            description
              "Allow different encapsulation types on local and remote end";
          }
          leaf ignore-mtu-mismatch {
            type empty;
            description
              "Allow different MTUs on interfaces";
          }
        }
      }
    }
    container l2vpn {
      description
        "Configuration for Layer 2 VPN circuits over MPLS";
      uses apply-advanced;
      container resolution {
        description
          "Configuration of PW nexthop resolution";
        uses apply-advanced;
        leaf preserve-nexthop-hierarchy {
          type empty;
          description
            "Install expanded hierarchy";
        }
      }
    }
    container ldp {
      description
        "LDP options";
      uses juniper-protocols-ldp;
    }
    container mpls {
      description
        "Multiprotocol Label Switching options";
      uses juniper-protocols-mpls;
    }
    container ospf {
      description
        "OSPF configuration";
      uses juniper-protocols-ospf;
    }
    list ospf-instance {
      key "name";
      ordered-by user;
      description
        "Multi-instance OSPF configuration";
      leaf name {
        type string;
        description
          "OSPF instance name";
      }
      uses apply-advanced;
      list topology {
        key "name";
        ordered-by user;
        description
          "Topology parameters";
        leaf name {
          type string;
          description
            "Topology name";
        }
        uses apply-advanced;
        leaf disable {
          type empty;
          description
            "Disable this topology";
        }
        leaf topology-id {
          type union {
            type string {
              pattern "<.*>|$.*";
            }
            type uint8 {
              range "32 .. 127";
            }
          }
          description
            "Topology identifier";
        }
        leaf overload {
          type empty;
          description
            "Set the overload mode (repel transit traffic)";
        }
        leaf rib-group {
          type string;
          description
            "Routing table group for importing routes";
        }
        container spf-options {
          description
            "Configure options for SPF";
          uses apply-advanced;
          container microloop-avoidance {
            description
              "Configure microloop avoidance mechanism";
            uses apply-advanced;
            container post-convergence-path {
              presence "enable post-convergence-path";
              description
                "Temporarily install post-convergence path for routes potentially affected by microloops";
              uses apply-advanced;
              leaf delay {
                type union {
                  type string {
                    pattern "<.*>|$.*";
                  }
                  type uint32 {
                    range "500 .. 60000";
                  }
                }
                units "milliseconds";
                description
                  "Time after which temporary post-convergence paths are removed";
              }
              leaf maximum-labels {
                type union {
                  type string {
                    pattern "<.*>|$.*";
                  }
                  type uint32 {
                    range "2 .. 8";
                  }
                }
                description
                  "Maximum number of labels installed for post-convergence paths";
              }
            }
          }
          leaf delay {
            type union {
              type string {
                pattern "<.*>|$.*";
              }
              type uint32 {
                range "50 .. 8000";
              }
            }
            units "milliseconds";
            description
              "Time to wait before running an SPF";
          }
          leaf holddown {
            type union {
              type string {
                pattern "<.*>|$.*";
              }
              type uint32 {
                range "2000 .. 20000";
              }
            }
            units "milliseconds";
            description
              "Time to hold down before running an SPF";
          }
          leaf rapid-runs {
            type union {
              type string {
                pattern "<.*>|$.*";
              }
              type uint32 {
                range "1 .. 10";
              }
            }
            description
              "Number of maximum rapid SPF runs before holddown";
          }
          leaf no-ignore-our-externals {
            type empty;
            description
              "Do not ignore self-generated external and NSSA LSAs";
          }
          container multipath {
            description
              "Configure multipath options";
            uses apply-advanced;
            container weighted {
              description
                "Weighted multipath options";
              uses apply-advanced;
              leaf one-hop {
                type empty;
                description
                  "Enable load balancing on onehop multipath based on interface bandwidth";
              }
            }
          }
        }
        container backup-spf-options {
          description
            "Configure options for backup SPF";
          uses apply-advanced;
          container remote-backup-calculation {
            presence "enable remote-backup-calculation";
            description
              "Calculate Remote LFA backup nexthops";
            uses apply-advanced;
            container pq-nodes-nearest-to-source {
              description
                "PQ nodes selection based upon nearest to source";
              uses apply-advanced;
              leaf percent {
                type union {
                  type string {
                    pattern "<.*>|$.*";
                  }
                  type uint32 {
                    range "10 .. 100";
                  }
                }
                description
                  "Selection percentage for nearest to source";
              }
            }
          }
          container use-post-convergence-lfa {
            presence "enable use-post-convergence-lfa";
            description
              "Calculate post-convergence backup paths";
            uses apply-advanced;
            leaf maximum-labels {
              type union {
                type string {
                  pattern "<.*>|$.*";
                }
                type uint32 {
                  range "2 .. 8";
                }
              }
              description
                "Maximum number of labels installed for post-convergence paths";
            }
            leaf maximum-backup-paths {
              type union {
                type string {
                  pattern "<.*>|$.*";
                }
                type uint32 {
                  range "1 .. 8";
                }
              }
              description
                "Maximum number of equal-cost post-convergence paths installed";
            }
          }
          leaf use-source-packet-routing {
            type empty;
            description
              "Use spring backup paths for inet.0 routes";
          }
          leaf disable {
            type empty;
            description
              "Do not run backup SPF";
          }
          leaf no-install {
            type empty;
            description
              "Do not install backup nexthops into the RIB";
          }
          leaf downstream-paths-only {
            type empty;
            description
              "Use only downstream backup paths";
          }
          container per-prefix-calculation {
            description
              "Calculate backup nexthops for non-best prefix originators";
            uses apply-advanced;
            leaf stubs {
              type empty;
              description
                "Per prefix calculation for stubs only";
            }
            leaf summary {
              type empty;
              description
                "Per prefix calculation for summary originators only";
            }
            leaf externals {
              type empty;
              description
                "Per prefix calculation for externals";
            }
            leaf all {
              type empty;
              description
                "Per prefix calculation for all";
            }
          }
          leaf node-link-degradation {
            type empty;
            description
              "Degrade to link protection when nodelink protection not available";
          }
        }
        leaf prefix-export-limit {
          type union {
            type string {
              pattern "<.*>|$.*";
            }
            type uint32 {
              range "0 .. 4294967295";
            }
          }
          description
            "Maximum number of prefixes that can be exported";
        }
      }
      container spf-options {
        description
          "Configure options for SPF";
        uses apply-advanced;
        container microloop-avoidance {
          description
            "Configure microloop avoidance mechanism";
          uses apply-advanced;
          container post-convergence-path {
            presence "enable post-convergence-path";
            description
              "Temporarily install post-convergence path for routes potentially affected by microloops";
            uses apply-advanced;
            leaf delay {
              type union {
                type string {
                  pattern "<.*>|$.*";
                }
                type uint32 {
                  range "500 .. 60000";
                }
              }
              units "milliseconds";
              description
                "Time after which temporary post-convergence paths are removed";
            }
            leaf maximum-labels {
              type union {
                type string {
                  pattern "<.*>|$.*";
                }
                type uint32 {
                  range "2 .. 8";
                }
              }
              description
                "Maximum number of labels installed for post-convergence paths";
            }
          }
        }
        leaf delay {
          type union {
            type string {
              pattern "<.*>|$.*";
            }
            type uint32 {
              range "50 .. 8000";
            }
          }
          units "milliseconds";
          description
            "Time to wait before running an SPF";
        }
        leaf holddown {
          type union {
            type string {
              pattern "<.*>|$.*";
            }
            type uint32 {
              range "2000 .. 20000";
            }
          }
          units "milliseconds";
          description
            "Time to hold down before running an SPF";
        }
        leaf rapid-runs {
          type union {
            type string {
              pattern "<.*>|$.*";
            }
            type uint32 {
              range "1 .. 10";
            }
          }
          description
            "Number of maximum rapid SPF runs before holddown";
        }
        leaf no-ignore-our-externals {
          type empty;
          description
            "Do not ignore self-generated external and NSSA LSAs";
        }
        container multipath {
          description
            "Configure multipath options";
          uses apply-advanced;
          container weighted {
            description
              "Weighted multipath options";
            uses apply-advanced;
            leaf one-hop {
              type empty;
              description
                "Enable load balancing on onehop multipath based on interface bandwidth";
            }
          }
        }
      }
      container backup-spf-options {
        description
          "Configure options for backup SPF";
        uses apply-advanced;
        container remote-backup-calculation {
          presence "enable remote-backup-calculation";
          description
            "Calculate Remote LFA backup nexthops";
          uses apply-advanced;
          container pq-nodes-nearest-to-source {
            description
              "PQ nodes selection based upon nearest to source";
            uses apply-advanced;
            leaf percent {
              type union {
                type string {
                  pattern "<.*>|$.*";
                }
                type uint32 {
                  range "10 .. 100";
                }
              }
              description
                "Selection percentage for nearest to source";
            }
          }
        }
        container use-post-convergence-lfa {
          presence "enable use-post-convergence-lfa";
          description
            "Calculate post-convergence backup paths";
          uses apply-advanced;
          leaf maximum-labels {
            type union {
              type string {
                pattern "<.*>|$.*";
              }
              type uint32 {
                range "2 .. 8";
              }
            }
            description
              "Maximum number of labels installed for post-convergence paths";
          }
        }
        leaf use-source-packet-routing {
          type empty;
          description
            "Use spring backup paths for inet.0 routes";
        }
        leaf disable {
          type empty;
          description
            "Do not run backup SPF";
        }
        leaf no-install {
          type empty;
          description
            "Do not install backup nexthops into the RIB";
        }
        leaf downstream-paths-only {
          type empty;
          description
            "Use only downstream backup paths";
        }
        container per-prefix-calculation {
          description
            "Calculate backup nexthops for non-best prefix originators";
          uses apply-advanced;
          leaf stubs {
            type empty;
            description
              "Per prefix calculation for stubs only";
          }
          leaf summary {
            type empty;
            description
              "Per prefix calculation for summary originators only";
          }
          leaf externals {
            type empty;
            description
              "Per prefix calculation for externals";
          }
          leaf all {
            type empty;
            description
              "Per prefix calculation for all";
          }
        }
        leaf node-link-degradation {
          type empty;
          description
            "Degrade to link protection when nodelink protection not available";
        }
      }
      container source-packet-routing {
        presence "enable source-packet-routing";
        description
          "Enable source packet routing (SPRING)";
        uses apply-advanced;
        container adjacency-segment {
          description
            "Attributes for adjacency segments in spring";
          uses apply-advanced;
          leaf hold-time {
            type union {
              type string {
                pattern "<.*>|$.*";
              }
              type uint32 {
                range "180000 .. 900000";
              }
            }
            description
              "Retain time of Adjacency segment after isolating from an interface";
          }
        }
        leaf-list prefix-segment {
          type jt:policy-algebra;
          ordered-by user;
          description
            "Prefix Segment policy";
        }
        leaf explicit-null {
          type empty;
          description
            "Set E and P bits in all Prefix SID advertisements";
        }
        container node-segment {
          presence "enable node-segment";
          description
            "Enable support for Node segments in SPRING";
          uses apply-advanced;
          leaf ipv4-index {
            type union {
              type string {
                pattern "<.*>|$.*";
              }
              type uint32 {
                range "0 .. 199999";
              }
            }
            description
              "Set ipv4 node segment index";
          }
          leaf index-range {
            type union {
              type string {
                pattern "<.*>|$.*";
              }
              type uint32 {
                range "32 .. 16385";
              }
            }
            description
              "Set range of node segment indices allowed";
          }
        }
        container srgb {
          description
            "Set the SRGB global block in SPRING";
          leaf start-label {
            type union {
              type string {
                pattern "<.*>|$.*";
              }
              type uint32 {
                range "16 .. 1048575";
              }
            }
            description
              "Start range for SRGB label block";
          }
          leaf index-range {
            type union {
              type string {
                pattern "<.*>|$.*";
              }
              type uint32 {
                range "32 .. 1048559";
              }
            }
            description
              "Index to the SRGB start label block";
          }
        }
        leaf mapping-server {
          type string;
          description
            "Mapping server name";
        }
        leaf install-prefix-sid-for-best-route {
          type empty;
          description
            "For best route install a exact prefix sid route";
        }
        leaf ldp-stitching {
          type empty;
          description
            "Enable SR to LDP stitching";
        }
        leaf-list flex-algorithm {
          type union {
            type string {
              pattern "<.*>|$.*";
            }
            type uint32 {
              range "128 .. 255";
            }
          }
          max-elements 16;
          description
            "Flex-algorithms we would like to participate in";
        }
        leaf strict-asla-based-flex-algorithm {
          type empty;
          description
            "Flex-Algorithm to ignore links not having ASLA sub-TLVs";
        }
        container sensor-based-stats {
          description
            "Configure sensor based stats in SPRING";
          uses apply-advanced;
          container per-interface-per-member-link {
            description
              "Configure sensor based stats per nexthop";
            leaf ingress {
              type empty;
              description
                "Enable sensor based stats on ingress interface";
            }
            leaf egress {
              type empty;
              description
                "Enable sensor based stats on egress interface";
            }
          }
          container per-sid {
            description
              "Configure sensor based stats per spring route";
            leaf ingress {
              type empty;
              description
                "Enable sensor based stats for per-sid ingress accounting";
            }
            leaf egress {
              type empty;
              description
                "Enable sensor based stats for IP-MPLS egress accounting";
            }
          }
        }
      }
      list area {
        key "name";
        ordered-by user;
        description
          "Configure an OSPF area";
        leaf name {
          type jt:areaid;
          description
            "Area ID";
        }
        uses apply-advanced;
        choice stub-option {
          case case_1 {
            container stub {
              presence "enable stub";
              description
                "Configure a stub area";
              leaf default-metric {
                type union {
                  type string {
                    pattern "<.*>|$.*";
                  }
                  type uint32 {
                    range "1 .. 16777215";
                  }
                }
                description
                  "Metric for the default route in this stub area";
              }
              choice summaries-choice {
                leaf summaries {
                  type empty;
                  description
                    "Flood summary LSAs into this stub area";
                }
                leaf no-summaries {
                  type empty;
                  description
                    "Don't flood summary LSAs into this stub area";
                }
              }
            }
          }
          case case_2 {
            container nssa {
              presence "enable nssa";
              description
                "Configure a not-so-stubby area";
              uses apply-advanced;
              container default-lsa {
                presence "enable default-lsa";
                description
                  "Configure a default LSA";
                uses apply-advanced;
                leaf default-metric {
                  type union {
                    type string {
                      pattern "<.*>|$.*";
                    }
                    type uint32 {
                      range "1 .. 16777215";
                    }
                  }
                  description
                    "Metric for the default route in this area";
                }
                leaf metric-type {
                  type union {
                    type string {
                      pattern "<.*>|$.*";
                    }
                    type uint32 {
                      range "1 .. 2";
                    }
                  }
                  description
                    "External metric type for the default type 7 LSA";
                }
                leaf type-7 {
                  type empty;
                  description
                    "Flood type 7 default LSA if no-summaries is configured";
                }
              }
              leaf default-metric {
                type union {
                  type string {
                    pattern "<.*>|$.*";
                  }
                  type uint32 {
                    range "1 .. 16777215";
                  }
                }
                status deprecated;
                description
                  "Metric for the default route in this area";
              }
              leaf metric-type {
                type union {
                  type string {
                    pattern "<.*>|$.*";
                  }
                  type uint32 {
                    range "1 .. 2";
                  }
                }
                status deprecated;
                description
                  "External metric type for the default type 7 LSA";
              }
              choice summaries-choice {
                leaf summaries {
                  type empty;
                  description
                    "Flood summary LSAs into this NSSA area";
                }
                leaf no-summaries {
                  type empty;
                  description
                    "Don't flood summary LSAs into this NSSA area";
                }
              }
              list area-range {
                key "name";
                ordered-by user;
                description
                  "Configure NSSA area ranges";
                leaf name {
                  type jt:ipprefix;
                  description
                    "Range to summarize NSSA routes in this area";
                }
                uses apply-advanced;
                leaf restrict {
                  type empty;
                  description
                    "Restrict advertisement of this area range";
                }
                leaf exact {
                  type empty;
                  description
                    "Enforce exact match for advertisement of this area range";
                }
                container override-metric {
                  presence "enable override-metric";
                  description
                    "Override the dynamic metric for this area-range";
                  uses apply-advanced;
                  leaf metric {
                    type union {
                      type string {
                        pattern "<.*>|$.*";
                      }
                      type uint32 {
                        range "1 .. 16777215";
                      }
                    }
                    mandatory true;
                    description
                      "Metric value";
                  }
                  leaf metric-type {
                    type union {
                      type string {
                        pattern "<.*>|$.*";
                      }
                      type uint32 {
                        range "1 .. 2";
                      }
                    }
                    default "1";
                    description
                      "Set the metric type for the override metric";
                  }
                }
              }
            }
          }
        }
        list area-range {
          key "name";
          ordered-by user;
          description
            "Configure area ranges";
          leaf name {
            type jt:ipprefix;
            description
              "Range to summarize routes in this area";
          }
          uses apply-advanced;
          leaf restrict {
            type empty;
            description
              "Restrict advertisement of this area range";
          }
          leaf exact {
            type empty;
            description
              "Enforce exact match for advertisement of this area range";
          }
          leaf override-metric {
            type union {
              type string {
                pattern "<.*>|$.*";
              }
              type uint32 {
                range "1 .. 16777215";
              }
            }
            description
              "Override the dynamic metric for this area-range";
          }
        }
        leaf-list network-summary-export {
          type jt:policy-algebra;
          ordered-by user;
          description
            "Export policy for Type 3 Summary LSAs";
        }
        leaf-list network-summary-import {
          type jt:policy-algebra;
          ordered-by user;
          description
            "Import policy for Type 3 Summary LSAs";
        }
        leaf-list inter-area-prefix-export {
          type jt:policy-algebra;
          ordered-by user;
          description
            "Export policy for Inter Area Prefix LSAs";
        }
        leaf-list inter-area-prefix-import {
          type jt:policy-algebra;
          ordered-by user;
          description
            "Import policy for Inter Area Prefix LSAs";
        }
        leaf authentication-type {
          type enumeration {
            enum "none" {
              status deprecated;
              description
                "No authentication";
            }
            enum "simple" {
              status deprecated;
              description
                "Simple password authentication";
            }
            enum "md5" {
              status deprecated;
              description
                "MD5 authentication";
            }
          }
          status deprecated;
          description
            "Authentication type";
        }
        list virtual-link {
          key "neighbor-id transit-area";
          ordered-by user;
          description
            "Configure virtual links";
          leaf neighbor-id {
            type jt:ipv4addr;
            description
              "Router ID of a virtual neighbor";
          }
          leaf transit-area {
            type jt:areaid;
            description
              "Transit area in common with virtual neighbor";
          }
          uses apply-advanced;
          choice enable-disable {
            case case_1 {
              leaf disable {
                type empty;
                description
                  "Disable this virtual link";
              }
            }
          }
          leaf retransmit-interval {
            type union {
              type string {
                pattern "<.*>|$.*";
              }
              type uint32 {
                range "1 .. 65535";
              }
            }
            description
              "Retransmission interval (seconds)";
          }
          leaf transit-delay {
            type union {
              type string {
                pattern "<.*>|$.*";
              }
              type uint32 {
                range "1 .. 65535";
              }
            }
            description
              "Transit delay (seconds)";
          }
          leaf hello-interval {
            type union {
              type string {
                pattern "<.*>|$.*";
              }
              type uint32 {
                range "1 .. 255";
              }
            }
            description
              "Hello interval (seconds)";
          }
          leaf dead-interval {
            type union {
              type string {
                pattern "<.*>|$.*";
              }
              type uint32 {
                range "1 .. 65535";
              }
            }
            description
              "Dead interval (seconds)";
          }
          leaf mtu {
            type union {
              type string {
                pattern "<.*>|$.*";
              }
              type uint32 {
                range "128 .. 65535";
              }
            }
            description
              "Maximum OSPF packet size";
          }
          choice auth {
            case case_1 {
              container authentication {
                uses juniper-ospf-authentication;
              }
            }
            case case_2 {
              container authentication-key {
                status deprecated;
                description
                  "Authentication key";
                leaf keyname {
                  type jt:unreadable;
                  mandatory true;
                  description
                    "Authentication key value";
                }
                leaf key-id {
                  type union {
                    type string {
                      pattern "<.*>|$.*";
                    }
                    type uint32 {
                      range "0 .. 255";
                    }
                  }
                  description
                    "Key ID for MD5 authentication";
                }
              }
            }
          }
          leaf demand-circuit {
            type empty;
            description
              "Interface functions as a demand circuit";
          }
          leaf flood-reduction {
            type empty;
            description
              "Enable flood reduction";
          }
          leaf no-neighbor-down-notification {
            type empty;
            description
              "Don't inform other protocols about neighbor down events";
          }
          leaf ipsec-sa {
            type string {
              length "1 .. 32";
            }
            description
              "IPSec security association name";
          }
          list topology {
            key "name";
            ordered-by user;
            description
              "Topology specific attributes";
            leaf name {
              type string;
              description
                "Topology name";
            }
            uses apply-advanced;
            leaf disable {
              type empty;
              description
                "Disable this topology";
            }
            leaf metric {
              type union {
                type string {
                  pattern "<.*>|$.*";
                }
                type uint16 {
                  range "1 .. 65535";
                }
              }
              description
                "Topology metric";
            }
            container bandwidth-based-metrics {
              description
                "Configure bandwidth based metrics";
              uses apply-advanced;
              list bandwidth {
                key "name";
                description
                  "Bandwidth threshold";
                leaf name {
                  type string;
                }
                leaf metric {
                  type union {
                    type string {
                      pattern "<.*>|$.*";
                    }
                    type uint16 {
                      range "1 .. 65535";
                    }
                  }
                  mandatory true;
                  description
                    "Metric associated with specified bandwidth";
                }
              }
            }
          }
        }
        list sham-link-remote {
          key "name";
          ordered-by user;
          description
            "Configure parameters for remote sham link endpoint";
          leaf name {
            type jt:ipaddr;
            description
              "Remote sham link endpoint address";
          }
          uses apply-advanced;
          leaf metric {
            type union {
              type string {
                pattern "<.*>|$.*";
              }
              type uint16 {
                range "1 .. 65535";
              }
            }
            description
              "Sham link metric";
          }
          leaf ipsec-sa {
            type string {
              length "1 .. 32";
            }
            description
              "IPSec security association name";
          }
          leaf demand-circuit {
            type empty;
            description
              "Interface functions as a demand circuit";
          }
          leaf flood-reduction {
            type empty;
            description
              "Enable flood reduction";
          }
          list topology {
            key "name";
            ordered-by user;
            description
              "Topology specific attributes";
            leaf name {
              type string;
              description
                "Topology name";
            }
            uses apply-advanced;
            leaf disable {
              type empty;
              description
                "Disable this topology";
            }
            leaf metric {
              type union {
                type string {
                  pattern "<.*>|$.*";
                }
                type uint16 {
                  range "1 .. 65535";
                }
              }
              description
                "Topology metric";
            }
            container bandwidth-based-metrics {
              description
                "Configure bandwidth based metrics";
              uses apply-advanced;
              list bandwidth {
                key "name";
                description
                  "Bandwidth threshold";
                leaf name {
                  type string;
                }
                leaf metric {
                  type union {
                    type string {
                      pattern "<.*>|$.*";
                    }
                    type uint16 {
                      range "1 .. 65535";
                    }
                  }
                  mandatory true;
                  description
                    "Metric associated with specified bandwidth";
                }
              }
            }
          }
          leaf keychain {
            type string {
              length "1 .. 128";
            }
            description
              "Key chain name";
          }
        }
        list interface {
          key "name";
          ordered-by user;
          description
            "Include an interface in this area";
          leaf name {
            type union {
              type jt:ipv4addr-or-interface;
              type string {
                pattern "<.*>|$.*";
              }
            }
            description
              "Interface name";
          }
          uses apply-advanced;
          choice enable-disable {
            case case_1 {
              leaf disable {
                type empty;
                description
                  "Disable OSPF on this interface";
              }
            }
          }
          leaf interface-type {
            type enumeration {
              enum "nbma" {
                description
                  "Nonbroadcast multiaccess";
              }
              enum "p2mp" {
                description
                  "Point-to-multipoint NBMA";
              }
              enum "p2p" {
                description
                  "Point-to-point";
              }
              enum "p2mp-over-lan" {
                description
                  "Point-to-multipoint over LAN mode";
              }
            }
            description
              "Type of interface";
          }
          container passive {
            presence "enable passive";
            description
              "Do not run OSPF, but advertise it";
            uses apply-advanced;
            container traffic-engineering {
              description
                "Advertise TE link information";
              uses apply-advanced;
              leaf remote-node-id {
                type jt:ipaddr;
                description
                  "Remote address of the link";
              }
              leaf remote-node-router-id {
                type jt:ipv4addr;
                description
                  "TE Router-ID of the remote node";
              }
            }
          }
          leaf secondary {
            type empty;
            description
              "Treat interface as secondary";
          }
          leaf own-router-lsa {
            type empty;
            description
              "Generate a separate router LSA for this interface";
          }
          container bandwidth-based-metrics {
            description
              "Configure bandwidth based metrics";
            uses apply-advanced;
            list bandwidth {
              key "name";
              description
                "Bandwidth threshold";
              leaf name {
                type string;
              }
              leaf metric {
                type union {
                  type string {
                    pattern "<.*>|$.*";
                  }
                  type uint16 {
                    range "1 .. 65535";
                  }
                }
                mandatory true;
                description
                  "Metric associated with specified bandwidth";
              }
            }
          }
          leaf metric {
            type union {
              type string {
                pattern "<.*>|$.*";
              }
              type uint16 {
                range "1 .. 65535";
              }
            }
            description
              "Interface metric";
          }
          leaf priority {
            type union {
              type string {
                pattern "<.*>|$.*";
              }
              type uint32 {
                range "0 .. 255";
              }
            }
            description
              "Designated router priority";
          }
          leaf retransmit-interval {
            type union {
              type string {
                pattern "<.*>|$.*";
              }
              type uint32 {
                range "1 .. 65535";
              }
            }
            description
              "Retransmission interval (seconds)";
          }
          leaf transit-delay {
            type union {
              type string {
                pattern "<.*>|$.*";
              }
              type uint32 {
                range "1 .. 65535";
              }
            }
            description
              "Transit delay (seconds)";
          }
          leaf hello-interval {
            type union {
              type string {
                pattern "<.*>|$.*";
              }
              type uint32 {
                range "1 .. 255";
              }
            }
            description
              "Hello interval (seconds)";
          }
          leaf dead-interval {
            type union {
              type string {
                pattern "<.*>|$.*";
              }
              type uint32 {
                range "1 .. 65535";
              }
            }
            description
              "Dead interval (seconds)";
          }
          leaf mtu {
            type union {
              type string {
                pattern "<.*>|$.*";
              }
              type uint32 {
                range "128 .. 65535";
              }
            }
            description
              "Maximum OSPF packet size";
          }
          choice auth {
            case case_1 {
              container authentication {
                uses juniper-ospf-authentication;
              }
            }
            case case_2 {
              container authentication-key {
                status deprecated;
                description
                  "Authentication key";
                leaf keyname {
                  type jt:unreadable;
                  mandatory true;
                  description
                    "Authentication key value";
                }
                leaf key-id {
                  type union {
                    type string {
                      pattern "<.*>|$.*";
                    }
                    type uint32 {
                      range "0 .. 255";
                    }
                  }
                  description
                    "Key ID for MD5 authentication";
                }
              }
            }
          }
          leaf demand-circuit {
            type empty;
            description
              "Interface functions as a demand circuit";
          }
          leaf flood-reduction {
            type empty;
            description
              "Enable flood reduction";
          }
          leaf no-neighbor-down-notification {
            type empty;
            description
              "Don't inform other protocols about neighbor down events";
          }
          list topology {
            key "name";
            ordered-by user;
            description
              "Topology specific attributes";
            leaf name {
              type string;
              description
                "Topology name";
            }
            uses apply-advanced;
            leaf disable {
              type empty;
              description
                "Disable this topology";
            }
            leaf metric {
              type union {
                type string {
                  pattern "<.*>|$.*";
                }
                type uint16 {
                  range "1 .. 65535";
                }
              }
              description
                "Topology metric";
            }
            container bandwidth-based-metrics {
              description
                "Configure bandwidth based metrics";
              uses apply-advanced;
              list bandwidth {
                key "name";
                description
                  "Bandwidth threshold";
                leaf name {
                  type string;
                }
                leaf metric {
                  type union {
                    type string {
                      pattern "<.*>|$.*";
                    }
                    type uint16 {
                      range "1 .. 65535";
                    }
                  }
                  mandatory true;
                  description
                    "Metric associated with specified bandwidth";
                }
              }
            }
          }
          leaf transmit-interval {
            type union {
              type string {
                pattern "<.*>|$.*";
              }
              type uint32 {
                range "1 .. 4294967295";
              }
            }
            status deprecated;
            description
              "OSPF packet transmit interval (milliseconds)";
          }
          container bfd-liveness-detection {
            description
              "Bidirectional Forwarding Detection options";
            uses apply-advanced;
            leaf version {
              type enumeration {
                enum "0" {
                  description
                    "BFD version 0 (deprecated)";
                }
                enum "1" {
                  description
                    "BFD version 1";
                }
                enum "automatic" {
                  description
                    "Choose BFD version automatically";
                }
              }
              default "automatic";
              description
                "BFD protocol version number";
            }
            leaf minimum-interval {
              type union {
                type string {
                  pattern "<.*>|$.*";
                }
                type uint32 {
                  range "1 .. 255000";
                }
              }
              units "milliseconds";
              description
                "Minimum transmit and receive interval";
            }
            leaf minimum-transmit-interval {
              type union {
                type string {
                  pattern "<.*>|$.*";
                }
                type uint32 {
                  range "1 .. 255000";
                }
              }
              units "milliseconds";
              status deprecated;
              description
                "Minimum transmit interval";
            }
            leaf minimum-receive-interval {
              type union {
                type string {
                  pattern "<.*>|$.*";
                }
                type uint32 {
                  range "1 .. 255000";
                }
              }
              units "milliseconds";
              description
                "Minimum receive interval";
            }
            leaf multiplier {
              type union {
                type string {
                  pattern "<.*>|$.*";
                }
                type uint32 {
                  range "1 .. 255";
                }
              }
              default "3";
              description
                "Detection time multiplier";
            }
            leaf inline-disable {
              type empty;
              description
                "Disable inline mode for this BFD session";
            }
            leaf pdu-size {
              type union {
                type string {
                  pattern "<.*>|$.*";
                }
                type uint32 {
                  range "24 .. 16000";
                }
              }
              default "24";
              description
                "BFD transport protocol payload size";
            }
            choice adaptation-choice {
              case case_1 {
                leaf no-adaptation {
                  type empty;
                  description
                    "Disable adaptation";
                }
              }
            }
            container transmit-interval {
              description
                "Transmit-interval options";
              uses apply-advanced;
              leaf minimum-interval {
                type union {
                  type string {
                    pattern "<.*>|$.*";
                  }
                  type uint32 {
                    range "1 .. 255000";
                  }
                }
                units "milliseconds";
                description
                  "Minimum transmit interval";
              }
              leaf threshold {
                type union {
                  type uint32;
                  type string {
                    pattern "<.*>|$.*";
                  }
                }
                units "milliseconds";
                description
                  "High transmit interval triggering a trap";
              }
            }
            container detection-time {
              description
                "Detection-time options";
              uses apply-advanced;
              leaf threshold {
                type union {
                  type uint32;
                  type string {
                    pattern "<.*>|$.*";
                  }
                }
                units "milliseconds";
                description
                  "High detection-time triggering a trap";
              }
            }
            container authentication {
              description
                "Authentication options";
              uses apply-advanced;
              leaf key-chain {
                type string;
                description
                  "Key chain name";
              }
              leaf algorithm {
                type enumeration {
                  enum "simple-password" {
                    description
                      "Simple password";
                  }
                  enum "keyed-md5" {
                    description
                      "Keyed message Digest 5";
                  }
                  enum "meticulous-keyed-md5" {
                    description
                      "Meticulous keyed message Digest 5";
                  }
                  enum "keyed-sha-1" {
                    description
                      "Keyed secure hash algorithm (SHA1) ";
                  }
                  enum "meticulous-keyed-sha-1" {
                    description
                      "Meticulous keyed secure hash algorithm (SHA1) ";
                  }
                }
                description
                  "Algorithm name";
              }
              leaf loose-check {
                type empty;
                description
                  "Verify authentication only if authentication is negotiated";
              }
            }
            container echo {
              description
                "Echo mode parameters";
              uses apply-advanced;
              leaf minimum-interval {
                type union {
                  type string {
                    pattern "<.*>|$.*";
                  }
                  type uint32 {
                    range "100 .. 255000";
                  }
                }
                units "milliseconds";
                description
                  "Minimum transmit and receive interval";
              }
            }
            container echo-lite {
              description
                "Echo-lite more parameters";
              uses apply-advanced;
              leaf minimum-interval {
                type union {
                  type string {
                    pattern "<.*>|$.*";
                  }
                  type uint32 {
                    range "100 .. 255000";
                  }
                }
                units "milliseconds";
                description
                  "Minimum transmit and receive interval";
              }
            }
            leaf full-neighbors-only {
              type empty;
              description
                "Setup BFD sessions only to Full neighbors";
            }
            leaf holddown-interval {
              type union {
                type string {
                  pattern "<.*>|$.*";
                }
                type uint32 {
                  range "0 .. 255000";
                }
              }
              units "milliseconds";
              description
                "Time to hold the session-UP notification to the client";
            }
          }
          leaf dynamic-neighbors {
            type empty;
            description
              "Learn neighbors dynamically on a p2mp interface";
          }
          leaf no-advertise-adjacency-segment {
            type empty;
            description
              "Do not advertise an adjacency segment for this interface";
          }
          list neighbor {
            key "name";
            ordered-by user;
            description
              "NBMA neighbor";
            leaf name {
              type jt:ipaddr;
              description
                "Address of neighbor";
            }
            leaf eligible {
              type empty;
              description
                "Eligible to be DR on an NBMA network";
            }
          }
          leaf poll-interval {
            type union {
              type string {
                pattern "<.*>|$.*";
              }
              type uint32 {
                range "1 .. 65535";
              }
            }
            description
              "Poll interval for NBMA interfaces";
          }
          leaf no-interface-state-traps {
            type empty;
            description
              "Do not send interface state change traps";
          }
          leaf strict-bfd {
            type empty;
            description
              "Enable strict bfd over this interface";
          }
          container post-convergence-lfa {
            presence "enable post-convergence-lfa";
            description
              "Protect interface using post-convergence backup path";
            uses apply-advanced;
          }
          leaf te-metric {
            type union {
              type string {
                pattern "<.*>|$.*";
              }
              type uint32 {
                range "1 .. 4294967295";
              }
            }
            description
              "Traffic engineering metric";
          }
          container ldp-synchronization {
            presence "enable ldp-synchronization";
            description
              "Advertise maximum metric until LDP is operational";
            uses ldp-sync-obj;
          }
          container ipv4-adjacency-segment {
            description
              "Configure ipv4 adjacency segment";
            uses apply-advanced;
            container unprotected {
              description
                "Adjacency SID uneligible for protection";
              choice adjsid-type {
                case case_1 {
                  container index {
                    description
                      "Adjacency SID indexed from SRGB";
                    leaf index-number {
                      type union {
                        type string {
                          pattern "<.*>|$.*";
                        }
                        type uint32 {
                          range "0 .. 199999";
                        }
                      }
                    }
                  }
                }
                case case_2 {
                  leaf label {
                    type union {
                      type string {
                        pattern "<.*>|$.*";
                      }
                      type uint32 {
                        range "16 .. 1048575";
                      }
                    }
                    description
                      "Adjacency SID from static label pool";
                  }
                }
                case case_3 {
                  leaf dynamic {
                    type empty;
                    description
                      "Dynamically allocate an adjacency segment";
                  }
                }
              }
            }
          }
          list lan-neighbor {
            key "name";
            ordered-by user;
            description
              "Configuration specific to a LAN neighbor";
            leaf name {
              type jt:ipaddr;
              description
                "Address of neighbor";
            }
            uses apply-advanced;
            container ipv4-adjacency-segment {
              description
                "Configure ipv4 adjacency segment";
              uses apply-advanced;
              container protected {
                description
                  "Adjacency SID is eligible for protection";
                choice adjsid-type {
                  case case_1 {
                    container index {
                      description
                        "Adjacency SID indexed from SRGB";
                      leaf index-number {
                        type union {
                          type string {
                            pattern "<.*>|$.*";
                          }
                          type uint32 {
                            range "0 .. 199999";
                          }
                        }
                      }
                    }
                  }
                  case case_2 {
                    leaf label {
                      type union {
                        type string {
                          pattern "<.*>|$.*";
                        }
                        type uint32 {
                          range "16 .. 1048575";
                        }
                      }
                      description
                        "Adjacency SID from static label pool";
                    }
                  }
                  case case_3 {
                    leaf dynamic {
                      type empty;
                      description
                        "Dynamically allocate an adjacency segment";
                    }
                  }
                }
              }
              container unprotected {
                description
                  "Adjacency SID uneligible for protection";
                choice adjsid-type {
                  case case_1 {
                    container index {
                      description
                        "Adjacency SID indexed from SRGB";
                      leaf index-number {
                        type union {
                          type string {
                            pattern "<.*>|$.*";
                          }
                          type uint32 {
                            range "0 .. 199999";
                          }
                        }
                      }
                    }
                  }
                  case case_2 {
                    leaf label {
                      type union {
                        type string {
                          pattern "<.*>|$.*";
                        }
                        type uint32 {
                          range "16 .. 1048575";
                        }
                      }
                      description
                        "Adjacency SID from static label pool";
                    }
                  }
                  case case_3 {
                    leaf dynamic {
                      type empty;
                      description
                        "Dynamically allocate an adjacency segment";
                    }
                  }
                }
              }
            }
          }
          leaf delay-metric {
            type union {
              type string {
                pattern "<.*>|$.*";
              }
              type uint32 {
                range "0 .. 16777215";
              }
            }
            units "microseconds";
            description
              "Delay metric";
          }
          container delay-measurement {
            presence "enable delay-measurement";
            description
              "Enable delay measurement";
            uses apply-advanced;
            leaf probe-interval {
              type union {
                type string {
                  pattern "<.*>|$.*";
                }
                type uint32 {
                  range "1 .. 255";
                }
              }
              units "seconds";
              description
                "Probe interval";
            }
            leaf probe-count {
              type union {
                type string {
                  pattern "<.*>|$.*";
                }
                type uint32 {
                  range "1 .. 15";
                }
              }
              description
                "Probe count";
            }
            container advertisement {
              description
                "Delay advertisement";
              uses apply-advanced;
              container periodic {
                description
                  "Periodic advertisement parameters";
                uses apply-advanced;
                leaf threshold {
                  type union {
                    type string {
                      pattern "<.*>|$.*";
                    }
                    type uint32 {
                      range "0 .. 100";
                    }
                  }
                  units "percentage";
                  description
                    "Threshold";
                }
                leaf interval {
                  type union {
                    type string {
                      pattern "<.*>|$.*";
                    }
                    type uint32 {
                      range "30 .. 3600";
                    }
                  }
                  units "seconds";
                  description
                    "Interval";
                }
              }
              container accelerated {
                presence "enable accelerated";
                description
                  "Accelerated advertisement parameters";
                uses apply-advanced;
                leaf threshold {
                  type union {
                    type string {
                      pattern "<.*>|$.*";
                    }
                    type uint32 {
                      range "0 .. 100";
                    }
                  }
                  units "percentage";
                  description
                    "Threshold";
                }
              }
            }
          }
          container application-specific {
            description
              "Advertise application-specific TE attributes";
            uses apply-advanced;
            list attribute-group {
              key "name";
              max-elements 1;
              ordered-by user;
              description
                "Link attribute group name";
              leaf name {
                type string;
                description
                  "Link attribute group name";
              }
              uses apply-advanced;
              leaf te-metric {
                type union {
                  type string {
                    pattern "<.*>|$.*";
                  }
                  type uint32 {
                    range "1 .. 4294967295";
                  }
                }
                description
                  "Traffic engineering metric for this attribute group";
              }
              leaf-list admin-group {
                type string;
                max-elements 16;
                ordered-by user;
                description
                  "Administrative groups for this attribute-group";
              }
              leaf delay-metric {
                type union {
                  type string {
                    pattern "<.*>|$.*";
                  }
                  type uint32 {
                    range "0 .. 16777215";
                  }
                }
                units "microseconds";
                description
                  "Delay metric for this attribute-group";
              }
              leaf advertise-interface-delay {
                type empty;
                description
                  "Use interface specific static/dynamic delay values as applicable in ASLA Sub-TLVs";
              }
              container application {
                description
                  "Standard Applications part of this attribute-group";
                uses apply-advanced;
                leaf flex-algorithm {
                  type empty;
                  description
                    "Set X flag in standard application bit mask";
                }
              }
            }
          }
        }
        leaf no-source-packet-routing {
          type empty;
          description
            "Disable SPRING in this area";
        }
      }
      choice enable-disable {
        case case_1 {
          leaf disable {
            type empty;
            description
              "Disable OSPF";
          }
        }
      }
      container traceoptions {
        description
          "Trace options for OSPF";
        uses apply-advanced;
        container file {
          description
            "Trace file options";
          leaf filename {
            type string {
              length "1 .. 1024";
            }
            description
              "Name of file in which to write trace information";
          }
          leaf replace {
            type empty;
            status deprecated;
            description
              "Replace trace file rather than appending to it";
          }
          leaf size {
            type string;
            description
              "Maximum trace file size";
          }
          leaf files {
            type union {
              type string {
                pattern "<.*>|$.*";
              }
              type uint32 {
                range "2 .. 1000";
              }
            }
            default "10";
            description
              "Maximum number of trace files";
          }
          leaf no-stamp {
            type empty;
            status deprecated;
            description
              "Do not timestamp trace file";
          }
          choice world-readable-choice {
            leaf world-readable {
              type empty;
              description
                "Allow any user to read the log file";
            }
            leaf no-world-readable {
              type empty;
              description
                "Don't allow any user to read the log file";
            }
          }
        }
        list flag {
          key "name";
          ordered-by user;
          description
            "Tracing parameters";
          leaf name {
            type enumeration {
              enum "spf" {
                description
                  "Trace SPF calculations";
              }
              enum "error" {
                description
                  "Trace errored packets";
              }
              enum "event" {
                description
                  "Trace OSPF state machine events";
              }
              enum "packet-dump" {
                description
                  "Dump the contents of selected packet types";
              }
              enum "flooding" {
                description
                  "Trace LSA flooding";
              }
              enum "lsa-analysis" {
                description
                  "Trace LSA analysis";
              }
              enum "packets" {
                description
                  "Trace all OSPF packets";
              }
              enum "hello" {
                description
                  "Trace hello packets";
              }
              enum "database-description" {
                description
                  "Trace database description packets";
              }
              enum "lsa-request" {
                description
                  "Trace LSA request packets";
              }
              enum "lsa-update" {
                description
                  "Trace LSA update packets";
              }
              enum "lsa-ack" {
                description
                  "Trace LSA acknowledgment packets";
              }
              enum "ldp-synchronization" {
                description
                  "Trace synchronization between OSPF and LDP";
              }
              enum "on-demand" {
                description
                  "Trace demand circuit extensions";
              }
              enum "nsr-synchronization" {
                description
                  "Trace NSR synchronization events";
              }
              enum "graceful-restart" {
                description
                  "Trace graceful restart";
              }
              enum "restart-signaling" {
                description
                  "Trace restart signaling";
              }
              enum "traffic-statistics" {
                description
                  "Trace Segment Routing Traffic Statistics";
              }
              enum "backup-spf" {
                description
                  "Trace backup SPF (LFA) specific events";
              }
              enum "source-packet-routing" {
                description
                  "Trace source packet routing (SPRING) events";
              }
              enum "post-convergence-lfa" {
                description
                  "Trace post-convergence-lfa related events";
              }
              enum "flex-algorithm" {
                description
                  "Trace flex-algorithm related events";
              }
              enum "rmopd" {
                description
                  "Trace rmopd interactions";
              }
              enum "route" {
                description
                  "Trace routing information";
              }
              enum "normal" {
                description
                  "Trace normal events";
              }
              enum "general" {
                description
                  "Trace general events";
              }
              enum "state" {
                description
                  "Trace state transitions";
              }
              enum "policy" {
                description
                  "Trace policy processing";
              }
              enum "task" {
                description
                  "Trace routing protocol task processing";
              }
              enum "timer" {
                description
                  "Trace routing protocol timer processing";
              }
              enum "all" {
                description
                  "Trace everything";
              }
            }
          }
          leaf send {
            type empty;
            description
              "Trace transmitted packets";
          }
          leaf receive {
            type empty;
            description
              "Trace received packets";
          }
          leaf detail {
            type empty;
            description
              "Trace detailed information";
          }
          leaf disable {
            type empty;
            description
              "Disable this trace flag";
          }
        }
      }
      leaf prefix-export-limit {
        type union {
          type string {
            pattern "<.*>|$.*";
          }
          type uint32 {
            range "0 .. 4294967295";
          }
        }
        description
          "Maximum number of prefixes that can be exported";
      }
      container rib-groups {
        description
          "Routing table groups for importing OSPF routes";
        uses apply-advanced;
        leaf inet {
          type string;
          description
            "Name of the IPv4/v6 routing table group";
        }
        leaf inet3 {
          type string;
          description
            "Name of the IPv4/v6 inet.3 routing table group";
        }
      }
      leaf job-stats {
        type empty;
        description
          "Collect job statistics";
      }
      container overload {
        presence "enable overload";
        description
          "Set the overload mode (repel transit traffic)";
        uses apply-advanced;
        leaf timeout {
          type union {
            type string {
              pattern "<.*>|$.*";
            }
            type uint32 {
              range "60 .. 3600";
            }
          }
          units "seconds";
          description
            "Time after which overload mode is reset";
        }
        leaf allow-route-leaking {
          type empty;
          description
            "Allow routes to be leaked when overload is configured";
        }
        leaf stub-network {
          type empty;
          description
            "Advertise Stub Network with maximum metric";
        }
        leaf intra-area-prefix {
          type empty;
          description
            "Advertise Intra Area Prefix with maximum metric";
        }
        leaf as-external {
          type empty;
          description
            "Advertise As External with maximum usable metric";
        }
      }
      container database-protection {
        presence "enable database-protection";
        description
          "Configure database protection attributes";
        uses apply-advanced;
        leaf maximum-lsa {
          type union {
            type string {
              pattern "<.*>|$.*";
            }
            type uint32 {
              range "1 .. 1000000";
            }
          }
          mandatory true;
          description
            "Maximum allowed non self-generated LSAs";
        }
        leaf warning-only {
          type empty;
          description
            "Emit only a warning when LSA maximum limit is exceeded";
        }
        leaf warning-threshold {
          type union {
            type string {
              pattern "<.*>|$.*";
            }
            type uint8 {
              range "30 .. 100";
            }
          }
          units "percent";
          description
            "Percentage of LSA maximum above which to trigger warning";
        }
        leaf ignore-count {
          type union {
            type string {
              pattern "<.*>|$.*";
            }
            type uint8 {
              range "1 .. 32";
            }
          }
          description
            "Maximum number of times to go into ignore state";
        }
        leaf ignore-time {
          type union {
            type string {
              pattern "<.*>|$.*";
            }
            type uint16 {
              range "30 .. 3600";
            }
          }
          units "seconds";
          description
            "Time to stay in ignore state and ignore all neighbors";
        }
        leaf reset-time {
          type union {
            type string {
              pattern "<.*>|$.*";
            }
            type uint32 {
              range "60 .. 86400";
            }
          }
          units "seconds";
          description
            "Time after which the ignore count gets reset to zero";
        }
      }
      container graceful-restart {
        description
          "Configure graceful restart attributes";
        uses apply-advanced;
        choice enable-disable {
          case case_1 {
            leaf disable {
              type empty;
              description
                "Disable OSPF graceful restart capability";
            }
          }
        }
        leaf restart-duration {
          type union {
            type string {
              pattern "<.*>|$.*";
            }
            type uint32 {
              range "1 .. 3600";
            }
          }
          units "seconds";
          description
            "Time for all neighbors to become full";
        }
        leaf notify-duration {
          type union {
            type string {
              pattern "<.*>|$.*";
            }
            type uint32 {
              range "1 .. 3600";
            }
          }
          units "seconds";
          description
            "Time to send all max-aged grace LSAs";
        }
        container helper-disable {
          presence "enable helper-disable";
          description
            "Disable graceful restart helper capability";
          uses apply-advanced;
          choice disable-choices {
            case case_1 {
              leaf standard {
                type empty;
                description
                  "Disable helper-mode for rfc3623 based GR";
              }
            }
            case case_2 {
              leaf restart-signaling {
                type empty;
                description
                  "Disable helper mode for restart-signaling ";
              }
            }
            case case_3 {
              leaf both {
                type empty;
                description
                  "Disable helper mode for both the types of GR";
              }
            }
          }
        }
        leaf no-strict-lsa-checking {
          type empty;
          description
            "Do not abort graceful helper mode upon LSA changes";
        }
      }
      leaf route-type-community {
        type enumeration {
          enum "iana" {
            description
              "BGP extended community value used is 0x0306";
          }
          enum "vendor" {
            description
              "Vendor BGP extended community value used is 0x8000";
          }
        }
        description
          "Specify BGP extended community value to encode OSPF route type";
      }
      container domain-id {
        description
          "Configure domain ID";
        choice domain_id_or_disable {
          case case_1 {
            leaf domain-id {
              type string;
              description
                "Domain ID";
            }
          }
          case case_2 {
            leaf disable {
              type empty;
              description
                "Disable domain ID";
            }
          }
        }
      }
      choice domain_vpn_tag_or_disable {
        case case_1 {
          leaf domain-vpn-tag {
            type union {
              type string {
                pattern "<.*>|$.*";
              }
              type uint32 {
                range "0 .. 4294967295";
              }
            }
            description
              "Domain VPN tag for external LSA";
          }
        }
        case case_2 {
          leaf no-domain-vpn-tag {
            type empty;
            description
              "Disable domain VPN tag";
          }
        }
      }
      leaf preference {
        type union {
          type uint32;
          type string {
            pattern "<.*>|$.*";
          }
        }
        description
          "Preference of internal routes";
      }
      leaf external-preference {
        type union {
          type uint32;
          type string {
            pattern "<.*>|$.*";
          }
        }
        description
          "Preference of external routes";
      }
      leaf labeled-preference {
        type union {
          type uint32;
          type string {
            pattern "<.*>|$.*";
          }
        }
        description
          "Preference of labeled routes";
      }
      leaf-list export {
        type jt:policy-algebra;
        ordered-by user;
        description
          "Export policy";
      }
      leaf-list import {
        type jt:policy-algebra;
        ordered-by user;
        description
          "Import policy (for external routes or setting priority)";
      }
      leaf reference-bandwidth {
        type string;
        description
          "Bandwidth for calculating metric defaults";
      }
      leaf lsa-refresh-interval {
        type union {
          type string {
            pattern "<.*>|$.*";
          }
          type uint32 {
            range "25 .. 50";
          }
        }
        default "50";
        description
          "LSA refresh interval (minutes)";
      }
      leaf spf-delay {
        type union {
          type string {
            pattern "<.*>|$.*";
          }
          type uint32 {
            range "50 .. 8000";
          }
        }
        units "milliseconds";
        status deprecated;
        description
          "Time to wait before running an SPF";
      }
      leaf no-rfc-1583 {
        type empty;
        description
          "Disable RFC1583 compatibility";
      }
      leaf forwarding-address-to-broadcast {
        type empty;
        description
          "Set forwarding address in Type 5 LSA in broadcast network";
      }
      choice nssa-abr-option {
        case case_1 {
          leaf no-nssa-abr {
            type empty;
            description
              "Disable full NSSA functionality at ABR";
          }
        }
      }
      container sham-link {
        presence "enable sham-link";
        description
          "Configure parameters for sham links";
        uses apply-advanced;
        leaf local {
          type jt:ipaddr;
          description
            "Local sham link endpoint address";
        }
        leaf no-advertise-local {
          type empty;
          status deprecated;
          description
            "Don't advertise local sham link endpoint as stub in router LSA";
        }
      }
    }
    container ospf3 {
      description
        "OSPFv3 configuration";
      uses juniper-protocols-ospf3;
    }
    container source-packet-routing {
      presence "enable source-packet-routing";
      description
        "Enable source packet routing (SPRING)";
      uses apply-advanced;
      container traceoptions {
        description
          "Trace options for soure-packet-routing";
        uses apply-advanced;
        container file {
          description
            "Trace file options";
          leaf filename {
            type string {
              length "1 .. 1024";
            }
            description
              "Name of file in which to write trace information";
          }
          leaf replace {
            type empty;
            status deprecated;
            description
              "Replace trace file rather than appending to it";
          }
          leaf size {
            type string;
            description
              "Maximum trace file size";
          }
          leaf files {
            type union {
              type string {
                pattern "<.*>|$.*";
              }
              type uint32 {
                range "2 .. 1000";
              }
            }
            default "10";
            description
              "Maximum number of trace files";
          }
          leaf no-stamp {
            type empty;
            status deprecated;
            description
              "Do not timestamp trace file";
          }
          choice world-readable-choice {
            leaf world-readable {
              type empty;
              description
                "Allow any user to read the log file";
            }
            leaf no-world-readable {
              type empty;
              description
                "Don't allow any user to read the log file";
            }
          }
        }
        list flag {
          key "name";
          ordered-by user;
          description
            "Tracing parameters";
          leaf name {
            type enumeration {
              enum "controller" {
                description
                  "Trace controller-related activity";
              }
              enum "state" {
                description
                  "Trace LSP state-related activity";
              }
              enum "route" {
                description
                  "Trace route-related activity";
              }
              enum "general" {
                description
                  "Trace general activity";
              }
              enum "interface" {
                description
                  "Trace interface-related activity";
              }
              enum "dtm" {
                description
                  "Trace dtm-related activity";
              }
              enum "bfd" {
                description
                  "Trace bfd-related activity";
              }
              enum "translation" {
                description
                  "Trace translation-related activity";
              }
              enum "srv6-te" {
                description
                  "Trace srv6-te activity";
              }
              enum "telemetry-statistics" {
                description
                  "Trace telemetry statistics related activity";
              }
              enum "compute" {
                description
                  "Trace compute profile and computed lsp related activity";
              }
              enum "nsr-replication" {
                description
                  "Trace NSR replication activity";
              }
              enum "traffic-engineering-database" {
                description
                  "Trace spring-te to ted export related activity";
              }
              enum "delay-measurement" {
                description
                  "Trace path delay measurement related activity";
              }
              enum "all" {
                description
                  "Trace everything";
              }
            }
          }
          leaf detail {
            type empty;
            description
              "Trace detailed information";
          }
        }
      }
      list lsp-external-controller {
        key "name";
        ordered-by user;
        description
          "External path computing entity";
        leaf name {
          type string {
            length "1 .. 64";
          }
          description
            "Name of the external path computing entity";
        }
        uses apply-advanced;
      }
      leaf entropy-label {
        type empty;
        description
          "Enable entropy label for all SR-MPLS tunnels";
      }
      leaf preference {
        type union {
          type uint32;
          type string {
            pattern "<.*>|$.*";
          }
        }
        description
          "Route preference for SPRING-TE routes";
      }
      leaf sr-preference-override {
        type union {
          type string {
            pattern "<.*>|$.*";
          }
          type uint32 {
            range "0 .. 4294967295";
          }
        }
        description
          "SR-preference override for static SR-policies.Higher value is more preferred";
      }
      leaf sr-preference {
        type union {
          type string {
            pattern "<.*>|$.*";
          }
          type uint32 {
            range "0 .. 4294967295";
          }
        }
        description
          "SR-preference for static SR-policies.Higher value is more preferred";
      }
      leaf maximum-segment-list-depth {
        type union {
          type string {
            pattern "<.*>|$.*";
          }
          type uint32 {
            range "1 .. 16";
          }
        }
        description
          "Maximum segment list depth for SR-TE policies";
      }
      leaf maximum-srv6-te-segment-list-depth {
        type union {
          type string {
            pattern "<.*>|$.*";
          }
          type uint32 {
            range "1 .. 6";
          }
        }
        description
          "Maximum segment list depth for SRv6-TE policies";
      }
      leaf no-chained-composite-next-hop {
        type empty;
        description
          "Do not use chained composite next hops for SRTE routes";
      }
      leaf tunnel-tracking {
        type empty;
        description
          "Track route status for first hop label based tunnels";
      }
      list segment-list {
        key "name";
        ordered-by user;
        description
          "Explicit path for SR-TE segments";
        leaf name {
          type string {
            length "1 .. 64";
          }
          description
            "Name of SR-TE segment-list";
        }
        uses apply-advanced;
        leaf inherit-label-nexthops {
          type empty;
          description
            "Inherit label nexthops for first hop in this segment list";
        }
        choice translation-type {
          case case_1 {
            container auto-translate {
              presence "enable auto-translate";
              description
                "Enable auto translation from IP address to labels";
              uses apply-advanced;
              choice protection-choice {
                case case_1 {
                  container protected {
                    presence "enable protected";
                    description
                      "Choose protected labels if available";
                    uses apply-advanced;
                    leaf mandatory {
                      type empty;
                      description
                        "Mandatorily choose protected labels";
                    }
                  }
                }
                case case_2 {
                  container unprotected {
                    presence "enable unprotected";
                    description
                      "Choose unprotected labels if available";
                    uses apply-advanced;
                    leaf mandatory {
                      type empty;
                      description
                        "Mandatorily choose unprotected labels";
                    }
                  }
                }
              }
              leaf skip-tail-end-validation {
                type empty;
                description
                  "Skip validation of end hops";
              }
            }
          }
          case case_2 {
            container dynamic {
              presence "enable dynamic";
              description
                "Enable dynamic last hop computation";
              uses apply-advanced;
              choice protection-choice {
                case case_1 {
                  container protected {
                    presence "enable protected";
                    description
                      "Choose protected labels if available";
                    uses apply-advanced;
                    leaf mandatory {
                      type empty;
                      description
                        "Mandatorily choose protected labels";
                    }
                  }
                }
                case case_2 {
                  container unprotected {
                    presence "enable unprotected";
                    description
                      "Choose unprotected labels if available";
                    uses apply-advanced;
                    leaf mandatory {
                      type empty;
                      description
                        "Mandatorily choose unprotected labels";
                    }
                  }
                }
              }
            }
          }
        }
        leaf compute {
          type empty;
          description
            "Segment list used for specifying explicit path for computed paths";
        }
        leaf srv6 {
          type empty;
          description
            "Segment list used for SRv6";
        }
        list hop-list {
          key "name";
          max-elements 36;
          ordered-by user;
          leaf name {
            type string {
              length "1 .. 64";
            }
            description
              "Next hop in segment-list";
          }
          uses apply-advanced;
          leaf label {
            type union {
              type string {
                pattern "<.*>|$.*";
              }
              type uint32 {
                range "0 .. 1048575";
              }
            }
            description
              "Next label in SR-TE segment-list";
          }
          leaf ip-address {
            type jt:ipaddr;
            description
              "IP address of the hop";
          }
          leaf srv6-sid {
            type jt:ipaddr;
            description
              "Sid for SRv6 segment-list in form of ipv6 address";
          }
          container micro-srv6-sid {
            description
              "Configure a micro srv6 sid";
            uses apply-advanced;
            leaf micro-sid {
              type jt:ipaddr;
              mandatory true;
              description
                "Micro sid for SRv6 segment-list in form of ipv6 address";
            }
            leaf strict-adjacency {
              type empty;
              description
                "Strictly follow the micro adjacency sid";
            }
          }
          choice hop-choice {
            case case_1 {
              leaf strict {
                type empty;
                description
                  "Strict hop";
              }
            }
            case case_2 {
              leaf loose {
                type empty;
                description
                  "Loose hop";
              }
            }
          }
          container label-type {
            description
              "Type of label for the hop";
            uses apply-advanced;
            leaf node {
              type empty;
              description
                "Hop represents a node";
            }
          }
        }
      }
      list compute-profile {
        key "name";
        ordered-by user;
        description
          "Compute profile for dynamically computed paths";
        leaf name {
          type string {
            length "1 .. 64";
          }
          description
            "Name of the computation-profile";
        }
        uses apply-advanced;
        container admin-group {
          description
            "Administrative group policy";
          uses admin_group_include_exclude;
        }
        leaf maximum-segment-list-depth {
          type union {
            type string {
              pattern "<.*>|$.*";
            }
            type uint32 {
              range "1 .. 16";
            }
          }
          description
            "Maximum depth of computed path";
        }
        leaf algorithm {
          type union {
            type string {
              pattern "<.*>|$.*";
            }
            type uint32 {
              range "1 .. 255";
            }
          }
          description
            "Algorithm to constrain the path into";
        }
        leaf no-label-stack-compression {
          type empty;
          description
            "Provide fully expanded path, using adjacency segment identifiers";
        }
        choice protection-choice {
          case case_1 {
            container protected {
              presence "enable protected";
              description
                "Choose protected labels if available";
              uses apply-advanced;
              leaf mandatory {
                type empty;
                description
                  "Mandatorily choose protected labels";
              }
            }
          }
          case case_2 {
            container unprotected {
              presence "enable unprotected";
              description
                "Choose unprotected labels if available";
              uses apply-advanced;
              leaf mandatory {
                type empty;
                description
                  "Mandatorily choose unprotected labels";
              }
            }
          }
        }
        leaf compute-segment-list {
          type string {
            length "1 .. 64";
          }
          description
            "Name of the compute type segmentlist";
        }
        leaf maximum-computed-segment-lists {
          type union {
            type string {
              pattern "<.*>|$.*";
            }
            type uint32 {
              range "1 .. 128";
            }
          }
          description
            "Maximum number of segment-lists(ECMP paths) to be computed";
        }
        container metric-type {
          description
            "Metric type used for computaion";
          uses apply-advanced;
          choice metric-choice {
            case case_1 {
              leaf te {
                type empty;
                description
                  "TE metric";
              }
            }
            case case_2 {
              leaf igp {
                type empty;
                description
                  "IGP metric";
              }
            }
            case case_3 {
              container delay {
                presence "enable delay";
                description
                  "Delay metric";
                uses apply-advanced;
                choice metric-choice {
                  case case_1 {
                    leaf minimum {
                      type empty;
                      description
                        "Minimum delay metric type";
                    }
                  }
                  case case_2 {
                    leaf maximum {
                      type empty;
                      description
                        "Maximum delay metric type";
                    }
                  }
                  case case_3 {
                    leaf average {
                      type empty;
                      description
                        "Average delay metric type";
                    }
                  }
                }
                leaf delay-variation-threshold {
                  type union {
                    type string {
                      pattern "<.*>|$.*";
                    }
                    type uint32 {
                      range "1 .. 16777215";
                    }
                  }
                  description
                    "Link delay variation threshold";
                }
              }
            }
          }
        }
        container bound-metric {
          description
            "Bound metric used for computation";
          uses apply-advanced;
          leaf te {
            type union {
              type string {
                pattern "<.*>|$.*";
              }
              type uint32 {
                range "1 .. 4294967295";
              }
            }
            description
              "TE bound metric value";
          }
          leaf igp {
            type union {
              type string {
                pattern "<.*>|$.*";
              }
              type uint32 {
                range "1 .. 4294967295";
              }
            }
            description
              "IGP bound metric value";
          }
          leaf delay {
            type union {
              type string {
                pattern "<.*>|$.*";
              }
              type uint32 {
                range "1 .. 4294967295";
              }
            }
            description
              "Delay bound metric value";
          }
        }
        leaf bandwidth-requested {
          type string;
          units "bps";
          description
            "SR Path requested bandwidth in (bits/sec)";
        }
        container bandwidth-reservation-priority {
          presence "enable bandwidth-reservation-priority";
          description
            "SR path bandwidth reservation priority";
        }
        leaf setup-priority {
          type union {
            type string {
              pattern "<.*>|$.*";
            }
            type uint32 {
              range "0 .. 7";
            }
          }
          description
            "Setup priority";
        }
        leaf reservation-priority {
          type union {
            type string {
              pattern "<.*>|$.*";
            }
            type uint32 {
              range "0 .. 7";
            }
          }
          description
            "Reservation priority";
        }
      }
      leaf srv6 {
        type empty;
        description
          "Enable srv6 support for source-packet-routing";
      }
      container preserve-nexthop-hierarchy {
        presence "enable preserve-nexthop-hierarchy";
        description
          "Enable preserve-nexthop-hierarchy for source-packet-routing";
        uses apply-advanced;
        container sr-mpls {
          description
            "Disable preserve-nexthop-hierarchy for sr-mpls";
          uses apply-advanced;
          choice enable-disable {
            case case_1 {
              leaf disable {
                type empty;
                description
                  "Disable preserve-nexthop-hierarchy for sr-mpls";
              }
            }
          }
        }
        container srv6 {
          description
            "Disable preserve-nexthop-hierarchy for srv6";
          uses apply-advanced;
          choice enable-disable {
            case case_1 {
              leaf disable {
                type empty;
                description
                  "Disable preserve-nexthop-hierarchy for srv6";
              }
            }
          }
        }
      }
      leaf sbfd-frr {
        type empty;
        description
          "Enable sbfd frr support for source-packet-routing";
      }
      list source-routing-path {
        key "name";
        ordered-by user;
        description
          "Configure a source-routing-path";
        leaf name {
          type string {
            length "1 .. 64";
          }
          description
            "Name of the source routing path";
        }
        uses apply-advanced;
        leaf srv6 {
          type empty;
          description
            "Tunnel type SRv6";
        }
        leaf ldp-tunneling {
          type empty;
          description
            "Allow LDP to use this LSP for tunneling";
        }
        leaf use-for-shortcut {
          type empty;
          description
            "Allow this LSP to be used as a shortcut tunnel";
        }
        container diversity-association {
          description
            "Configure diversity association for LSP";
          uses apply-advanced;
          leaf-list group {
            type string;
            max-elements 8;
            ordered-by user;
            description
              "Configure diversity association group";
          }
          leaf shortest-path-first {
            type empty;
            description
              "Enable priority computation";
          }
        }
        container te-policy-association {
          description
            "Configure te policy association for LSP";
          uses apply-advanced;
          leaf-list group {
            type string;
            max-elements 8;
            ordered-by user;
            description
              "Configure te policy association group";
          }
        }
        leaf to {
          type jt:ipaddr;
          mandatory true;
          description
            "Ip-address of the tunnel end-point";
        }
        leaf from {
          type jt:ipaddr;
          description
            "Ip-address of the tunnel start-point";
        }
        leaf color {
          type union {
            type uint32;
            type string {
              pattern "<.*>|$.*";
            }
          }
          description
            "Color identifier for the tunnel end-point";
        }
        leaf no-ingress {
          type empty;
          description
            "Disable ingress functionality for this tunnel";
        }
        leaf binding-sid {
          type union {
            type string {
              pattern "<.*>|$.*";
            }
            type uint32 {
              range "16 .. 1048575";
            }
          }
          description
            "Specify the binding-label to enable transit functionality for this tunnel";
        }
        list install {
          key "name";
          ordered-by user;
          description
            "Install prefix";
          leaf name {
            type jt:ipaddr;
            description
              "Destination prefix";
          }
        }
        leaf preference {
          type union {
            type uint32;
            type string {
              pattern "<.*>|$.*";
            }
          }
          status deprecated;
          description
            "Preference for routes downloaded for this tunnel";
        }
        leaf metric {
          type union {
            type string {
              pattern "<.*>|$.*";
            }
            type uint32 {
              range "1 .. 16777215";
            }
          }
          description
            "Metric for routes downloaded for this tunnel";
        }
        leaf te-group-id {
          type union {
            type string {
              pattern "<.*>|$.*";
            }
            type uint32 {
              range "1 .. 128";
            }
          }
          description
            "Te group id";
        }
        leaf sr-preference {
          type union {
            type string {
              pattern "<.*>|$.*";
            }
            type uint32 {
              range "0 .. 4294967295";
            }
          }
          description
            "SR-preference for SPRING-TE routes. Higher value is more preferred";
        }
        leaf lsp-external-controller {
          type string {
            length "1 .. 64";
          }
          description
            "Name of the external path computing entity";
        }
        list primary {
          key "name";
          max-elements 128;
          ordered-by user;
          description
            "Configure a primary segment list for this source-routing-path";
          leaf name {
            type string {
              length "1 .. 64";
            }
            mandatory true;
            description
              "Name of SR-TE segment-list";
          }
          uses apply-advanced;
          leaf weight {
            type union {
              type uint32;
              type string {
                pattern "<.*>|$.*";
              }
            }
            description
              "Specify the balance factor for this segment list in SR-TE tunnel";
          }
          container bfd-liveness-detection {
            description
              "Bidirectional forwarding detection options";
            uses apply-advanced;
            container sbfd {
              presence "enable sbfd";
              description
                "Seamless BFD parameters";
              uses apply-advanced;
              leaf remote-discriminator {
                type union {
                  type string {
                    pattern "<.*>|$.*";
                  }
                  type uint32 {
                    range "1 .. 4294967295";
                  }
                }
                description
                  "Remote discriminator of reflector";
              }
              leaf responder-ip {
                type jt:ipaddr;
                description
                  "Seamless BFD responder address";
              }
              leaf ip-ttl {
                type union {
                  type string {
                    pattern "<.*>|$.*";
                  }
                  type uint8 {
                    range "1 .. 255";
                  }
                }
                default "5";
                description
                  "TTL for IP Header";
              }
              leaf destination-ipv6-local-host {
                type empty;
                description
                  "Use IPv6 local-host address as last address in SRH in compliance with RFC 7881";
              }
            }
            leaf minimum-interval {
              type union {
                type string {
                  pattern "<.*>|$.*";
                }
                type uint32 {
                  range "1 .. 255000";
                }
              }
              units "milliseconds";
              description
                "Minimum transmit and receive interval";
            }
            leaf multiplier {
              type union {
                type string {
                  pattern "<.*>|$.*";
                }
                type uint32 {
                  range "1 .. 255";
                }
              }
              default "3";
              description
                "Detection time multiplier";
            }
            leaf pdu-size {
              type union {
                type string {
                  pattern "<.*>|$.*";
                }
                type uint32 {
                  range "24 .. 16000";
                }
              }
              default "24";
              description
                "BFD transport protocol payload size";
            }
            leaf no-router-alert-option {
              type empty;
              description
                "Do not set the router alert option in IP header";
            }
          }
          container compute {
            presence "enable compute";
            description
              "Enable computation";
            uses apply-advanced;
            leaf compute-profile-name {
              type string {
                length "1 .. 64";
              }
              description
                "Name of compute-profile";
            }
          }
          leaf lsp-external-controller {
            type string {
              length "1 .. 64";
            }
            description
              "Name of the external path computing entity";
          }
        }
        list secondary {
          key "name";
          max-elements 1;
          ordered-by user;
          description
            "Configure a secondary segment list for this source-routing-path";
          leaf name {
            type string {
              length "1 .. 64";
            }
            mandatory true;
            description
              "Name of SR-TE segment-list";
          }
          uses apply-advanced;
          container bfd-liveness-detection {
            description
              "Bidirectional forwarding detection options";
            uses apply-advanced;
            container sbfd {
              presence "enable sbfd";
              description
                "Seamless BFD parameters";
              uses apply-advanced;
              leaf remote-discriminator {
                type union {
                  type string {
                    pattern "<.*>|$.*";
                  }
                  type uint32 {
                    range "1 .. 4294967295";
                  }
                }
                description
                  "Remote discriminator of reflector";
              }
              leaf responder-ip {
                type jt:ipaddr;
                description
                  "Seamless BFD responder address";
              }
              leaf ip-ttl {
                type union {
                  type string {
                    pattern "<.*>|$.*";
                  }
                  type uint8 {
                    range "1 .. 255";
                  }
                }
                default "5";
                description
                  "TTL for IP Header";
              }
              leaf destination-ipv6-local-host {
                type empty;
                description
                  "Use IPv6 local-host address as last address in SRH in compliance with RFC 7881";
              }
            }
            leaf minimum-interval {
              type union {
                type string {
                  pattern "<.*>|$.*";
                }
                type uint32 {
                  range "1 .. 255000";
                }
              }
              units "milliseconds";
              description
                "Minimum transmit and receive interval";
            }
            leaf multiplier {
              type union {
                type string {
                  pattern "<.*>|$.*";
                }
                type uint32 {
                  range "1 .. 255";
                }
              }
              default "3";
              description
                "Detection time multiplier";
            }
            leaf pdu-size {
              type union {
                type string {
                  pattern "<.*>|$.*";
                }
                type uint32 {
                  range "24 .. 16000";
                }
              }
              default "24";
              description
                "BFD transport protocol payload size";
            }
            leaf no-router-alert-option {
              type empty;
              description
                "Do not set the router alert option in IP header";
            }
          }
          container compute {
            presence "enable compute";
            description
              "Enable computation";
            uses apply-advanced;
            leaf compute-profile-name {
              type string {
                length "1 .. 64";
              }
              description
                "Name of compute-profile";
            }
          }
        }
        leaf entropy-label {
          type empty;
          description
            "Enable entropy label for this tunnel";
        }
      }
      list source-routing-path-template {
        key "name";
        ordered-by user;
        description
          "Configure a source-routing-path-template";
        leaf name {
          type string {
            length "1 .. 64";
          }
          description
            "Name of the source routing path";
        }
        uses apply-advanced;
        leaf no-ingress {
          type empty;
          description
            "Disable ingress functionality for this tunnel";
        }
        leaf use-for-shortcut {
          type empty;
          description
            "Allow this LSP to be used as a shortcut tunnel";
        }
        container diversity-association {
          description
            "Configure diversity association for LSP";
          uses apply-advanced;
          leaf-list group {
            type string;
            max-elements 8;
            ordered-by user;
            description
              "Configure diversity association group";
          }
          leaf shortest-path-first {
            type empty;
            description
              "Enable priority computation";
          }
        }
        container te-policy-association {
          description
            "Configure te policy association for LSP";
          uses apply-advanced;
          leaf-list group {
            type string;
            max-elements 8;
            ordered-by user;
            description
              "Configure te policy association group";
          }
        }
        leaf metric {
          type union {
            type string {
              pattern "<.*>|$.*";
            }
            type uint32 {
              range "1 .. 16777215";
            }
          }
          description
            "Metric for routes downloaded for this tunnel";
        }
        leaf sr-preference {
          type union {
            type string {
              pattern "<.*>|$.*";
            }
            type uint32 {
              range "0 .. 4294967295";
            }
          }
          description
            "SR-preference for SPRING-TE routes. Higher value is more preferred";
        }
        leaf ldp-tunneling {
          type empty;
          description
            "Allow LDP to use this LSP for tunneling";
        }
        leaf entropy-label {
          type empty;
          description
            "Enable entropy label for all SR-MPLS tunnels referring to this template";
        }
        leaf lsp-external-controller {
          type string {
            length "1 .. 64";
          }
          description
            "Name of the external path computing entity";
        }
        list primary {
          key "name";
          max-elements 128;
          ordered-by user;
          description
            "Configure a primary segment list for this source-routing-path";
          leaf name {
            type string {
              length "1 .. 64";
            }
            mandatory true;
            description
              "Name of SR-TE segment-list";
          }
          uses apply-advanced;
          leaf weight {
            type union {
              type uint32;
              type string {
                pattern "<.*>|$.*";
              }
            }
            description
              "Specify the balance factor for this segment list in SR-TE tunnel";
          }
          container compute {
            presence "enable compute";
            description
              "Enable computation";
            uses apply-advanced;
            leaf compute-profile-name {
              type string {
                length "1 .. 64";
              }
              description
                "Name of compute-profile";
            }
          }
          leaf lsp-external-controller {
            type string {
              length "1 .. 64";
            }
            description
              "Name of the external path computing entity";
          }
        }
        list secondary {
          key "name";
          max-elements 1;
          ordered-by user;
          description
            "Configure a secondary segment list for this source-routing-path";
          leaf name {
            type string {
              length "1 .. 64";
            }
            mandatory true;
            description
              "Name of SR-TE segment-list";
          }
          uses apply-advanced;
          container compute {
            presence "enable compute";
            description
              "Enable computation";
            uses apply-advanced;
            leaf compute-profile-name {
              type string {
                length "1 .. 64";
              }
              description
                "Name of compute-profile";
            }
          }
        }
        container bfd-liveness-detection {
          description
            "Bidirectional forwarding detection options";
          uses apply-advanced;
          container sbfd {
            presence "enable sbfd";
            description
              "Seamless BFD parameters";
            uses apply-advanced;
            leaf remote-discriminator {
              type union {
                type string {
                  pattern "<.*>|$.*";
                }
                type uint32 {
                  range "1 .. 4294967295";
                }
              }
              description
                "Remote discriminator of reflector";
            }
            leaf responder-ip {
              type jt:ipaddr;
              description
                "Seamless BFD responder address";
            }
            leaf ip-ttl {
              type union {
                type string {
                  pattern "<.*>|$.*";
                }
                type uint8 {
                  range "1 .. 255";
                }
              }
              default "5";
              description
                "TTL for IP Header";
            }
            leaf destination-ipv6-local-host {
              type empty;
              description
                "Use IPv6 local-host address as last address in SRH in compliance with RFC 7881";
            }
          }
          leaf minimum-interval {
            type union {
              type string {
                pattern "<.*>|$.*";
              }
              type uint32 {
                range "1 .. 255000";
              }
            }
            units "milliseconds";
            description
              "Minimum transmit and receive interval";
          }
          leaf multiplier {
            type union {
              type string {
                pattern "<.*>|$.*";
              }
              type uint32 {
                range "1 .. 255";
              }
            }
            default "3";
            description
              "Detection time multiplier";
          }
          leaf pdu-size {
            type union {
              type string {
                pattern "<.*>|$.*";
              }
              type uint32 {
                range "24 .. 16000";
              }
            }
            default "24";
            description
              "BFD transport protocol payload size";
          }
          leaf no-router-alert-option {
            type empty;
            description
              "Do not set the router alert option in IP header";
          }
        }
        leaf srv6 {
          type empty;
          description
            "Template type SRv6";
        }
      }
      leaf inherit-label-nexthops {
        type empty;
        description
          "Inherit label nexthops for first hop in segment lists";
      }
      container rib-group {
        description
          "Enable rib-group import  poilicies on SR-TE";
        uses apply-advanced;
        container ipv4 {
          presence "enable ipv4";
          description
            "Import  policy to be applied on ipv4 uncolored route";
          uses apply-advanced;
          leaf rib-group-name {
            type string {
              length "1 .. 64";
            }
            mandatory true;
            description
              "Rib-group import policy";
          }
        }
        container ipv6 {
          presence "enable ipv6";
          description
            "Import  policy to be applied on ipv6 uncolored route";
          uses apply-advanced;
          leaf rib-group-name {
            type string {
              length "1 .. 64";
            }
            mandatory true;
            description
              "Rib-group import policy";
          }
        }
        container ipv4-color {
          presence "enable ipv4-color";
          description
            "Import  policy to be applied on ipv4 colored route";
          uses apply-advanced;
          leaf rib-group-name {
            type string {
              length "1 .. 64";
            }
            mandatory true;
            description
              "Rib-group import policy";
          }
        }
        container ipv6-color {
          presence "enable ipv6-color";
          description
            "Import  policy to be applied on ipv6 colored route";
          uses apply-advanced;
          leaf rib-group-name {
            type string {
              length "1 .. 64";
            }
            mandatory true;
            description
              "Rib-group import policy";
          }
        }
        container tag {
          presence "enable tag";
          description
            "Import  policy to be applied on mpls route";
          uses apply-advanced;
          leaf rib-group-name {
            type string {
              length "1 .. 64";
            }
            mandatory true;
            description
              "Rib-group import policy";
          }
        }
      }
      container telemetry {
        description
          "Enable telemetry on SR-TE policies";
        uses apply-advanced;
        container statistics {
          presence "enable statistics";
          description
            "Enable traffic-statistics collection on SR-TE policies";
          uses apply-advanced;
          leaf no-transit {
            type empty;
            description
              "Disable statistics collection on binding sid route";
          }
          leaf no-ingress {
            type empty;
            description
              "Disable statistics collection on destination route";
          }
          container per-source {
            description
              "Enable traffic-statistics collection per source";
            uses apply-advanced;
            leaf per-segment-list {
              type empty;
              description
                "Enable per path level traffic-statistics collection";
            }
          }
        }
      }
      container traffic-engineering {
        description
          "Enable import of all Spring-TE policies into TED";
        uses apply-advanced;
        leaf database {
          type empty;
          description
            "Spring-TE policies Traffic engineering database";
        }
      }
      container use-transport-class {
        presence "enable use-transport-class";
        description
          "Enable transport class on SR-TE colored policies";
        uses apply-advanced;
        leaf fib-install {
          type empty;
          description
            "Install SRTE routes in FIB";
        }
        leaf inet3-install {
          type empty;
          description
            "Install SRTE routes in inet{6}.3 table";
        }
      }
      leaf inet-color-append-explicit-null {
        type empty;
        description
          "Enable appending explicit NULL for inet SRTE policy";
      }
      leaf retry-timer {
        type union {
          type string {
            pattern "<.*>|$.*";
          }
          type int32 {
            range "1 .. 600";
          }
        }
        units "seconds";
        description
          "Time before retrying auto-translation failed paths";
      }
      leaf import-color-only-cross-af {
        type empty;
        description
          "Enable importing of Null Endpoint color route for cross address family";
      }
      leaf inet6-color-append-explicit-null {
        type empty;
        description
          "Enable appending explicit NULL for inet6 SRTE policy";
      }
      leaf ipv6-tunneling-append-explicit-null {
        type empty;
        description
          "Enable appending explicit NULL for v4ov6 SRTE routes ";
      }
      container source-routing-path-template-map {
        description
          "Configure a source routing path template map";
        uses apply-advanced;
        leaf-list policy {
          type jt:policy-algebra;
          ordered-by user;
          description
            "Configure policy";
        }
      }
    }
    container dcbx {
      presence "enable dcbx";
    }
    container lldp {
      description
        "Link Layer Detection Protocol";
      uses apply-advanced;
      choice enable-disable {
        case case_1 {
          leaf disable {
            type empty;
            description
              "Disable LLDP";
          }
        }
      }
      container traceoptions {
        description
          "Trace options for LLDP";
        uses apply-advanced;
        container file {
          description
            "Trace file options";
          leaf filename {
            type string {
              length "1 .. 1024";
            }
            description
              "Name of file in which to write trace information";
          }
          leaf replace {
            type empty;
            status deprecated;
            description
              "Replace trace file rather than appending to it";
          }
          leaf size {
            type string;
            description
              "Maximum trace file size";
          }
          leaf files {
            type union {
              type string {
                pattern "<.*>|$.*";
              }
              type uint32 {
                range "2 .. 1000";
              }
            }
            default "10";
            description
              "Maximum number of trace files";
          }
          leaf no-stamp {
            type empty;
            status deprecated;
            description
              "Do not timestamp trace file";
          }
          choice world-readable-choice {
            leaf world-readable {
              type empty;
              description
                "Allow any user to read the log file";
            }
            leaf no-world-readable {
              type empty;
              description
                "Don't allow any user to read the log file";
            }
          }
        }
        list flag {
          key "name";
          description
            "Tracing parameters";
          leaf name {
            type enumeration {
              enum "all" {
                description
                  "Trace configuration events";
              }
              enum "configuration" {
                description
                  "Log configuration events";
              }
              enum "rtsock" {
                description
                  "Trace rtsock message events";
              }
              enum "packet" {
                description
                  "Trace packet information";
              }
              enum "protocol" {
                description
                  "Trace protocol information";
              }
              enum "interface" {
                description
                  "Trace interface update events";
              }
              enum "vlan" {
                description
                  "Trace VLAN update events";
              }
              enum "snmp" {
                description
                  "Trace SNMP events";
              }
              enum "jvision" {
                description
                  "Trace Jvision events";
              }
            }
          }
          leaf disable {
            type empty;
            description
              "Disable this trace flag";
          }
        }
      }
      leaf management-address {
        type jt:ipaddr;
        description
          "LLDP management address";
      }
      leaf advertisement-interval {
        type union {
          type string {
            pattern "<.*>|$.*";
          }
          type uint32 {
            range "5 .. 32768";
          }
        }
        units "seconds";
        default "30";
        description
          "Transmit interval for LLDP messages";
      }
      leaf transmit-delay {
        type union {
          type string {
            pattern "<.*>|$.*";
          }
          type uint32 {
            range "1 .. 8192";
          }
        }
        units "seconds";
        description
          "Transmit delay time interval for LLDP messages";
      }
      leaf hold-multiplier {
        type union {
          type string {
            pattern "<.*>|$.*";
          }
          type uint32 {
            range "2 .. 10";
          }
        }
        default "4";
        description
          "Hold timer interval for LLDP messages";
      }
      leaf port-id-subtype {
        type enumeration {
          enum "locally-assigned" {
            description
              "Locally assigned value (SNMP index of the interface)";
          }
          enum "interface-name" {
            description
              "Interface name on which LLDPDU is sent";
          }
        }
        default "locally-assigned";
        description
          "Sub-type to be used for Port ID TLV generation";
      }
      container chassis-id {
        description
          "Chassis-id to be used for Chassis ID TLV generation";
        uses apply-advanced;
        leaf chassis-id-type {
          type enumeration {
            enum "chassis-component" {
              description
                "User define chassis component name.";
            }
            enum "interface-alias" {
              description
                "Interface description or name on which LLDPDU is sent";
            }
            enum "port-component" {
              description
                "User define port component name";
            }
            enum "mac-address" {
              description
                "MAC Address of Interface on which LLDPDU is sent";
            }
            enum "network-address" {
              description
                "Netwok Address of Interface on which LLDPDU is sent";
            }
            enum "interface-name" {
              description
                "Interface name on which LLDPDU is sent";
            }
            enum "locally-assigned" {
              description
                "Locally assigned value (SNMP index of the interface)";
            }
          }
          description
            "Chassis-id-type to be used for Chassis ID TLV generation";
        }
        leaf chassis-id-value {
          type string {
            length "1 .. 256";
          }
          description
            "Chassis-id value as per chassis id type";
        }
      }
      leaf port-description-type {
        type enumeration {
          enum "interface-alias" {
            description
              "Use object ifAlias value for TLV generation";
          }
          enum "interface-description" {
            description
              "Use object ifDescr value for TLV generation";
          }
        }
        default "interface-alias";
        description
          "The Interfaces Group MIB object to be used for Port Description TLV generation";
      }
      leaf neighbour-port-info-display {
        type enumeration {
          enum "port-id" {
            description
              "Display port-id information of neighbor in port info";
          }
          enum "port-description" {
            description
              "Display port description of neighbor in port info";
          }
        }
        description
          "Show lldp neighbors to display port-id or port-description ";
      }
      leaf mau-type {
        type empty;
        description
          "Populate mau-type in lldp PDU";
      }
      leaf lldp-tx-fast-init {
        type union {
          type string {
            pattern "<.*>|$.*";
          }
          type uint32 {
            range "1 .. 8";
          }
        }
        description
          "Transmission count in fast transmission mode";
      }
      leaf fast-rx-processing {
        type empty;
        description
          "Start optimised processing of received pdu";
      }
      leaf-list tlv-select {
        type enumeration {
          enum "port-description" {
            description
              "Port Description";
          }
          enum "system-name" {
            description
              "System Name";
          }
          enum "system-description" {
            description
              "System Description";
          }
          enum "system-capabilities" {
            description
              "System Capabilities";
          }
          enum "management-address" {
            description
              "Management Address";
          }
          enum "mac-phy-config-status" {
            description
              "OUI IEEE 802.3 mac-phy-config-status";
          }
          enum "power-vi-mdi" {
            description
              "OUI IEEE 802.3 power-vi-mdi";
          }
          enum "link-aggregation" {
            description
              "OUI IEEE 802.3 link-aggregation";
          }
          enum "maximum-frame-size" {
            description
              "OUI IEEE 802.3 maximum-frame-size";
          }
          enum "jnpr-chassis-serial" {
            description
              "OUI Juniper chassis-serial";
          }
          enum "jnpr-vcp" {
            description
              "OUI Juniper vcp";
          }
          enum "jnpr-mode-change" {
            description
              "OUI Juniper mode-change";
          }
          enum "jnpr-mode-change-error" {
            description
              "OUI Juniper mode-change-error";
          }
          enum "jnpr-mode-change-ip-address" {
            description
              "OUI Juniper mode-change-ip-address";
          }
          enum "jnpr-mode-change-image-name" {
            description
              "OUI Juniper mode-change-image-name";
          }
          enum "jnpr-mode-change-ftp-login" {
            description
              "OUI Juniper mode-change-ftp-login";
          }
          enum "jnpr-mode-change-image-md5" {
            description
              "OUI Juniper mode-change-image-md5";
          }
          enum "jnpr-mode-change-ftp-server" {
            description
              "OUI Juniper mode-change-ftp-server";
          }
          enum "port-vid" {
            description
              "OUI IEEE 802.1 port-vid";
          }
          enum "port-protocol-vid" {
            description
              "OUI IEEE 802.1 port-procol-vid";
          }
          enum "vlan-name" {
            description
              "OUI IEEE 802.1 vlan-name";
          }
          enum "protocol-id" {
            description
              "OUI IEEE 802.1 protocol-id";
          }
          enum "link-aggregation-8021" {
            description
              "OUI IEEE 802.1 link-aggregation";
          }
          enum "dcbx-ets-configuration" {
            description
              "OUI IEEE 802.1 dcbx ets configuration";
          }
          enum "dcbx-ets-recommendation" {
            description
              "OUI IEEE 802.1 dcbx ets recommendation";
          }
          enum "dcbx-priority-flow-control" {
            description
              "OUI IEEE 802.1 dcbx pfc";
          }
          enum "dcbx-version-101" {
            description
              "OUI IEEE 802.1 dcbx version 1.01";
          }
          enum "evb" {
            description
              "OUI IEEE 82.1QBG evb";
          }
          enum "power-via-mdi-measurements" {
            description
              "OUI IEEE 802.3 power-via-mdi-measurements";
          }
          enum "cloud-reach-event" {
            description
              "Cloud reachability event";
          }
          enum "phone-home-active" {
            description
              "Phone-home active configuration";
          }
          enum "cloud-connect-event" {
            description
              "Cloud-connectivity configuration";
          }
        }
        ordered-by user;
        description
          "Select TLVs to be sent";
      }
      leaf-list tlv-filter {
        type enumeration {
          enum "all" {
            description
              "Filter all non mandatory TLVs";
          }
          enum "port-description" {
            description
              "Port Description";
          }
          enum "system-name" {
            description
              "System Name";
          }
          enum "system-description" {
            description
              "System Description";
          }
          enum "system-capabilities" {
            description
              "System Capabilities";
          }
          enum "management-address" {
            description
              "Management Address";
          }
          enum "mac-phy-config-status" {
            description
              "OUI IEEE 802.3 mac-phy-config-status";
          }
          enum "power-vi-mdi" {
            description
              "OUI IEEE 802.3 power-vi-mdi";
          }
          enum "link-aggregation" {
            description
              "OUI IEEE 802.3 link-aggregation";
          }
          enum "maximum-frame-size" {
            description
              "OUI IEEE 802.3 maximum-frame-size";
          }
          enum "jnpr-chassis-serial" {
            description
              "OUI Juniper chassis-serial";
          }
          enum "jnpr-vcp" {
            description
              "OUI Juniper vcp";
          }
          enum "jnpr-mode-change" {
            description
              "OUI Juniper mode-change";
          }
          enum "jnpr-mode-change-error" {
            description
              "OUI Juniper mode-change-error";
          }
          enum "jnpr-mode-change-ip-address" {
            description
              "OUI Juniper mode-change-ip-address";
          }
          enum "jnpr-mode-change-image-name" {
            description
              "OUI Juniper mode-change-image-name";
          }
          enum "jnpr-mode-change-ftp-login" {
            description
              "OUI Juniper mode-change-ftp-login";
          }
          enum "jnpr-mode-change-image-md5" {
            description
              "OUI Juniper mode-change-image-md5";
          }
          enum "jnpr-mode-change-ftp-server" {
            description
              "OUI Juniper mode-change-ftp-server";
          }
          enum "port-vid" {
            description
              "OUI IEEE 802.1 port-vid";
          }
          enum "port-protocol-vid" {
            description
              "OUI IEEE 802.1 port-procol-vid";
          }
          enum "vlan-name" {
            description
              "OUI IEEE 802.1 vlan-name";
          }
          enum "protocol-id" {
            description
              "OUI IEEE 802.1 protocol-id";
          }
          enum "link-aggregation-8021" {
            description
              "OUI IEEE 802.1 Link Aggregation";
          }
          enum "dcbx-priority-flow-control" {
            description
              "OUI IEEE 802.1 dcbx pfc";
          }
          enum "dcbx-ets-configuration" {
            description
              "OUI IEEE 802.1 dcbx ets configuration";
          }
          enum "dcbx-ets-recommendation" {
            description
              "OUI IEEE 802.1 dcbx ets recommendation";
          }
          enum "dcbx-version-101" {
            description
              "OUI IEEE 802.1 dcbx version 1.01";
          }
          enum "evb" {
            description
              "OUI IEEE 802.1QBG evb";
          }
          enum "power-via-mdi-measurements" {
            description
              "OUI IEEE 802.3 power-via-mdi-measurements";
          }
          enum "cloud-reach-event" {
            description
              "Cloud reachability event";
          }
          enum "phone-home-active" {
            description
              "Phone-home active configuration";
          }
          enum "cloud-connect-event" {
            description
              "Cloud-connectivity configuration";
          }
        }
        ordered-by user;
        description
          "Filter TLVs to be sent";
      }
      leaf dest-mac-type {
        type enumeration {
          enum "nearest-bridge" {
            description
              "To set destination mac as 01:80:C2:00:00:0E";
          }
          enum "nearest-non-tpmr-bridge" {
            description
              "To set destination mac as 01:80:C2:00:00:03";
          }
          enum "nearest-customer-bridge" {
            description
              "To set destination mac as 01:80:C2:00:00:00";
          }
        }
        description
          "Destination address to be used";
      }
      leaf management-interface {
        type union {
          type jt:interface-name;
          type string {
            pattern "<.*>|$.*";
          }
        }
        description
          "Management interface to be used in LLDP PDUs";
      }
      list interface {
        key "name";
        ordered-by user;
        description
          "Interface configuration";
        leaf name {
          type string;
        }
        uses apply-advanced;
        choice enable-disable {
          case case_1 {
            leaf disable {
              type empty;
              description
                "Disable LLDP";
            }
          }
        }
        leaf-list tlv-select {
          type enumeration {
            enum "port-description" {
              description
                "Port Description";
            }
            enum "system-name" {
              description
                "System Name";
            }
            enum "system-description" {
              description
                "System Description";
            }
            enum "system-capabilities" {
              description
                "System Capabilities";
            }
            enum "management-address" {
              description
                "Management Address";
            }
            enum "mac-phy-config-status" {
              description
                "OUI IEEE 802.3 mac-phy-config-status";
            }
            enum "power-vi-mdi" {
              description
                "OUI IEEE 802.3 power-vi-mdi";
            }
            enum "link-aggregation" {
              description
                "OUI IEEE 802.3 link-aggregation";
            }
            enum "maximum-frame-size" {
              description
                "OUI IEEE 802.3 maximum-frame-size";
            }
            enum "jnpr-chassis-serial" {
              description
                "OUI Juniper chassis-serial";
            }
            enum "jnpr-vcp" {
              description
                "OUI Juniper vcp";
            }
            enum "jnpr-mode-change" {
              description
                "OUI Juniper mode-change";
            }
            enum "jnpr-mode-change-error" {
              description
                "OUI Juniper mode-change-error";
            }
            enum "jnpr-mode-change-ip-address" {
              description
                "OUI Juniper mode-change-ip-address";
            }
            enum "jnpr-mode-change-image-name" {
              description
                "OUI Juniper mode-change-image-name";
            }
            enum "jnpr-mode-change-ftp-login" {
              description
                "OUI Juniper mode-change-ftp-login";
            }
            enum "jnpr-mode-change-image-md5" {
              description
                "OUI Juniper mode-change-image-md5";
            }
            enum "jnpr-mode-change-ftp-server" {
              description
                "OUI Juniper mode-change-ftp-server";
            }
            enum "port-vid" {
              description
                "OUI IEEE 802.1 port-vid";
            }
            enum "port-protocol-vid" {
              description
                "OUI IEEE 802.1 port-procol-vid";
            }
            enum "vlan-name" {
              description
                "OUI IEEE 802.1 vlan-name";
            }
            enum "protocol-id" {
              description
                "OUI IEEE 802.1 protocol-id";
            }
            enum "link-aggregation-8021" {
              description
                "OUI IEEE 802.1 link-aggregation";
            }
            enum "dcbx-ets-configuration" {
              description
                "OUI IEEE 802.1 dcbx ets configuration";
            }
            enum "dcbx-ets-recommendation" {
              description
                "OUI IEEE 802.1 dcbx ets recommendation";
            }
            enum "dcbx-priority-flow-control" {
              description
                "OUI IEEE 802.1 dcbx pfc";
            }
            enum "dcbx-version-101" {
              description
                "OUI IEEE 802.1 dcbx version 1.01";
            }
            enum "evb" {
              description
                "OUI IEEE 82.1QBG evb";
            }
            enum "power-via-mdi-measurements" {
              description
                "OUI IEEE 802.3 power-via-mdi-measurements";
            }
            enum "cloud-reach-event" {
              description
                "Cloud reachability event";
            }
            enum "phone-home-active" {
              description
                "Phone-home active configuration";
            }
            enum "cloud-connect-event" {
              description
                "Cloud-connectivity configuration";
            }
          }
          ordered-by user;
          description
            "Select TLV(s) to be sent";
        }
        leaf-list tlv-filter {
          type enumeration {
            enum "all" {
              description
                "Filter all non mandatory TLVs";
            }
            enum "port-description" {
              description
                "Port Description";
            }
            enum "system-name" {
              description
                "System Name";
            }
            enum "system-description" {
              description
                "System Description";
            }
            enum "system-capabilities" {
              description
                "System Capabilities";
            }
            enum "management-address" {
              description
                "Management Address";
            }
            enum "mac-phy-config-status" {
              description
                "OUI IEEE 802.3 mac-phy-config-status";
            }
            enum "power-vi-mdi" {
              description
                "OUI IEEE 802.3 power-vi-mdi";
            }
            enum "link-aggregation" {
              description
                "OUI IEEE 802.3 link-aggregation";
            }
            enum "maximum-frame-size" {
              description
                "OUI IEEE 802.3 maximum-frame-size";
            }
            enum "jnpr-chassis-serial" {
              description
                "OUI Juniper chassis-serial";
            }
            enum "jnpr-vcp" {
              description
                "OUI Juniper vcp";
            }
            enum "jnpr-mode-change" {
              description
                "OUI Juniper mode-change";
            }
            enum "jnpr-mode-change-error" {
              description
                "OUI Juniper mode-change-error";
            }
            enum "jnpr-mode-change-ip-address" {
              description
                "OUI Juniper mode-change-ip-address";
            }
            enum "jnpr-mode-change-image-name" {
              description
                "OUI Juniper mode-change-image-name";
            }
            enum "jnpr-mode-change-ftp-login" {
              description
                "OUI Juniper mode-change-ftp-login";
            }
            enum "jnpr-mode-change-image-md5" {
              description
                "OUI Juniper mode-change-image-md5";
            }
            enum "jnpr-mode-change-ftp-server" {
              description
                "OUI Juniper mode-change-ftp-server";
            }
            enum "port-vid" {
              description
                "OUI IEEE 802.1 port-vid";
            }
            enum "port-protocol-vid" {
              description
                "OUI IEEE 802.1 port-procol-vid";
            }
            enum "vlan-name" {
              description
                "OUI IEEE 802.1 vlan-name";
            }
            enum "protocol-id" {
              description
                "OUI IEEE 802.1 protocol-id";
            }
            enum "link-aggregation-8021" {
              description
                "OUI IEEE 802.1 Link Aggregation";
            }
            enum "dcbx-priority-flow-control" {
              description
                "OUI IEEE 802.1 dcbx pfc";
            }
            enum "dcbx-ets-configuration" {
              description
                "OUI IEEE 802.1 dcbx ets configuration";
            }
            enum "dcbx-ets-recommendation" {
              description
                "OUI IEEE 802.1 dcbx ets recommendation";
            }
            enum "dcbx-version-101" {
              description
                "OUI IEEE 802.1 dcbx version 1.01";
            }
            enum "evb" {
              description
                "OUI IEEE 802.1QBG evb";
            }
            enum "power-via-mdi-measurements" {
              description
                "OUI IEEE 802.3 power-via-mdi-measurements";
            }
            enum "cloud-reach-event" {
              description
                "Cloud reachability event";
            }
            enum "phone-home-active" {
              description
                "Phone-home active configuration";
            }
            enum "cloud-connect-event" {
              description
                "Cloud-connectivity configuration";
            }
          }
          ordered-by user;
          description
            "Filter TLV(s) to be sent";
        }
        leaf dest-mac-type {
          type enumeration {
            enum "nearest-bridge" {
              description
                "To set destination mac as 01:80:C2:00:00:0E";
            }
            enum "nearest-non-tpmr-bridge" {
              description
                "To set destination mac as 01:80:C2:00:00:03";
            }
            enum "nearest-customer-bridge" {
              description
                "To set destination mac as 01:80:C2:00:00:00";
            }
          }
          description
            "Destination address to be used";
        }
      }
      leaf system-name {
        type string {
          length "1 .. 255";
        }
        description
          "System name to be used in system-name TLV";
      }
      leaf system-description {
        type string {
          length "1 .. 255";
        }
        description
          "System description to be used in system-description TLV";
      }
    }
    container layer2-control {
      description
        "Global options for layer 2 protocols";
      uses juniper-protocols-l2control;
    }
    container loop-detect {
      presence "enable loop-detect";
      description
        "Layer2 Loop Detect on interface with non-IP L2 Multicast mac as destination mac";
      uses apply-advanced;
      list interface {
        key "name";
        ordered-by user;
        description
          "Interface name to block Loop Detect PDUs on";
        leaf name {
          type string;
        }
        uses apply-advanced;
        leaf disable {
          type empty;
          description
            "Disable loop detect feature on a port";
        }
      }
      container enhanced {
        description
          "Enhanced loop detect configuration";
        uses apply-advanced;
        list interface {
          key "name";
          ordered-by user;
          description
            "Name of interface";
          leaf name {
            type string;
          }
          uses apply-advanced;
          leaf vlan-id {
            type string;
            description
              "VLAN identifier for trunk interface or all";
          }
          leaf loop-detect-action {
            type enumeration {
              enum "interface-down" {
                description
                  "Interface down action";
              }
              enum "laser-off" {
                description
                  "Laser off action";
              }
            }
            default "interface-down";
            description
              "Action that needs to be taken";
          }
          leaf transmit-interval {
            type enumeration {
              enum "1s";
              enum "10s";
              enum "1m";
              enum "10m";
            }
            default "1s";
            description
              "Interval between loop-detect messages";
          }
          leaf revert-interval {
            type union {
              type string {
                pattern "<.*>|$.*";
              }
              type uint32 {
                range "0 .. 300";
              }
            }
            units "seconds";
            default "0";
            description
              "Interval after which action will be reverted";
          }
        }
      }
      leaf destination-mac {
        type jt:mac-multicast;
        description
          "Destination non-IP L2 multicast mac to be used for transmitting Loop Detect PDUs";
      }
      leaf transmit-interval {
        type union {
          type string {
            pattern "<.*>|$.*";
          }
          type uint16 {
            range "5 .. 3600";
          }
        }
        units "seconds";
        description
          "Loop Detect PDU TX interval in sec --default 30s";
      }
    }
    container mvrp {
      description
        "MVRP configuration";
      uses juniper-protocols-mvrp;
    }
    container oam {
      presence "enable oam";
      uses apply-advanced;
      container ethernet {
        presence "enable ethernet";
        uses apply-advanced;
        container fnp {
          presence "enable fnp";
          description
            "Failure notification protocol configuration";
          uses apply-advanced;
          container traceoptions {
            description
              "Tracing options for FNP";
            uses apply-advanced;
            container file {
              description
                "Trace file options";
              leaf filename {
                type string {
                  length "1 .. 1024";
                }
                description
                  "Name of file in which to write trace information";
              }
              leaf replace {
                type empty;
                status deprecated;
                description
                  "Replace trace file rather than appending to it";
              }
              leaf size {
                type string;
                description
                  "Maximum trace file size";
              }
              leaf files {
                type union {
                  type string {
                    pattern "<.*>|$.*";
                  }
                  type uint32 {
                    range "2 .. 1000";
                  }
                }
                default "10";
                description
                  "Maximum number of trace files";
              }
              leaf no-stamp {
                type empty;
                status deprecated;
                description
                  "Do not timestamp trace file";
              }
              choice world-readable-choice {
                leaf world-readable {
                  type empty;
                  description
                    "Allow any user to read the log file";
                }
                leaf no-world-readable {
                  type empty;
                  description
                    "Don't allow any user to read the log file";
                }
              }
            }
            list flag {
              key "name";
              ordered-by user;
              description
                "Tracing parameters";
              leaf name {
                type enumeration {
                  enum "events" {
                    description
                      "Trace protocol events";
                  }
                  enum "pdu" {
                    description
                      "Trace PDU reception and transmission";
                  }
                  enum "timers" {
                    description
                      "Trace protocol timers";
                  }
                  enum "error" {
                    description
                      "Trace all failure conditions";
                  }
                  enum "all" {
                    description
                      "Trace all";
                  }
                }
              }
            }
          }
          leaf interval {
            type enumeration {
              enum "100ms";
              enum "1s";
              enum "10s";
              enum "1m";
              enum "10m";
            }
            default "1s";
            description
              "Interval between FNP messages";
          }
          leaf loss-threshold {
            type union {
              type string {
                pattern "<.*>|$.*";
              }
              type uint8 {
                range "3 .. 255";
              }
            }
            default "4";
            description
              "Number of FNP messages lost before clearing FNP state";
          }
          list interface {
            key "name";
            ordered-by user;
            description
              "Interface configuration";
            leaf name {
              type union {
                type jt:interface-name;
                type string {
                  pattern "<.*>|$.*";
                }
              }
            }
            uses apply-advanced;
            leaf domain-id {
              type union {
                type uint32;
                type string {
                  pattern "<.*>|$.*";
                }
              }
              default "0";
              description
                "Ethernet domain identifier";
            }
          }
        }
      }
    }
  }

  grouping admin_group_include_exclude {
    uses apply-advanced;
    choice include-any-choice {
      case case_1 {
        leaf-list include-any {
          type string;
          ordered-by user;
          description
            "Groups, one or more of which must be present";
        }
      }
    }
    choice include-all-choice {
      case case_1 {
        leaf-list include-all {
          type string;
          ordered-by user;
          description
            "Groups, all of which must be present";
        }
      }
    }
    choice exclude-choice {
      case case_1 {
        leaf-list exclude {
          type string;
          ordered-by user;
          description
            "Groups, all of which must be absent";
        }
      }
    }
  }

  grouping juniper-ospf-authentication {
    description
      "Authentication information";
    uses apply-advanced;
    choice authentication-type {
      case case_1 {
        leaf simple-password {
          type jt:unreadable;
          description
            "Authentication key";
        }
      }
      case case_2 {
        list md5 {
          key "name";
          ordered-by user;
          description
            "MD5 authentication key";
          leaf name {
            type union {
              type string {
                pattern "<.*>|$.*";
              }
              type uint32 {
                range "0 .. 255";
              }
            }
            description
              "Key ID for MD5 authentication";
          }
          leaf key {
            type jt:unreadable;
            mandatory true;
            description
              "MD5 authentication key value";
          }
          leaf start-time {
            type jt:time;
            description
              "Start time for key transmission (YYYY-MM-DD.HH:MM)";
          }
        }
      }
      case case_3 {
        list multi-active-md5 {
          key "name";
          ordered-by user;
          description
            "Authentication Multiple active MD5 keys";
          leaf name {
            type union {
              type string {
                pattern "<.*>|$.*";
              }
              type uint32 {
                range "0 .. 255";
              }
            }
            description
              "Key ID for MD5 authentication";
          }
          leaf key {
            type jt:unreadable;
            mandatory true;
            description
              "MD5 authentication key value";
          }
          leaf delete-if-not-inuse {
            type empty;
            description
              "Delete this key if not in use";
          }
        }
      }
      case case_4 {
        leaf keychain {
          type string {
            length "1 .. 128";
          }
          description
            "Key chain name";
        }
      }
    }
  }

  grouping juniper-protocols-bgp {
    uses apply-advanced;
    container path-selection {
      description
        "Configure path selection strategy";
      uses apply-advanced;
      leaf l2vpn-use-bgp-rules {
        type empty;
        description
          "Use standard BGP rules during L2VPN path selection";
      }
      leaf cisco-non-deterministic {
        type empty;
        description
          "Use Cisco IOS nondeterministic path selection algorithm";
      }
      leaf always-compare-med {
        type empty;
        description
          "Always compare MED values, regardless of neighbor AS";
      }
      container med-plus-igp {
        presence "enable med-plus-igp";
        description
          "Add IGP cost to next-hop to MED before comparing MED values";
        uses apply-advanced;
        leaf med-multiplier {
          type union {
            type string {
              pattern "<.*>|$.*";
            }
            type uint16 {
              range "1 .. 1000";
            }
          }
          default "1";
          description
            "Multiplier for MED";
        }
        leaf igp-multiplier {
          type union {
            type string {
              pattern "<.*>|$.*";
            }
            type uint16 {
              range "1 .. 1000";
            }
          }
          default "1";
          description
            "Multiplier for IGP cost to next-hop";
        }
      }
      leaf external-router-id {
        type empty;
        description
          "Compare router ID on BGP externals";
      }
      leaf as-path-ignore {
        type empty;
        description
          "Ignore AS path comparison during path selection";
      }
    }
    container accept-prpd-connection {
      presence "enable accept-prpd-connection";
      description
        "Enable BGP to accept PRPD connections";
    }
    container global-load-balancing {
      presence "enable global-load-balancing";
      description
        "Enable global load balancing";
      uses apply-advanced;
      choice mode {
        case case_1 {
          leaf helper-only {
            type empty;
            description
              "Work as helper role only";
          }
        }
        case case_2 {
          leaf load-balancer-only {
            type empty;
            description
              "Work as load balancer role only";
          }
        }
      }
    }
    leaf advertise-from-main-vpn-tables {
      type empty;
      description
        "Advertise VPN routes from bgp.Xvpn.0 tables in master instance";
    }
    leaf stale-labels-holddown-period {
      type union {
        type string {
          pattern "<.*>|$.*";
        }
        type int32 {
          range "1 .. 600";
        }
      }
      description
        "Duration (sec) MPLS labels allocated by BGP are kept after they go stale";
    }
    leaf holddown-all-stale-labels {
      type empty;
      description
        "Hold all BGP stale-labels, facilitating make-before-break for new label advertisements";
    }
    container egress-te-backup-paths {
      description
        "Backup-path for Egress-TE peer interface failure";
      uses apply-advanced;
      list template {
        key "name";
        description
          "Backup-path template";
        leaf name {
          type string;
          description
            "Name of Egress-TE backup path";
        }
        uses apply-advanced;
        list peer {
          key "name";
          ordered-by user;
          description
            "Egress peer TE backup exit path";
          leaf name {
            type jt:ipaddr;
            description
              "Address of BGP peer to use as backup next-hop";
          }
          uses apply-advanced;
        }
        container remote-nexthop {
          description
            "Resolve and use tunnel to this next-hop as backup path";
          uses apply-advanced;
          leaf remote-nh-addr {
            type jt:ipaddr;
            mandatory true;
            description
              "Address of remote-nexthop to use as backup path";
          }
        }
        container ip-forward {
          presence "enable ip-forward";
          description
            "Use IP-forward backup path for Egress TE";
          uses apply-advanced;
          leaf rti-name {
            type string;
            description
              "Routing-instance to use as IP forward backup-path";
          }
        }
      }
    }
    leaf sr-preference-override {
      type union {
        type uint32;
        type string {
          pattern "<.*>|$.*";
        }
      }
      description
        "Replace received segment routing traffic engineering preference value with override value";
    }
    leaf vpn-apply-export {
      type empty;
      description
        "Apply BGP export policy when exporting VPN routes";
    }
    container family {
      description
        "Protocol family for NLRIs in updates";
      uses apply-advanced;
      container inet {
        description
          "IPv4 NLRI parameters";
        uses apply-advanced;
        container labeled-unicast {
          presence "enable labeled-unicast";
          description
            "Include labeled unicast NLRI";
          uses bgp-afi-labeled;
        }
        container segment-routing-te {
          presence "enable segment-routing-te";
          description
            "Include segment-routing TE policy";
          uses bgp-afi-srte;
        }
        container transport {
          presence "enable transport";
          description
            "Include Classful Transport NLRI";
          uses bgp-afi-inet-transport;
        }
        container unicast {
          presence "enable unicast";
          description
            "Include unicast NLRI";
          uses bgp-afi-topo;
        }
        container multicast {
          presence "enable multicast";
          description
            "Include multicast NLRI";
          uses bgp-afi-default;
        }
        container flow {
          presence "enable flow";
          description
            "Include flow NLRI";
          uses bgp-afi-flow-with-redirect-ip-action;
        }
        container any {
          presence "enable any";
          description
            "Include unicast or multicast NLRI";
          uses bgp-afi-default;
        }
      }
      container inet-vpn {
        description
          "IPv4 Layer 3 VPN NLRI parameters";
        uses apply-advanced;
        container unicast {
          presence "enable unicast";
          description
            "Include unicast NLRI";
          uses bgp-afi-l3vpn;
        }
        container multicast {
          presence "enable multicast";
          description
            "Include multicast NLRI";
          uses bgp-afi-vpn;
        }
        container flow {
          presence "enable flow";
          description
            "Include flow VPN NLRI";
          uses bgp-afi-flow-with-redirect-ip-action;
        }
        container any {
          presence "enable any";
          description
            "Include unicast or multicast NLRI";
          uses bgp-afi-vpn;
        }
      }
      container inet6 {
        description
          "IPv6 NLRI parameters";
        uses apply-advanced;
        container labeled-unicast {
          presence "enable labeled-unicast";
          description
            "Include labeled unicast NLRI";
          uses bgp-afi-inet6-labeled;
        }
        container segment-routing-te {
          presence "enable segment-routing-te";
          description
            "Include segment-routing TE policy";
          uses bgp-afi-srte;
        }
        container transport {
          presence "enable transport";
          description
            "Include Classful Transport NLRI";
          uses bgp-afi-inet6-transport;
        }
        container unicast {
          presence "enable unicast";
          description
            "Include unicast NLRI";
          uses bgp-afi-topo;
        }
        container multicast {
          presence "enable multicast";
          description
            "Include multicast NLRI";
          uses bgp-afi-default;
        }
        container flow {
          presence "enable flow";
          description
            "Include flow NLRI";
          uses bgp-afi-flow;
        }
        container any {
          presence "enable any";
          description
            "Include unicast or multicast NLRI";
          uses bgp-afi-default;
        }
      }
      container inet6-vpn {
        description
          "IPv6 Layer 3 VPN NLRI parameters";
        uses apply-advanced;
        container unicast {
          presence "enable unicast";
          description
            "Include unicast NLRI";
          uses bgp-afi-l3vpn;
        }
        container multicast {
          presence "enable multicast";
          description
            "Include multicast NLRI";
          uses bgp-afi-vpn;
        }
        container flow {
          presence "enable flow";
          description
            "Include flow VPN NLRI";
          uses bgp-afi-flow;
        }
        container any {
          presence "enable any";
          description
            "Include unicast or multicast NLRI";
          uses bgp-afi-vpn;
        }
      }
      container iso-vpn {
        description
          "ISO Layer 3 VPN NLRI parameters";
        uses apply-advanced;
        container unicast {
          presence "enable unicast";
          description
            "Include unicast NLRI";
          uses bgp-afi-vpn-protection;
        }
      }
      container l2vpn {
        description
          "MPLS-based Layer 2 VPN and VPLS NLRI parameters";
        uses apply-advanced;
        container auto-discovery-only {
          presence "enable auto-discovery-only";
          description
            "Include auto-discovery NLRI for LDP Layer 2 VPN and VPLS";
          uses bgp-afi-default;
        }
        container auto-discovery-mspw {
          presence "enable auto-discovery-mspw";
          description
            "Include auto-discovery NLRI for LDP Signalled MultiSegment PW";
          uses bgp-afi-default;
        }
        container signaling {
          presence "enable signaling";
          description
            "Include Layer 2 VPN and VPLS signaling NLRI";
          uses bgp-afi-l2vpn;
        }
      }
      container evpn {
        description
          "EVPN NLRI parameters";
        uses apply-advanced;
        container signaling {
          presence "enable signaling";
          description
            "Include EVPN signaling NLRI";
          uses bgp-afi-default;
        }
      }
      container inet-mvpn {
        description
          "IPv4 MVPN NLRI parameters";
        uses apply-advanced;
        container signaling {
          presence "enable signaling";
          description
            "Include IPv4 multicast VPN signaling NLRI";
          uses bgp-afi-default;
        }
      }
      container inet6-mvpn {
        description
          "IPv6 MVPN NLRI parameters";
        uses apply-advanced;
        container signaling {
          presence "enable signaling";
          description
            "Include IPv6 multicast VPN signaling NLRI";
          uses bgp-afi-default;
        }
      }
      container inet-mdt {
        description
          "IPv4 Multicast Distribution Tree (MDT) NLRI parameters";
        uses apply-advanced;
        container signaling {
          presence "enable signaling";
          description
            "Include IPv4 multicast VPN auto-discovery NLRI";
          uses bgp-afi-default;
        }
      }
      container traffic-engineering {
        description
          "Traffic Engineering (BGP-TE) NLRI parameters";
        uses apply-advanced;
        container unicast {
          presence "enable unicast";
          description
            "Include BGP-TE NLRI";
          uses bgp-afi-default;
        }
      }
      container route-target {
        presence "enable route-target";
        description
          "Route target NLRI used for VPN route filtering";
        uses apply-advanced;
        container prefix-limit {
          description
            "Limit maximum number of prefixes from a peer";
          uses bgpaf-prefix-limit;
        }
        container accepted-prefix-limit {
          description
            "Limit maximum number of prefixes accepted from a peer";
          uses bgpaf-accepted-prefix-limit;
        }
        container proxy-generate {
          presence "enable proxy-generate";
          description
            "Generate route target NLRI for peers that don't support it";
          uses apply-advanced;
          leaf-list route-target-policy {
            type jt:policy-algebra;
            ordered-by user;
            description
              "Limit VPN routes that are used to generate proxy route-target filters";
          }
        }
        leaf external-paths {
          type union {
            type string {
              pattern "<.*>|$.*";
            }
            type uint32 {
              range "1 .. 256";
            }
          }
          description
            "Number of external paths accepted for route filtering";
        }
        leaf advertise-default {
          type empty;
          description
            "Advertise default and suppress more specific routes";
        }
        leaf damping {
          type empty;
          description
            "Enable route flap damping";
        }
        container graceful-restart {
          description
            "BGP graceful restart options";
          uses bgp-af-gr;
        }
        leaf local-ipv4-address {
          type jt:ipv4addr;
          description
            "Local IPv4 address";
        }
        container nexthop-resolution {
          description
            "Configure nexthop resolution properties";
          uses apply-advanced;
          leaf no-resolution {
            type empty;
            description
              "Consider nexthop good without resolution attempt";
          }
        }
        container output-queue-priority {
          description
            "Default output-queue to assign updates to";
          uses bgp-output-queue-priority-class;
        }
        container route-refresh-priority {
          description
            "Default output-queue to assign route refreshes to";
          uses bgp-output-queue-priority-class;
        }
        container withdraw-priority {
          description
            "Default output-queue to assign withdrawn routes to";
          uses bgp-output-queue-priority-class;
        }
        leaf-list export {
          type jt:policy-algebra;
          ordered-by user;
          description
            "Export policy";
        }
        leaf-list import {
          type jt:policy-algebra;
          ordered-by user;
          description
            "Import policy";
        }
      }
      container inet-bgpmcast {
        description
          "IPv4 BGPMCAST NLRI parameters";
        uses apply-advanced;
        container signaling {
          presence "enable signaling";
          description
            "Include IPv4 BGP multicast signaling NLRI";
          uses bgp-afi-default;
        }
      }
      container inet6-bgpmcast {
        description
          "IPv6 BGPMCAST NLRI parameters";
        uses apply-advanced;
        container signaling {
          presence "enable signaling";
          description
            "Include IPv6 BGP multicast signaling NLRI";
          uses bgp-afi-default;
        }
      }
    }
    container egress-te {
      presence "enable egress-te";
      description
        "Use Egress Peering traffic engineering";
      uses apply-advanced;
      leaf install-address {
        type jt:ipaddr;
        description
          "Address to use in egress-te created inet route";
      }
      container rib {
        description
          "Select primary table for Egress-TE routes";
        uses apply-advanced;
        leaf inet.0 {
          type empty;
          description
            "Install Egress-TE routes in inet.0";
        }
        leaf inet6.0 {
          type empty;
          description
            "Install Egress-TE routes in inet6.0";
        }
      }
      leaf no-install {
        type empty;
        description
          "Avoid installation to FIB or resolving over";
      }
      leaf-list import {
        type jt:policy-algebra;
        ordered-by user;
        description
          "Import policy to set attributes";
      }
      leaf backup-path {
        type string;
        description
          "The 'egress-te-backup-paths template' to use for this peer";
      }
    }
    leaf advertise-prefix-sid {
      type empty;
      description
        "Advertise prefix sid to E-BGP peers";
    }
    leaf accept-prefix-sid {
      type empty;
      description
        "Accept prefix sid from E-BGP peers";
    }
    leaf advertise-srgb {
      type empty;
      description
        "Advertise SRGB TLV";
    }
    leaf tcp-connect-port {
      type union {
        type string {
          pattern "<.*>|$.*";
        }
        type uint16 {
          range "1 .. 65535";
        }
      }
      description
        "TCP port number to connect with peer on";
    }
    leaf egress-te-sid-stats {
      type empty;
      description
        "Create BGP-Peer-SID sensor";
    }
    list egress-te-set-segment {
      key "name";
      ordered-by user;
      description
        "Configure BGP-Peer-Set segment";
      leaf name {
        type string;
        description
          "The BGP-Peer-Set segment name";
      }
      uses apply-advanced;
      container label {
        description
          "BGP-Peer-Set SID label from static label pool";
        uses apply-advanced;
        leaf label-value {
          type union {
            type string {
              pattern "<.*>|$.*";
            }
            type uint32 {
              range "16 .. 1048575";
            }
          }
          description
            "BGP-Peer-Set SID label value from static label pool";
        }
      }
      container egress-te-backup-segment {
        description
          "Backup segment for FRR";
        uses apply-advanced;
        container label {
          description
            "Backup segment label from static label pool";
          uses apply-advanced;
          leaf label-value {
            type union {
              type string {
                pattern "<.*>|$.*";
              }
              type uint32 {
                range "16 .. 1048575";
              }
            }
            description
              "Backup segment label value from static label pool";
          }
        }
      }
      container egress-te-backup-ip-forward {
        presence "enable egress-te-backup-ip-forward";
        description
          "Use IP-forward backup path for Egress TE";
        uses apply-advanced;
        leaf instance-name {
          type string;
          description
            "Routing-instance to use as IP forward backup-path";
        }
      }
    }
    list group {
      key "name";
      ordered-by user;
      description
        "Define a peer group";
      leaf name {
        type string;
        description
          "Group name";
      }
      uses apply-advanced;
      leaf type {
        type enumeration {
          enum "internal" {
            description
              "IBGP group";
          }
          enum "external" {
            description
              "EBGP group";
          }
        }
        description
          "Type of peer group";
      }
      leaf protocol {
        type enumeration {
          enum "rip" {
            status deprecated;
            description
              "Use RIP to resolve the BGP next hop";
          }
          enum "ospf" {
            status deprecated;
            description
              "Use OSPF to resolve the BGP next hop";
          }
          enum "isis" {
            status deprecated;
            description
              "Use IS-IS to resolve the BGP next hop";
          }
        }
        status deprecated;
        description
          "IGP to use to resolve the next hop";
      }
      container traceoptions {
        description
          "Trace options for BGP";
        uses apply-advanced;
        container file {
          description
            "Trace file options";
          leaf filename {
            type string {
              length "1 .. 1024";
            }
            description
              "Name of file in which to write trace information";
          }
          leaf replace {
            type empty;
            status deprecated;
            description
              "Replace trace file rather than appending to it";
          }
          leaf size {
            type string;
            description
              "Maximum trace file size";
          }
          leaf files {
            type union {
              type string {
                pattern "<.*>|$.*";
              }
              type uint32 {
                range "2 .. 1000";
              }
            }
            default "10";
            description
              "Maximum number of trace files";
          }
          leaf no-stamp {
            type empty;
            status deprecated;
            description
              "Do not timestamp trace file";
          }
          choice world-readable-choice {
            leaf world-readable {
              type empty;
              description
                "Allow any user to read the log file";
            }
            leaf no-world-readable {
              type empty;
              description
                "Don't allow any user to read the log file";
            }
          }
        }
        list flag {
          key "name";
          ordered-by user;
          description
            "Tracing parameters";
          leaf name {
            type enumeration {
              enum "damping" {
                description
                  "Trace BGP damping information";
              }
              enum "packets" {
                description
                  "Trace all BGP protocol packets";
              }
              enum "open" {
                description
                  "Trace BGP open packets";
              }
              enum "update" {
                description
                  "Trace BGP update packets";
              }
              enum "keepalive" {
                description
                  "Trace BGP keepalive packets";
              }
              enum "refresh" {
                description
                  "Trace BGP refresh packets";
              }
              enum "nsr-synchronization" {
                description
                  "Trace NSR synchronization events";
              }
              enum "bfd" {
                description
                  "Trace BFD events";
              }
              enum "4byte-as" {
                description
                  "Trace 4 byte AS events";
              }
              enum "add-path" {
                description
                  "Trace add-path events";
              }
              enum "graceful-restart" {
                description
                  "Trace Graceful Restart events";
              }
              enum "egress-te" {
                description
                  "Egress Peering Traffic-Engineering events";
              }
              enum "thread-io" {
                description
                  "Trace threaded I/O processing";
              }
              enum "sharding" {
                description
                  "Trace BGP rib sharding";
              }
              enum "glb" {
                description
                  "Trace BGP global-load-balancing";
              }
              enum "thread-update-io" {
                description
                  "Trace threaded update I/O processing";
              }
              enum "route-validation" {
                description
                  "Trace route validation";
              }
              enum "ipsec" {
                description
                  "Trace ipsec";
              }
              enum "route" {
                description
                  "Trace routing information";
              }
              enum "normal" {
                description
                  "Trace normal events";
              }
              enum "general" {
                description
                  "Trace general events";
              }
              enum "state" {
                description
                  "Trace state transitions";
              }
              enum "policy" {
                description
                  "Trace policy processing";
              }
              enum "task" {
                description
                  "Trace routing protocol task processing";
              }
              enum "timer" {
                description
                  "Trace routing protocol timer processing";
              }
              enum "all" {
                description
                  "Trace everything";
              }
            }
          }
          leaf send {
            type empty;
            description
              "Trace transmitted packets";
          }
          leaf receive {
            type empty;
            description
              "Trace received packets";
          }
          leaf detail {
            type empty;
            description
              "Trace detailed information";
          }
          leaf disable {
            type empty;
            description
              "Disable this trace flag";
          }
          container filter {
            presence "enable filter";
            description
              "Filter to apply to this flag";
            uses bgp_filter_obj;
          }
        }
      }
      leaf description {
        type string {
          length "1 .. 255";
        }
        description
          "Text description";
      }
      container metric-out {
        description
          "Route metric sent in MED";
        choice metric_param {
          case case_1 {
            leaf metric-value {
              type union {
                type string {
                  pattern "<.*>|$.*";
                }
                type uint32 {
                  range "0 .. 4294967295";
                }
              }
              description
                "Metric value";
            }
          }
          case case_2 {
            container minimum-igp {
              presence "enable minimum-igp";
              description
                "Track the minimum IGP metric";
              leaf metric-offset {
                type union {
                  type int32;
                  type string {
                    pattern "<.*>|$.*";
                  }
                }
                description
                  "Metric offset for MED";
              }
            }
          }
          case case_3 {
            container igp {
              presence "enable igp";
              description
                "Track the IGP metric";
              leaf metric-offset {
                type union {
                  type int32;
                  type string {
                    pattern "<.*>|$.*";
                  }
                }
                description
                  "Metric offset for MED";
              }
              leaf delay-med-update {
                type empty;
                description
                  "Delay updating MED when IGP metric increases";
              }
            }
          }
          case case_4 {
            container effective-aigp {
              presence "enable effective-aigp";
              description
                "Track the effective AIGP metric";
              leaf metric-offset {
                type union {
                  type int32;
                  type string {
                    pattern "<.*>|$.*";
                  }
                }
                description
                  "Metric offset for MED";
              }
            }
          }
          case case_5 {
            container minimum-effective-aigp {
              presence "enable minimum-effective-aigp";
              description
                "Track the minimum effective AIGP metric";
              leaf metric-offset {
                type union {
                  type int32;
                  type string {
                    pattern "<.*>|$.*";
                  }
                }
                description
                  "Metric offset for MED";
              }
            }
          }
        }
      }
      container multihop {
        presence "enable multihop";
        description
          "Configure an EBGP multihop session";
        uses apply-advanced;
        leaf ttl {
          type union {
            type string {
              pattern "<.*>|$.*";
            }
            type uint8 {
              range "1 .. 255";
            }
          }
          description
            "TTL value for the session";
        }
        leaf no-nexthop-change {
          type empty;
          description
            "Do not change next hop to self in advertisements";
        }
      }
      container ebgp-community-cleanup {
        presence "enable ebgp-community-cleanup";
        description
          "Community specific cleanup for eBGP peers";
        uses apply-advanced;
        leaf origin-validation {
          type enumeration {
            enum "accept" {
              description
                "Accept Origin Validation State Community";
            }
            enum "reject" {
              description
                "Reject Origin Validation State Community";
            }
          }
          description
            "Origin Validation State receive behavior";
        }
      }
      leaf route-server-client {
        type empty;
        description
          "Enable route server client behavior";
      }
      leaf accept-remote-nexthop {
        type empty;
        description
          "Allow import policy to specify a non-directly connected next-hop";
      }
      leaf preference {
        type union {
          type uint32;
          type string {
            pattern "<.*>|$.*";
          }
        }
        description
          "Preference value";
      }
      leaf local-preference {
        type union {
          type uint32;
          type string {
            pattern "<.*>|$.*";
          }
        }
        description
          "Value of LOCAL_PREF path attribute";
      }
      leaf local-address {
        type jt:ipaddr;
        description
          "Address of local end of BGP session";
      }
      leaf local-interface {
        type union {
          type jt:interface-name;
          type string {
            pattern "<.*>|$.*";
          }
        }
        description
          "Local interface for IPv6 link local EBGP peering";
      }
      leaf forwarding-context {
        type string;
        description
          "Routing-instance used for data-forwarding and transport-session";
      }
      leaf hold-time {
        type union {
          type string {
            pattern "<.*>|$.*";
          }
          type uint32 {
            range "0 .. 65535";
          }
        }
        description
          "Hold time used when negotiating with a peer";
      }
      leaf minimum-hold-time {
        type union {
          type string {
            pattern "<.*>|$.*";
          }
          type uint32 {
            range "3 .. 65535";
          }
        }
        description
          "Minimum hold time accepted from the peer";
      }
      leaf passive {
        type empty;
        description
          "Do not send open messages to a peer";
      }
      leaf advertise-inactive {
        type empty;
        description
          "Advertise inactive routes";
      }
      choice advertise-peer-as-choice {
        leaf advertise-peer-as {
          type empty;
          description
            "Advertise routes received from the same autonomous system";
        }
        leaf no-advertise-peer-as {
          type empty;
          description
            "Don't advertise routes received from the same autonomous system";
        }
      }
      container advertise-external {
        presence "enable advertise-external";
        description
          "Advertise best external routes";
        leaf conditional {
          type empty;
          description
            "Route matches active route upto med-comparison rule";
        }
      }
      leaf keep {
        type enumeration {
          enum "all" {
            description
              "Retain all routes";
          }
          enum "none" {
            description
              "Retain no routes";
          }
        }
        description
          "How to retain routes in the routing table";
      }
      leaf rfc6514-compliant-safi129 {
        type empty;
        description
          "Compliant with RFC6514 SAFI129 format";
      }
      leaf no-aggregator-id {
        type empty;
        description
          "Set router ID in aggregator path attribute to 0";
      }
      leaf mtu-discovery {
        type empty;
        description
          "Enable TCP path MTU discovery";
      }
      leaf enforce-first-as {
        type empty;
        description
          "Enforce first AS in AS-path is the neighbor's AS";
      }
      leaf out-delay {
        type union {
          type string {
            pattern "<.*>|$.*";
          }
          type uint32 {
            range "0 .. 65535";
          }
        }
        description
          "How long before exporting routes from routing table";
      }
      leaf ttl {
        type enumeration {
          enum "1";
          enum "255";
        }
        description
          "TTL value for the single-hop peer";
      }
      leaf log-updown {
        type empty;
        description
          "Log a message for peer state transitions";
      }
      leaf damping {
        type empty;
        description
          "Enable route flap damping";
      }
      leaf-list import {
        type jt:policy-algebra;
        ordered-by user;
        description
          "Import policy";
      }
      leaf-list nlri {
        type enumeration {
          enum "unicast" {
            status deprecated;
            description
              "Include unicast NLRI";
          }
          enum "multicast" {
            status deprecated;
            description
              "Include multicast NLRI";
          }
          enum "any" {
            status deprecated;
            description
              "Include any kind of NLRI";
          }
        }
        ordered-by user;
        status deprecated;
        description
          "NLRI type to include in updates";
      }
      container bgp-error-tolerance {
        presence "enable bgp-error-tolerance";
        description
          "Handle BGP malformed updates softly, enabled by default. Configure logging parameters";
        uses apply-advanced;
        leaf malformed-update-log-interval {
          type union {
            type string {
              pattern "<.*>|$.*";
            }
            type uint32 {
              range "10 .. 65535";
            }
          }
          units "seconds";
          default "300";
          description
            "Time used when logging malformed update";
        }
        choice malformed-routes-limit-choice {
          case case_1 {
            leaf malformed-route-limit {
              type union {
                type string {
                  pattern "<.*>|$.*";
                }
                type uint32 {
                  range "0 .. 4294967295";
                }
              }
              default "1000";
              description
                "Maximum number of malformed routes from a peer";
            }
          }
          case case_2 {
            leaf no-malformed-route-limit {
              type empty;
              description
                "No malformed route limit";
            }
          }
        }
      }
      container family {
        description
          "Protocol family for NLRIs in updates";
        uses apply-advanced;
        container inet {
          description
            "IPv4 NLRI parameters";
          uses apply-advanced;
          container labeled-unicast {
            presence "enable labeled-unicast";
            description
              "Include labeled unicast NLRI";
            uses bgp-afi-labeled;
          }
          container segment-routing-te {
            presence "enable segment-routing-te";
            description
              "Include segment-routing TE policy";
            uses bgp-afi-srte;
          }
          container transport {
            presence "enable transport";
            description
              "Include Classful Transport NLRI";
            uses bgp-afi-inet-transport;
          }
          container unicast {
            presence "enable unicast";
            description
              "Include unicast NLRI";
            uses bgp-afi-topo;
          }
          container multicast {
            presence "enable multicast";
            description
              "Include multicast NLRI";
            uses bgp-afi-default;
          }
          container flow {
            presence "enable flow";
            description
              "Include flow NLRI";
            uses bgp-afi-flow-with-redirect-ip-action;
          }
          container any {
            presence "enable any";
            description
              "Include unicast or multicast NLRI";
            uses bgp-afi-default;
          }
        }
        container inet-vpn {
          description
            "IPv4 Layer 3 VPN NLRI parameters";
          uses apply-advanced;
          container unicast {
            presence "enable unicast";
            description
              "Include unicast NLRI";
            uses bgp-afi-l3vpn;
          }
          container multicast {
            presence "enable multicast";
            description
              "Include multicast NLRI";
            uses bgp-afi-vpn;
          }
          container flow {
            presence "enable flow";
            description
              "Include flow VPN NLRI";
            uses bgp-afi-flow-with-redirect-ip-action;
          }
          container any {
            presence "enable any";
            description
              "Include unicast or multicast NLRI";
            uses bgp-afi-vpn;
          }
        }
        container inet6 {
          description
            "IPv6 NLRI parameters";
          uses apply-advanced;
          container labeled-unicast {
            presence "enable labeled-unicast";
            description
              "Include labeled unicast NLRI";
            uses bgp-afi-inet6-labeled;
          }
          container segment-routing-te {
            presence "enable segment-routing-te";
            description
              "Include segment-routing TE policy";
            uses bgp-afi-srte;
          }
          container transport {
            presence "enable transport";
            description
              "Include Classful Transport NLRI";
            uses bgp-afi-inet6-transport;
          }
          container unicast {
            presence "enable unicast";
            description
              "Include unicast NLRI";
            uses bgp-afi-topo;
          }
          container multicast {
            presence "enable multicast";
            description
              "Include multicast NLRI";
            uses bgp-afi-default;
          }
          container flow {
            presence "enable flow";
            description
              "Include flow NLRI";
            uses bgp-afi-flow;
          }
          container any {
            presence "enable any";
            description
              "Include unicast or multicast NLRI";
            uses bgp-afi-default;
          }
        }
        container inet6-vpn {
          description
            "IPv6 Layer 3 VPN NLRI parameters";
          uses apply-advanced;
          container unicast {
            presence "enable unicast";
            description
              "Include unicast NLRI";
            uses bgp-afi-l3vpn;
          }
          container multicast {
            presence "enable multicast";
            description
              "Include multicast NLRI";
            uses bgp-afi-vpn;
          }
          container flow {
            presence "enable flow";
            description
              "Include flow VPN NLRI";
            uses bgp-afi-flow;
          }
          container any {
            presence "enable any";
            description
              "Include unicast or multicast NLRI";
            uses bgp-afi-vpn;
          }
        }
        container iso-vpn {
          description
            "ISO Layer 3 VPN NLRI parameters";
          uses apply-advanced;
          container unicast {
            presence "enable unicast";
            description
              "Include unicast NLRI";
            uses bgp-afi-vpn-protection;
          }
        }
        container l2vpn {
          description
            "MPLS-based Layer 2 VPN and VPLS NLRI parameters";
          uses apply-advanced;
          container auto-discovery-only {
            presence "enable auto-discovery-only";
            description
              "Include auto-discovery NLRI for LDP Layer 2 VPN and VPLS";
            uses bgp-afi-default;
          }
          container auto-discovery-mspw {
            presence "enable auto-discovery-mspw";
            description
              "Include auto-discovery NLRI for LDP Signalled MultiSegment PW";
            uses bgp-afi-default;
          }
          container signaling {
            presence "enable signaling";
            description
              "Include Layer 2 VPN and VPLS signaling NLRI";
            uses bgp-afi-l2vpn;
          }
        }
        container evpn {
          description
            "EVPN NLRI parameters";
          uses apply-advanced;
          container signaling {
            presence "enable signaling";
            description
              "Include EVPN signaling NLRI";
            uses bgp-afi-default;
          }
        }
        container inet-mvpn {
          description
            "IPv4 MVPN NLRI parameters";
          uses apply-advanced;
          container signaling {
            presence "enable signaling";
            description
              "Include IPv4 multicast VPN signaling NLRI";
            uses bgp-afi-default;
          }
        }
        container inet6-mvpn {
          description
            "IPv6 MVPN NLRI parameters";
          uses apply-advanced;
          container signaling {
            presence "enable signaling";
            description
              "Include IPv6 multicast VPN signaling NLRI";
            uses bgp-afi-default;
          }
        }
        container inet-mdt {
          description
            "IPv4 Multicast Distribution Tree (MDT) NLRI parameters";
          uses apply-advanced;
          container signaling {
            presence "enable signaling";
            description
              "Include IPv4 multicast VPN auto-discovery NLRI";
            uses bgp-afi-default;
          }
        }
        container traffic-engineering {
          description
            "Traffic Engineering (BGP-TE) NLRI parameters";
          uses apply-advanced;
          container unicast {
            presence "enable unicast";
            description
              "Include BGP-TE NLRI";
            uses bgp-afi-default;
          }
        }
        container route-target {
          presence "enable route-target";
          description
            "Route target NLRI used for VPN route filtering";
          uses apply-advanced;
          container prefix-limit {
            description
              "Limit maximum number of prefixes from a peer";
            uses bgpaf-prefix-limit;
          }
          container accepted-prefix-limit {
            description
              "Limit maximum number of prefixes accepted from a peer";
            uses bgpaf-accepted-prefix-limit;
          }
          container proxy-generate {
            presence "enable proxy-generate";
            description
              "Generate route target NLRI for peers that don't support it";
            uses apply-advanced;
            leaf-list route-target-policy {
              type jt:policy-algebra;
              ordered-by user;
              description
                "Limit VPN routes that are used to generate proxy route-target filters";
            }
          }
          leaf external-paths {
            type union {
              type string {
                pattern "<.*>|$.*";
              }
              type uint32 {
                range "1 .. 256";
              }
            }
            description
              "Number of external paths accepted for route filtering";
          }
          leaf advertise-default {
            type empty;
            description
              "Advertise default and suppress more specific routes";
          }
          leaf damping {
            type empty;
            description
              "Enable route flap damping";
          }
          container graceful-restart {
            description
              "BGP graceful restart options";
            uses bgp-af-gr;
          }
          leaf local-ipv4-address {
            type jt:ipv4addr;
            description
              "Local IPv4 address";
          }
          container nexthop-resolution {
            description
              "Configure nexthop resolution properties";
            uses apply-advanced;
            leaf no-resolution {
              type empty;
              description
                "Consider nexthop good without resolution attempt";
            }
          }
          container output-queue-priority {
            description
              "Default output-queue to assign updates to";
            uses bgp-output-queue-priority-class;
          }
          container route-refresh-priority {
            description
              "Default output-queue to assign route refreshes to";
            uses bgp-output-queue-priority-class;
          }
          container withdraw-priority {
            description
              "Default output-queue to assign withdrawn routes to";
            uses bgp-output-queue-priority-class;
          }
          leaf-list export {
            type jt:policy-algebra;
            ordered-by user;
            description
              "Export policy";
          }
          leaf-list import {
            type jt:policy-algebra;
            ordered-by user;
            description
              "Import policy";
          }
        }
        container inet-bgpmcast {
          description
            "IPv4 BGPMCAST NLRI parameters";
          uses apply-advanced;
          container signaling {
            presence "enable signaling";
            description
              "Include IPv4 BGP multicast signaling NLRI";
            uses bgp-afi-default;
          }
        }
        container inet6-bgpmcast {
          description
            "IPv6 BGPMCAST NLRI parameters";
          uses apply-advanced;
          container signaling {
            presence "enable signaling";
            description
              "Include IPv6 BGP multicast signaling NLRI";
            uses bgp-afi-default;
          }
        }
      }
      leaf authentication-key {
        type string {
          length "1 .. 126";
        }
        description
          "MD5 authentication key";
      }
      leaf authentication-algorithm {
        type enumeration {
          enum "md5" {
            description
              "Message Digest 5";
          }
          enum "hmac-sha-1-96" {
            description
              "Hash-based Message Authentication Code (SHA1) (96 bits)";
          }
          enum "aes-128-cmac-96" {
            description
              "Cipher-based Message Authentication Code (AES128) (96 bits)";
          }
          enum "ao" {
            description
              "TCP Authentication Option";
          }
        }
        description
          "Authentication algorithm name";
      }
      leaf tcpao-auth-mismatch {
        type enumeration {
          enum "allow-without-tcpao" {
            description
              "Allow the connection establishment without TCP-AO";
          }
        }
        description
          "Continue without TCP-AO if any one TCP endpoint does not have TCP-AO configured";
      }
      leaf authentication-key-chain {
        type string {
          length "1 .. 128";
        }
        description
          "Key chain name";
      }
      leaf-list export {
        type jt:policy-algebra;
        ordered-by user;
        description
          "Export policy";
      }
      container remove-private {
        presence "enable remove-private";
        description
          "Remove well-known private AS numbers";
        uses apply-advanced;
        container all {
          presence "enable all";
          description
            "Remove all private AS numbers and do not stop at the first public AS number";
          container replace {
            presence "enable replace";
            description
              "Replace private AS numbers with the BGP Group's local AS number";
            leaf nearest {
              type empty;
              description
                "Use closest public AS number to replace a private AS number";
            }
          }
        }
        leaf no-peer-loop-check {
          type empty;
          description
            "Remove peer loop-check";
        }
      }
      leaf cluster {
        type jt:areaid;
        description
          "Cluster identifier";
      }
      leaf no-client-reflect {
        type empty;
        description
          "Disable intracluster route redistribution";
      }
      leaf peer-as {
        type string;
        description
          " Autonomous system number in plain number or 'higher 16bits'.'Lower 16 bits' (asdot notation) format";
      }
      container local-as {
        description
          "Local autonomous system number";
        leaf as-number {
          type string;
          description
            " Autonomous system number in plain number or 'higher 16bits'.'Lower 16 bits' (asdot notation) format";
        }
        leaf loops {
          type union {
            type string {
              pattern "<.*>|$.*";
            }
            type int32 {
              range "1 .. 10";
            }
          }
          description
            "Maximum number of times this AS can be in an AS path";
        }
        leaf private {
          type empty;
          description
            "Hide this local AS in paths learned from this peering";
        }
        leaf alias {
          type empty;
          description
            "Treat this AS as an alias to the system AS";
        }
        leaf no-prepend-global-as {
          type empty;
          description
            "Do not prepend global autonomous-system number in advertised paths";
        }
      }
      leaf ipsec-sa {
        type string {
          length "1 .. 32";
        }
        description
          "IPSec SA name";
      }
      container graceful-shutdown {
        description
          "BGP peer graceful shutdown option";
        uses apply-advanced;
        container receiver {
          presence "enable receiver";
          description
            "BGP peer graceful-shutdown receiver";
          uses apply-advanced;
          leaf disable {
            type empty;
            description
              "Disable graceful-shutdown receiver";
          }
          leaf local-preference {
            type union {
              type uint32;
              type string {
                pattern "<.*>|$.*";
              }
            }
            description
              "Value of receiver LOCAL_PREF path attribute";
          }
        }
        container sender {
          presence "enable sender";
          description
            "BGP peer graceful-shutdown sender";
          uses apply-advanced;
          leaf local-preference {
            type union {
              type uint32;
              type string {
                pattern "<.*>|$.*";
              }
            }
            description
              "Value of sender LOCAL_PREF path attribute";
          }
        }
      }
      container shutdown {
        presence "enable shutdown";
        description
          "Shutdown";
        uses apply-advanced;
        leaf notify-message {
          type string;
          description
            "Notification message";
        }
      }
      leaf unconfigured-peer-graceful-restart {
        type empty;
        description
          "BGP unconfigured peer graceful restart options";
      }
      container graceful-restart {
        presence "enable graceful-restart";
        description
          "BGP graceful restart options";
        uses apply-advanced;
        choice enable-disable {
          case case_1 {
            leaf disable {
              type empty;
              description
                "Disable graceful restart";
            }
          }
        }
        leaf restart-time {
          type union {
            type string {
              pattern "<.*>|$.*";
            }
            type uint32 {
              range "1 .. 1800";
            }
          }
          description
            "Restart time used when negotiating with a peer";
        }
        leaf stale-routes-time {
          type union {
            type string {
              pattern "<.*>|$.*";
            }
            type uint32 {
              range "1 .. 1800";
            }
          }
          description
            "Maximum time for which stale routes are kept";
        }
        container long-lived {
          description
            "Long-lived graceful restart options";
          uses apply-advanced;
          container receiver {
            description
              "Long-lived graceful restart receiver (helper) options";
            uses apply-advanced;
            choice enable-disable {
              case case_1 {
                leaf disable {
                  type empty;
                  description
                    "Disable receiver (helper) functionality";
                }
              }
            }
          }
          container advertise-to-non-llgr-neighbor {
            presence "enable advertise-to-non-llgr-neighbor";
            description
              "Advertise stale routes to non-LLGR neighbors";
            uses apply-advanced;
            leaf omit-no-export {
              type empty;
              description
                "Do not attach no-export community to stale routes";
            }
          }
        }
        leaf disable-notification-extensions {
          type empty;
          description
            "Disable notification extensions";
        }
        leaf forwarding-state-bit {
          type enumeration {
            enum "as-rr-client" {
              description
                "As for a route reflector client";
            }
            enum "from-fib" {
              description
                "Always use state of associated FIB(s)";
            }
          }
          description
            "Control forwarding-state flag negotiation";
        }
        leaf dont-help-shared-fate-bfd-down {
          type empty;
          description
            "Honor BFD-Down(C=0) if GR-restart not in progress";
        }
      }
      leaf include-mp-next-hop {
        type empty;
        description
          "Include NEXT-HOP attribute in multiprotocol updates";
      }
      leaf disable-4byte-as {
        type empty;
        description
          "Disable 4 byte AS capability advertisement";
      }
      container idle-after-switch-over {
        description
          "Stop peer session from coming up after nonstop-routing switch-over";
        choice idle-interval {
          case case_1 {
            leaf forever {
              type empty;
              description
                "Idle the peer until the user intervenes";
            }
          }
          case case_2 {
            leaf timeout {
              type union {
                type string {
                  pattern "<.*>|$.*";
                }
                type uint32 {
                  range "1 .. 4294967295";
                }
              }
              description
                "Timeout value, in seconds, for starting peer after switch over";
            }
          }
        }
      }
      container outbound-route-filter {
        description
          "Dynamically negotiated cooperative route filtering";
        uses apply-advanced;
        leaf bgp-orf-cisco-mode {
          type empty;
          description
            "Using BGP ORF capability code 130 and Prefix ORF type 128";
        }
        container extended-community {
          status deprecated;
          description
            "Extended community filtering";
          uses apply-advanced;
          choice accept-choice {
            leaf accept {
              type empty;
              description
                "Honor remote requests for extended community ORF";
            }
            leaf no-accept {
              type empty;
              description
                "Don't honor remote requests for extended community ORF";
            }
          }
          leaf vrf-filter {
            type empty;
            description
              "Request remote filtering using locally configured VRF import targets";
          }
        }
        container prefix-based {
          presence "enable prefix-based";
          description
            "Prefix-based outbound route filtering";
          uses apply-advanced;
          container accept {
            presence "enable accept";
            description
              "Honor Prefix-based ORFs from remote peers";
            uses apply-advanced;
            leaf inet {
              type empty;
              description
                "Honor IPv4 prefix filters";
            }
            leaf inet6 {
              type empty;
              description
                "Honor IPv6 prefix filters";
            }
          }
        }
      }
      container message-batching {
        status deprecated;
        description
          "DEPRECATED - Batching of outgoing messages";
        uses apply-advanced;
        choice enable-disable {
          case case_1 {
            leaf enable {
              type empty;
              description
                "Enable parameter";
            }
          }
          case case_2 {
            leaf disable {
              type empty;
              description
                "Disable parameter";
            }
          }
        }
        leaf interval {
          type union {
            type string {
              pattern "<.*>|$.*";
            }
            type uint32 {
              range "100 .. 1000";
            }
          }
          units "milliseconds";
          default "250";
          description
            "DEPRECATED - Interval over which to batch messages";
        }
      }
      container multipath {
        presence "enable multipath";
        description
          "Allow load sharing among multiple BGP paths";
        uses apply-advanced;
        leaf disable {
          type empty;
          description
            "Disable Multipath";
        }
        leaf multiple-as {
          type empty;
          description
            "Use paths received from different ASs";
        }
        leaf allow-protection {
          type empty;
          description
            "Allow protection for multipath legs";
        }
        leaf pause-computation-during-churn {
          type empty;
          description
            "Pause multipath job to absorb churn";
        }
        leaf list-nexthop {
          type empty;
          description
            "Use List-NH for homogenous nexthop-set also";
        }
        container allow-external-internal {
          presence "enable allow-external-internal";
          description
            "Allow multipath to mix EBGP and IBGP routes";
          uses apply-advanced;
          leaf-list prefix-policy {
            type jt:policy-algebra;
            ordered-by user;
            description
              "Policy to constrain prefixes that apply";
          }
        }
      }
      leaf tcp-mss {
        type union {
          type string {
            pattern "<.*>|$.*";
          }
          type uint32 {
            range "1 .. 4096";
          }
        }
        description
          "Maximum TCP segment size";
      }
      leaf bgp-identifier {
        type jt:ipv4addr;
        description
          "BGP Identifier";
      }
      leaf tcp-aggressive-transmission {
        type empty;
        description
          "Enable aggressive transmission of pure TCP ACKs and retransmissions";
      }
      container bmp {
        description
          "Specific settings to override the routing-options settings";
        uses apply-advanced;
        leaf monitor {
          type enumeration {
            enum "enable" {
              description
                "Enable monitoring of BGP peer(s)";
            }
            enum "disable" {
              description
                "Disable monitoring of BGP peer(s)";
            }
          }
          description
            "Enable/Disable monitoring";
        }
        container route-monitoring {
          description
            "Control route monitoring settings";
          uses apply-advanced;
          leaf none {
            type empty;
            description
              "Do not send route monitoring messages";
          }
          container pre-policy {
            presence "enable pre-policy";
            description
              "Send pre-policy route monitoring messages";
            leaf exclude-non-feasible {
              type empty;
              description
                "Exclude looped routes, etc";
            }
          }
          container post-policy {
            presence "enable post-policy";
            description
              "Send post-policy route monitoring messages";
            leaf exclude-non-eligible {
              type empty;
              description
                "Exclude unresolved routes, etc.";
            }
          }
          container rib-out {
            presence "enable rib-out";
            description
              "Send adj-ribs-out route monitoring messages";
            leaf pre-policy {
              type empty;
              description
                "Send pre-policy adj-ribs-out route monitoring messages";
            }
            leaf post-policy {
              type empty;
              description
                "Send post-policy adj-ribs-out route monitoring messages";
            }
          }
        }
      }
      container advertise-bgp-static {
        presence "enable advertise-bgp-static";
        description
          "Advertise bgp-static routes";
        uses apply-advanced;
        leaf-list policy {
          type jt:policy-algebra;
          ordered-by user;
          description
            "Static route advertisement policy";
        }
      }
      leaf add-path-display-ipv4-address {
        type empty;
        description
          "Display add-path path-id in IPv4 address format";
      }
      container domain-path-id {
        description
          "Domain path id attribute";
        uses apply-advanced;
        leaf send {
          type empty;
          description
            "Allow sending domain path id attribute";
        }
        leaf receive {
          type empty;
          description
            "Allow receiving domain path id attribute";
        }
      }
      container bfd-liveness-detection {
        description
          "Bidirectional Forwarding Detection (BFD) options";
        uses apply-advanced;
        leaf version {
          type enumeration {
            enum "0" {
              description
                "BFD version 0 (deprecated)";
            }
            enum "1" {
              description
                "BFD version 1";
            }
            enum "automatic" {
              description
                "Choose BFD version automatically";
            }
          }
          default "automatic";
          description
            "BFD protocol version number";
        }
        leaf minimum-interval {
          type union {
            type string {
              pattern "<.*>|$.*";
            }
            type uint32 {
              range "1 .. 255000";
            }
          }
          units "milliseconds";
          description
            "Minimum transmit and receive interval";
        }
        leaf minimum-transmit-interval {
          type union {
            type string {
              pattern "<.*>|$.*";
            }
            type uint32 {
              range "1 .. 255000";
            }
          }
          units "milliseconds";
          status deprecated;
          description
            "Minimum transmit interval";
        }
        leaf minimum-receive-interval {
          type union {
            type string {
              pattern "<.*>|$.*";
            }
            type uint32 {
              range "1 .. 255000";
            }
          }
          units "milliseconds";
          description
            "Minimum receive interval";
        }
        leaf multiplier {
          type union {
            type string {
              pattern "<.*>|$.*";
            }
            type uint32 {
              range "1 .. 255";
            }
          }
          default "3";
          description
            "Detection time multiplier";
        }
        leaf inline-disable {
          type empty;
          description
            "Disable inline mode for this BFD session";
        }
        leaf pdu-size {
          type union {
            type string {
              pattern "<.*>|$.*";
            }
            type uint32 {
              range "24 .. 16000";
            }
          }
          default "24";
          description
            "BFD transport protocol payload size";
        }
        choice adaptation-choice {
          case case_1 {
            leaf no-adaptation {
              type empty;
              description
                "Disable adaptation";
            }
          }
        }
        container transmit-interval {
          description
            "Transmit-interval options";
          uses apply-advanced;
          leaf minimum-interval {
            type union {
              type string {
                pattern "<.*>|$.*";
              }
              type uint32 {
                range "1 .. 255000";
              }
            }
            units "milliseconds";
            description
              "Minimum transmit interval";
          }
          leaf threshold {
            type union {
              type uint32;
              type string {
                pattern "<.*>|$.*";
              }
            }
            units "milliseconds";
            description
              "High transmit interval triggering a trap";
          }
        }
        container detection-time {
          description
            "Detection-time options";
          uses apply-advanced;
          leaf threshold {
            type union {
              type uint32;
              type string {
                pattern "<.*>|$.*";
              }
            }
            units "milliseconds";
            description
              "High detection-time triggering a trap";
          }
        }
        container authentication {
          description
            "Authentication options";
          uses apply-advanced;
          leaf key-chain {
            type string;
            description
              "Key chain name";
          }
          leaf algorithm {
            type enumeration {
              enum "simple-password" {
                description
                  "Simple password";
              }
              enum "keyed-md5" {
                description
                  "Keyed message Digest 5";
              }
              enum "meticulous-keyed-md5" {
                description
                  "Meticulous keyed message Digest 5";
              }
              enum "keyed-sha-1" {
                description
                  "Keyed secure hash algorithm (SHA1) ";
              }
              enum "meticulous-keyed-sha-1" {
                description
                  "Meticulous keyed secure hash algorithm (SHA1) ";
              }
            }
            description
              "Algorithm name";
          }
          leaf loose-check {
            type empty;
            description
              "Verify authentication only if authentication is negotiated";
          }
        }
        leaf session-mode {
          type enumeration {
            enum "automatic" {
              description
                "Choose session-mode automatically";
            }
            enum "single-hop" {
              description
                "Use single-hop";
            }
            enum "multihop" {
              description
                "Use multihop";
            }
          }
          default "automatic";
          description
            "BFD single-hop or multihop session-mode";
        }
        container echo {
          description
            "Echo mode parameters";
          uses apply-advanced;
          leaf minimum-interval {
            type union {
              type string {
                pattern "<.*>|$.*";
              }
              type uint32 {
                range "100 .. 255000";
              }
            }
            units "milliseconds";
            description
              "Minimum transmit and receive interval";
          }
        }
        container echo-lite {
          description
            "Echo-lite more parameters";
          uses apply-advanced;
          leaf minimum-interval {
            type union {
              type string {
                pattern "<.*>|$.*";
              }
              type uint32 {
                range "100 .. 255000";
              }
            }
            units "milliseconds";
            description
              "Minimum transmit and receive interval";
          }
        }
        container strict-bfd {
          presence "enable strict-bfd";
          description
            "Bgp session waits for bfd";
          uses apply-advanced;
          leaf bfd-up-wait-interval {
            type union {
              type string {
                pattern "<.*>|$.*";
              }
              type uint32 {
                range "10 .. 255";
              }
            }
            units "seconds";
            description
              "Time to wait for bfd to come up";
          }
        }
        leaf holddown-interval {
          type union {
            type string {
              pattern "<.*>|$.*";
            }
            type uint32 {
              range "0 .. 255000";
            }
          }
          units "milliseconds";
          description
            "Time to hold the session-UP notification to the client";
        }
      }
      leaf as-override {
        type empty;
        description
          "Replace neighbor AS number with our AS number";
      }
      container link-bandwidth {
        description
          "Configure link-bandwidth options";
        uses apply-advanced;
        container auto-sense {
          presence "enable auto-sense";
          uses apply-advanced;
          leaf hold-down {
            type union {
              type string {
                pattern "<.*>|$.*";
              }
              type uint32 {
                range "0 .. 3600";
              }
            }
            description
              "Hold down in secs for link bandwidth auto-sense";
          }
        }
      }
      leaf-list allow {
        type jt:ipprefix;
        ordered-by user;
        description
          "Configure peer connections for specific networks";
      }
      list dynamic-neighbor {
        key "name";
        ordered-by user;
        description
          "Configure peer options for specific networks";
        leaf name {
          type string;
          description
            "Template name";
        }
        uses apply-advanced;
        leaf-list allow {
          type jt:ipprefix;
          ordered-by user;
          description
            "Configure peer connections for specific networks";
        }
        leaf peer-limit {
          type union {
            type string {
              pattern "<.*>|$.*";
            }
            type uint32 {
              range "0 .. 2048";
            }
          }
          description
            "Limit the number of peers for each subnet configured via dynamic-neighbor";
        }
        leaf authentication-key {
          type string {
            length "1 .. 126";
          }
          description
            "MD5 authentication key";
        }
        leaf authentication-algorithm {
          type enumeration {
            enum "md5" {
              description
                "Message Digest 5";
            }
            enum "hmac-sha-1-96" {
              description
                "Hash-based Message Authentication Code (SHA1) (96 bits)";
            }
            enum "aes-128-cmac-96" {
              description
                "Cipher-based Message Authentication Code (AES128) (96 bits)";
            }
            enum "ao" {
              description
                "TCP Authentication Option";
            }
          }
          description
            "Authentication algorithm name";
        }
        leaf tcpao-auth-mismatch {
          type enumeration {
            enum "allow-without-tcpao" {
              description
                "Allow the connection establishment without TCP-AO";
            }
          }
          description
            "Continue without TCP-AO if any one TCP endpoint does not have TCP-AO configured";
        }
        leaf authentication-key-chain {
          type string {
            length "1 .. 128";
          }
          description
            "Key chain name";
        }
        container peer-auto-discovery {
          description
            "Configure auto-discovery options for BGP neighbors";
          uses apply-advanced;
          container family {
            description
              "Address family based neighbor auto-discovery parameters";
            container inet6 {
              uses apply-advanced;
              choice auto-discovery-type {
                case case_1 {
                  container ipv6-nd {
                    presence "enable ipv6-nd";
                    description
                      "Use ipv6 neighbor discovery to learn neighbor address";
                  }
                }
              }
            }
          }
          list interface {
            key "name";
            leaf name {
              type union {
                type jt:interface-name;
                type string {
                  pattern "<.*>|$.*";
                }
              }
              description
                "Configure interfaces over which to discover bgp neighbors";
            }
            uses apply-advanced;
            choice enable-disable {
              case case_1 {
                leaf disable {
                  type empty;
                  description
                    "Disable peer discovery on interface";
                }
              }
            }
          }
        }
      }
      container optimal-route-reflection {
        description
          "Enable optimal route reflection for this client group";
        uses apply-advanced;
        leaf igp-primary {
          type jt:ipv4addr;
          description
            "Primary node identifier for this client group";
        }
        leaf igp-backup {
          type jt:ipv4addr;
          description
            "Backup node identifier for this client group";
        }
        leaf-list export {
          type jt:policy-algebra;
          description
            "Optimal route reflection export policy";
        }
      }
      leaf peer-as-list {
        type string;
        description
          "Configure list of peer autonomous systems for unconfigured neighbors";
      }
      leaf send-non-transitive-link-bandwidth {
        type empty;
        description
          "Allow sending non transitive link-bandwidth to EBGP peers";
      }
      leaf mvpn-iana-rt-import {
        type empty;
        status deprecated;
        description
          "Use IANA assigned rt-import type value for MVPN";
      }
      list neighbor {
        key "name";
        ordered-by user;
        description
          "Configure a neighbor";
        leaf name {
          type jt:ipaddr-scoped;
        }
        uses apply-advanced;
        container traceoptions {
          description
            "Trace options for BGP";
          uses apply-advanced;
          container file {
            description
              "Trace file options";
            leaf filename {
              type string {
                length "1 .. 1024";
              }
              description
                "Name of file in which to write trace information";
            }
            leaf replace {
              type empty;
              status deprecated;
              description
                "Replace trace file rather than appending to it";
            }
            leaf size {
              type string;
              description
                "Maximum trace file size";
            }
            leaf files {
              type union {
                type string {
                  pattern "<.*>|$.*";
                }
                type uint32 {
                  range "2 .. 1000";
                }
              }
              default "10";
              description
                "Maximum number of trace files";
            }
            leaf no-stamp {
              type empty;
              status deprecated;
              description
                "Do not timestamp trace file";
            }
            choice world-readable-choice {
              leaf world-readable {
                type empty;
                description
                  "Allow any user to read the log file";
              }
              leaf no-world-readable {
                type empty;
                description
                  "Don't allow any user to read the log file";
              }
            }
          }
          list flag {
            key "name";
            ordered-by user;
            description
              "Tracing parameters";
            leaf name {
              type enumeration {
                enum "damping" {
                  description
                    "Trace BGP damping information";
                }
                enum "packets" {
                  description
                    "Trace all BGP protocol packets";
                }
                enum "open" {
                  description
                    "Trace BGP open packets";
                }
                enum "update" {
                  description
                    "Trace BGP update packets";
                }
                enum "keepalive" {
                  description
                    "Trace BGP keepalive packets";
                }
                enum "refresh" {
                  description
                    "Trace BGP refresh packets";
                }
                enum "nsr-synchronization" {
                  description
                    "Trace NSR synchronization events";
                }
                enum "bfd" {
                  description
                    "Trace BFD events";
                }
                enum "4byte-as" {
                  description
                    "Trace 4 byte AS events";
                }
                enum "add-path" {
                  description
                    "Trace add-path events";
                }
                enum "graceful-restart" {
                  description
                    "Trace Graceful Restart events";
                }
                enum "egress-te" {
                  description
                    "Egress Peering Traffic-Engineering events";
                }
                enum "thread-io" {
                  description
                    "Trace threaded I/O processing";
                }
                enum "sharding" {
                  description
                    "Trace BGP rib sharding";
                }
                enum "glb" {
                  description
                    "Trace BGP global-load-balancing";
                }
                enum "thread-update-io" {
                  description
                    "Trace threaded update I/O processing";
                }
                enum "route-validation" {
                  description
                    "Trace route validation";
                }
                enum "ipsec" {
                  description
                    "Trace ipsec";
                }
                enum "route" {
                  description
                    "Trace routing information";
                }
                enum "normal" {
                  description
                    "Trace normal events";
                }
                enum "general" {
                  description
                    "Trace general events";
                }
                enum "state" {
                  description
                    "Trace state transitions";
                }
                enum "policy" {
                  description
                    "Trace policy processing";
                }
                enum "task" {
                  description
                    "Trace routing protocol task processing";
                }
                enum "timer" {
                  description
                    "Trace routing protocol timer processing";
                }
                enum "all" {
                  description
                    "Trace everything";
                }
              }
            }
            leaf send {
              type empty;
              description
                "Trace transmitted packets";
            }
            leaf receive {
              type empty;
              description
                "Trace received packets";
            }
            leaf detail {
              type empty;
              description
                "Trace detailed information";
            }
            leaf disable {
              type empty;
              description
                "Disable this trace flag";
            }
            container filter {
              presence "enable filter";
              description
                "Filter to apply to this flag";
              uses bgp_filter_obj;
            }
          }
        }
        leaf description {
          type string {
            length "1 .. 255";
          }
          description
            "Text description";
        }
        container metric-out {
          description
            "Route metric sent in MED";
          choice metric_param {
            case case_1 {
              leaf metric-value {
                type union {
                  type string {
                    pattern "<.*>|$.*";
                  }
                  type uint32 {
                    range "0 .. 4294967295";
                  }
                }
                description
                  "Metric value";
              }
            }
            case case_2 {
              container minimum-igp {
                presence "enable minimum-igp";
                description
                  "Track the minimum IGP metric";
                leaf metric-offset {
                  type union {
                    type int32;
                    type string {
                      pattern "<.*>|$.*";
                    }
                  }
                  description
                    "Metric offset for MED";
                }
              }
            }
            case case_3 {
              container igp {
                presence "enable igp";
                description
                  "Track the IGP metric";
                leaf metric-offset {
                  type union {
                    type int32;
                    type string {
                      pattern "<.*>|$.*";
                    }
                  }
                  description
                    "Metric offset for MED";
                }
                leaf delay-med-update {
                  type empty;
                  description
                    "Delay updating MED when IGP metric increases";
                }
              }
            }
            case case_4 {
              container effective-aigp {
                presence "enable effective-aigp";
                description
                  "Track the effective AIGP metric";
                leaf metric-offset {
                  type union {
                    type int32;
                    type string {
                      pattern "<.*>|$.*";
                    }
                  }
                  description
                    "Metric offset for MED";
                }
              }
            }
            case case_5 {
              container minimum-effective-aigp {
                presence "enable minimum-effective-aigp";
                description
                  "Track the minimum effective AIGP metric";
                leaf metric-offset {
                  type union {
                    type int32;
                    type string {
                      pattern "<.*>|$.*";
                    }
                  }
                  description
                    "Metric offset for MED";
                }
              }
            }
          }
        }
        container multihop {
          presence "enable multihop";
          description
            "Configure an EBGP multihop session";
          uses apply-advanced;
          leaf ttl {
            type union {
              type string {
                pattern "<.*>|$.*";
              }
              type uint8 {
                range "1 .. 255";
              }
            }
            description
              "TTL value for the session";
          }
          leaf no-nexthop-change {
            type empty;
            description
              "Do not change next hop to self in advertisements";
          }
        }
        container ebgp-community-cleanup {
          presence "enable ebgp-community-cleanup";
          description
            "Community specific cleanup for eBGP peers";
          uses apply-advanced;
          leaf origin-validation {
            type enumeration {
              enum "accept" {
                description
                  "Accept Origin Validation State Community";
              }
              enum "reject" {
                description
                  "Reject Origin Validation State Community";
              }
            }
            description
              "Origin Validation State receive behavior";
          }
        }
        leaf route-server-client {
          type empty;
          description
            "Enable route server client behavior";
        }
        leaf accept-remote-nexthop {
          type empty;
          description
            "Allow import policy to specify a non-directly connected next-hop";
        }
        leaf preference {
          type union {
            type uint32;
            type string {
              pattern "<.*>|$.*";
            }
          }
          description
            "Preference value";
        }
        leaf local-preference {
          type union {
            type uint32;
            type string {
              pattern "<.*>|$.*";
            }
          }
          description
            "Value of LOCAL_PREF path attribute";
        }
        leaf local-address {
          type jt:ipaddr;
          description
            "Address of local end of BGP session";
        }
        leaf local-interface {
          type union {
            type jt:interface-name;
            type string {
              pattern "<.*>|$.*";
            }
          }
          description
            "Local interface for IPv6 link local EBGP peering";
        }
        leaf forwarding-context {
          type string;
          description
            "Routing-instance used for data-forwarding and transport-session";
        }
        leaf hold-time {
          type union {
            type string {
              pattern "<.*>|$.*";
            }
            type uint32 {
              range "0 .. 65535";
            }
          }
          description
            "Hold time used when negotiating with a peer";
        }
        leaf minimum-hold-time {
          type union {
            type string {
              pattern "<.*>|$.*";
            }
            type uint32 {
              range "3 .. 65535";
            }
          }
          description
            "Minimum hold time accepted from the peer";
        }
        leaf passive {
          type empty;
          description
            "Do not send open messages to a peer";
        }
        leaf advertise-inactive {
          type empty;
          description
            "Advertise inactive routes";
        }
        choice advertise-peer-as-choice {
          leaf advertise-peer-as {
            type empty;
            description
              "Advertise routes received from the same autonomous system";
          }
          leaf no-advertise-peer-as {
            type empty;
            description
              "Don't advertise routes received from the same autonomous system";
          }
        }
        container advertise-external {
          presence "enable advertise-external";
          description
            "Advertise best external routes";
          leaf conditional {
            type empty;
            description
              "Route matches active route upto med-comparison rule";
          }
        }
        leaf keep {
          type enumeration {
            enum "all" {
              description
                "Retain all routes";
            }
            enum "none" {
              description
                "Retain no routes";
            }
          }
          description
            "How to retain routes in the routing table";
        }
        leaf rfc6514-compliant-safi129 {
          type empty;
          description
            "Compliant with RFC6514 SAFI129 format";
        }
        leaf no-aggregator-id {
          type empty;
          description
            "Set router ID in aggregator path attribute to 0";
        }
        leaf mtu-discovery {
          type empty;
          description
            "Enable TCP path MTU discovery";
        }
        leaf enforce-first-as {
          type empty;
          description
            "Enforce first AS in AS-path is the neighbor's AS";
        }
        leaf out-delay {
          type union {
            type string {
              pattern "<.*>|$.*";
            }
            type uint32 {
              range "0 .. 65535";
            }
          }
          description
            "How long before exporting routes from routing table";
        }
        leaf ttl {
          type enumeration {
            enum "1";
            enum "255";
          }
          description
            "TTL value for the single-hop peer";
        }
        leaf log-updown {
          type empty;
          description
            "Log a message for peer state transitions";
        }
        leaf damping {
          type empty;
          description
            "Enable route flap damping";
        }
        leaf-list import {
          type jt:policy-algebra;
          ordered-by user;
          description
            "Import policy";
        }
        leaf-list nlri {
          type enumeration {
            enum "unicast" {
              status deprecated;
              description
                "Include unicast NLRI";
            }
            enum "multicast" {
              status deprecated;
              description
                "Include multicast NLRI";
            }
            enum "any" {
              status deprecated;
              description
                "Include any kind of NLRI";
            }
          }
          ordered-by user;
          status deprecated;
          description
            "NLRI type to include in updates";
        }
        container bgp-error-tolerance {
          presence "enable bgp-error-tolerance";
          description
            "Handle BGP malformed updates softly, enabled by default. Configure logging parameters";
          uses apply-advanced;
          leaf malformed-update-log-interval {
            type union {
              type string {
                pattern "<.*>|$.*";
              }
              type uint32 {
                range "10 .. 65535";
              }
            }
            units "seconds";
            default "300";
            description
              "Time used when logging malformed update";
          }
          choice malformed-routes-limit-choice {
            case case_1 {
              leaf malformed-route-limit {
                type union {
                  type string {
                    pattern "<.*>|$.*";
                  }
                  type uint32 {
                    range "0 .. 4294967295";
                  }
                }
                default "1000";
                description
                  "Maximum number of malformed routes from a peer";
              }
            }
            case case_2 {
              leaf no-malformed-route-limit {
                type empty;
                description
                  "No malformed route limit";
              }
            }
          }
        }
        container family {
          description
            "Protocol family for NLRIs in updates";
          uses apply-advanced;
          container inet {
            description
              "IPv4 NLRI parameters";
            uses apply-advanced;
            container labeled-unicast {
              presence "enable labeled-unicast";
              description
                "Include labeled unicast NLRI";
              uses bgp-afi-labeled;
            }
            container segment-routing-te {
              presence "enable segment-routing-te";
              description
                "Include segment-routing TE policy";
              uses bgp-afi-srte;
            }
            container transport {
              presence "enable transport";
              description
                "Include Classful Transport NLRI";
              uses bgp-afi-inet-transport;
            }
            container unicast {
              presence "enable unicast";
              description
                "Include unicast NLRI";
              uses bgp-afi-topo;
            }
            container multicast {
              presence "enable multicast";
              description
                "Include multicast NLRI";
              uses bgp-afi-default;
            }
            container flow {
              presence "enable flow";
              description
                "Include flow NLRI";
              uses bgp-afi-flow-with-redirect-ip-action;
            }
            container any {
              presence "enable any";
              description
                "Include unicast or multicast NLRI";
              uses bgp-afi-default;
            }
          }
          container inet-vpn {
            description
              "IPv4 Layer 3 VPN NLRI parameters";
            uses apply-advanced;
            container unicast {
              presence "enable unicast";
              description
                "Include unicast NLRI";
              uses bgp-afi-l3vpn;
            }
            container multicast {
              presence "enable multicast";
              description
                "Include multicast NLRI";
              uses bgp-afi-vpn;
            }
            container flow {
              presence "enable flow";
              description
                "Include flow VPN NLRI";
              uses bgp-afi-flow-with-redirect-ip-action;
            }
            container any {
              presence "enable any";
              description
                "Include unicast or multicast NLRI";
              uses bgp-afi-vpn;
            }
          }
          container inet6 {
            description
              "IPv6 NLRI parameters";
            uses apply-advanced;
            container labeled-unicast {
              presence "enable labeled-unicast";
              description
                "Include labeled unicast NLRI";
              uses bgp-afi-inet6-labeled;
            }
            container segment-routing-te {
              presence "enable segment-routing-te";
              description
                "Include segment-routing TE policy";
              uses bgp-afi-srte;
            }
            container transport {
              presence "enable transport";
              description
                "Include Classful Transport NLRI";
              uses bgp-afi-inet6-transport;
            }
            container unicast {
              presence "enable unicast";
              description
                "Include unicast NLRI";
              uses bgp-afi-topo;
            }
            container multicast {
              presence "enable multicast";
              description
                "Include multicast NLRI";
              uses bgp-afi-default;
            }
            container flow {
              presence "enable flow";
              description
                "Include flow NLRI";
              uses bgp-afi-flow;
            }
            container any {
              presence "enable any";
              description
                "Include unicast or multicast NLRI";
              uses bgp-afi-default;
            }
          }
          container inet6-vpn {
            description
              "IPv6 Layer 3 VPN NLRI parameters";
            uses apply-advanced;
            container unicast {
              presence "enable unicast";
              description
                "Include unicast NLRI";
              uses bgp-afi-l3vpn;
            }
            container multicast {
              presence "enable multicast";
              description
                "Include multicast NLRI";
              uses bgp-afi-vpn;
            }
            container flow {
              presence "enable flow";
              description
                "Include flow VPN NLRI";
              uses bgp-afi-flow;
            }
            container any {
              presence "enable any";
              description
                "Include unicast or multicast NLRI";
              uses bgp-afi-vpn;
            }
          }
          container iso-vpn {
            description
              "ISO Layer 3 VPN NLRI parameters";
            uses apply-advanced;
            container unicast {
              presence "enable unicast";
              description
                "Include unicast NLRI";
              uses bgp-afi-vpn-protection;
            }
          }
          container l2vpn {
            description
              "MPLS-based Layer 2 VPN and VPLS NLRI parameters";
            uses apply-advanced;
            container auto-discovery-only {
              presence "enable auto-discovery-only";
              description
                "Include auto-discovery NLRI for LDP Layer 2 VPN and VPLS";
              uses bgp-afi-default;
            }
            container auto-discovery-mspw {
              presence "enable auto-discovery-mspw";
              description
                "Include auto-discovery NLRI for LDP Signalled MultiSegment PW";
              uses bgp-afi-default;
            }
            container signaling {
              presence "enable signaling";
              description
                "Include Layer 2 VPN and VPLS signaling NLRI";
              uses bgp-afi-l2vpn;
            }
          }
          container evpn {
            description
              "EVPN NLRI parameters";
            uses apply-advanced;
            container signaling {
              presence "enable signaling";
              description
                "Include EVPN signaling NLRI";
              uses bgp-afi-default;
            }
          }
          container inet-mvpn {
            description
              "IPv4 MVPN NLRI parameters";
            uses apply-advanced;
            container signaling {
              presence "enable signaling";
              description
                "Include IPv4 multicast VPN signaling NLRI";
              uses bgp-afi-default;
            }
          }
          container inet6-mvpn {
            description
              "IPv6 MVPN NLRI parameters";
            uses apply-advanced;
            container signaling {
              presence "enable signaling";
              description
                "Include IPv6 multicast VPN signaling NLRI";
              uses bgp-afi-default;
            }
          }
          container inet-mdt {
            description
              "IPv4 Multicast Distribution Tree (MDT) NLRI parameters";
            uses apply-advanced;
            container signaling {
              presence "enable signaling";
              description
                "Include IPv4 multicast VPN auto-discovery NLRI";
              uses bgp-afi-default;
            }
          }
          container traffic-engineering {
            description
              "Traffic Engineering (BGP-TE) NLRI parameters";
            uses apply-advanced;
            container unicast {
              presence "enable unicast";
              description
                "Include BGP-TE NLRI";
              uses bgp-afi-default;
            }
          }
          container route-target {
            presence "enable route-target";
            description
              "Route target NLRI used for VPN route filtering";
            uses apply-advanced;
            container prefix-limit {
              description
                "Limit maximum number of prefixes from a peer";
              uses bgpaf-prefix-limit;
            }
            container accepted-prefix-limit {
              description
                "Limit maximum number of prefixes accepted from a peer";
              uses bgpaf-accepted-prefix-limit;
            }
            container proxy-generate {
              presence "enable proxy-generate";
              description
                "Generate route target NLRI for peers that don't support it";
              uses apply-advanced;
              leaf-list route-target-policy {
                type jt:policy-algebra;
                ordered-by user;
                description
                  "Limit VPN routes that are used to generate proxy route-target filters";
              }
            }
            leaf external-paths {
              type union {
                type string {
                  pattern "<.*>|$.*";
                }
                type uint32 {
                  range "1 .. 256";
                }
              }
              description
                "Number of external paths accepted for route filtering";
            }
            leaf advertise-default {
              type empty;
              description
                "Advertise default and suppress more specific routes";
            }
            leaf damping {
              type empty;
              description
                "Enable route flap damping";
            }
            container graceful-restart {
              description
                "BGP graceful restart options";
              uses bgp-af-gr;
            }
            leaf local-ipv4-address {
              type jt:ipv4addr;
              description
                "Local IPv4 address";
            }
            container nexthop-resolution {
              description
                "Configure nexthop resolution properties";
              uses apply-advanced;
              leaf no-resolution {
                type empty;
                description
                  "Consider nexthop good without resolution attempt";
              }
            }
            container output-queue-priority {
              description
                "Default output-queue to assign updates to";
              uses bgp-output-queue-priority-class;
            }
            container route-refresh-priority {
              description
                "Default output-queue to assign route refreshes to";
              uses bgp-output-queue-priority-class;
            }
            container withdraw-priority {
              description
                "Default output-queue to assign withdrawn routes to";
              uses bgp-output-queue-priority-class;
            }
            leaf-list export {
              type jt:policy-algebra;
              ordered-by user;
              description
                "Export policy";
            }
            leaf-list import {
              type jt:policy-algebra;
              ordered-by user;
              description
                "Import policy";
            }
          }
          container inet-bgpmcast {
            description
              "IPv4 BGPMCAST NLRI parameters";
            uses apply-advanced;
            container signaling {
              presence "enable signaling";
              description
                "Include IPv4 BGP multicast signaling NLRI";
              uses bgp-afi-default;
            }
          }
          container inet6-bgpmcast {
            description
              "IPv6 BGPMCAST NLRI parameters";
            uses apply-advanced;
            container signaling {
              presence "enable signaling";
              description
                "Include IPv6 BGP multicast signaling NLRI";
              uses bgp-afi-default;
            }
          }
        }
        leaf authentication-key {
          type string {
            length "1 .. 126";
          }
          description
            "MD5 authentication key";
        }
        leaf authentication-algorithm {
          type enumeration {
            enum "md5" {
              description
                "Message Digest 5";
            }
            enum "hmac-sha-1-96" {
              description
                "Hash-based Message Authentication Code (SHA1) (96 bits)";
            }
            enum "aes-128-cmac-96" {
              description
                "Cipher-based Message Authentication Code (AES128) (96 bits)";
            }
            enum "ao" {
              description
                "TCP Authentication Option";
            }
          }
          description
            "Authentication algorithm name";
        }
        leaf tcpao-auth-mismatch {
          type enumeration {
            enum "allow-without-tcpao" {
              description
                "Allow the connection establishment without TCP-AO";
            }
          }
          description
            "Continue without TCP-AO if any one TCP endpoint does not have TCP-AO configured";
        }
        leaf authentication-key-chain {
          type string {
            length "1 .. 128";
          }
          description
            "Key chain name";
        }
        leaf-list export {
          type jt:policy-algebra;
          ordered-by user;
          description
            "Export policy";
        }
        container remove-private {
          presence "enable remove-private";
          description
            "Remove well-known private AS numbers";
          uses apply-advanced;
          container all {
            presence "enable all";
            description
              "Remove all private AS numbers and do not stop at the first public AS number";
            container replace {
              presence "enable replace";
              description
                "Replace private AS numbers with the BGP Group's local AS number";
              leaf nearest {
                type empty;
                description
                  "Use closest public AS number to replace a private AS number";
              }
            }
          }
          leaf no-peer-loop-check {
            type empty;
            description
              "Remove peer loop-check";
          }
        }
        leaf cluster {
          type jt:areaid;
          description
            "Cluster identifier";
        }
        leaf no-client-reflect {
          type empty;
          description
            "Disable intracluster route redistribution";
        }
        leaf peer-as {
          type string;
          description
            " Autonomous system number in plain number or 'higher 16bits'.'Lower 16 bits' (asdot notation) format";
        }
        container local-as {
          description
            "Local autonomous system number";
          leaf as-number {
            type string;
            description
              " Autonomous system number in plain number or 'higher 16bits'.'Lower 16 bits' (asdot notation) format";
          }
          leaf loops {
            type union {
              type string {
                pattern "<.*>|$.*";
              }
              type int32 {
                range "1 .. 10";
              }
            }
            description
              "Maximum number of times this AS can be in an AS path";
          }
          leaf private {
            type empty;
            description
              "Hide this local AS in paths learned from this peering";
          }
          leaf alias {
            type empty;
            description
              "Treat this AS as an alias to the system AS";
          }
          leaf no-prepend-global-as {
            type empty;
            description
              "Do not prepend global autonomous-system number in advertised paths";
          }
        }
        leaf ipsec-sa {
          type string {
            length "1 .. 32";
          }
          description
            "IPSec SA name";
        }
        container graceful-shutdown {
          description
            "BGP peer graceful shutdown option";
          uses apply-advanced;
          container receiver {
            presence "enable receiver";
            description
              "BGP peer graceful-shutdown receiver";
            uses apply-advanced;
            leaf disable {
              type empty;
              description
                "Disable graceful-shutdown receiver";
            }
            leaf local-preference {
              type union {
                type uint32;
                type string {
                  pattern "<.*>|$.*";
                }
              }
              description
                "Value of receiver LOCAL_PREF path attribute";
            }
          }
          container sender {
            presence "enable sender";
            description
              "BGP peer graceful-shutdown sender";
            uses apply-advanced;
            leaf local-preference {
              type union {
                type uint32;
                type string {
                  pattern "<.*>|$.*";
                }
              }
              description
                "Value of sender LOCAL_PREF path attribute";
            }
          }
        }
        container shutdown {
          presence "enable shutdown";
          description
            "Shutdown";
          uses apply-advanced;
          leaf notify-message {
            type string;
            description
              "Notification message";
          }
        }
        leaf unconfigured-peer-graceful-restart {
          type empty;
          description
            "BGP unconfigured peer graceful restart options";
        }
        container graceful-restart {
          presence "enable graceful-restart";
          description
            "BGP graceful restart options";
          uses apply-advanced;
          choice enable-disable {
            case case_1 {
              leaf disable {
                type empty;
                description
                  "Disable graceful restart";
              }
            }
          }
          leaf restart-time {
            type union {
              type string {
                pattern "<.*>|$.*";
              }
              type uint32 {
                range "1 .. 1800";
              }
            }
            description
              "Restart time used when negotiating with a peer";
          }
          leaf stale-routes-time {
            type union {
              type string {
                pattern "<.*>|$.*";
              }
              type uint32 {
                range "1 .. 1800";
              }
            }
            description
              "Maximum time for which stale routes are kept";
          }
          container long-lived {
            description
              "Long-lived graceful restart options";
            uses apply-advanced;
            container receiver {
              description
                "Long-lived graceful restart receiver (helper) options";
              uses apply-advanced;
              choice enable-disable {
                case case_1 {
                  leaf disable {
                    type empty;
                    description
                      "Disable receiver (helper) functionality";
                  }
                }
              }
            }
            container advertise-to-non-llgr-neighbor {
              presence "enable advertise-to-non-llgr-neighbor";
              description
                "Advertise stale routes to non-LLGR neighbors";
              uses apply-advanced;
              leaf omit-no-export {
                type empty;
                description
                  "Do not attach no-export community to stale routes";
              }
            }
          }
          leaf disable-notification-extensions {
            type empty;
            description
              "Disable notification extensions";
          }
          leaf forwarding-state-bit {
            type enumeration {
              enum "as-rr-client" {
                description
                  "As for a route reflector client";
              }
              enum "from-fib" {
                description
                  "Always use state of associated FIB(s)";
              }
            }
            description
              "Control forwarding-state flag negotiation";
          }
          leaf dont-help-shared-fate-bfd-down {
            type empty;
            description
              "Honor BFD-Down(C=0) if GR-restart not in progress";
          }
        }
        leaf include-mp-next-hop {
          type empty;
          description
            "Include NEXT-HOP attribute in multiprotocol updates";
        }
        leaf disable-4byte-as {
          type empty;
          description
            "Disable 4 byte AS capability advertisement";
        }
        container idle-after-switch-over {
          description
            "Stop peer session from coming up after nonstop-routing switch-over";
          choice idle-interval {
            case case_1 {
              leaf forever {
                type empty;
                description
                  "Idle the peer until the user intervenes";
              }
            }
            case case_2 {
              leaf timeout {
                type union {
                  type string {
                    pattern "<.*>|$.*";
                  }
                  type uint32 {
                    range "1 .. 4294967295";
                  }
                }
                description
                  "Timeout value, in seconds, for starting peer after switch over";
              }
            }
          }
        }
        container outbound-route-filter {
          description
            "Dynamically negotiated cooperative route filtering";
          uses apply-advanced;
          leaf bgp-orf-cisco-mode {
            type empty;
            description
              "Using BGP ORF capability code 130 and Prefix ORF type 128";
          }
          container extended-community {
            status deprecated;
            description
              "Extended community filtering";
            uses apply-advanced;
            choice accept-choice {
              leaf accept {
                type empty;
                description
                  "Honor remote requests for extended community ORF";
              }
              leaf no-accept {
                type empty;
                description
                  "Don't honor remote requests for extended community ORF";
              }
            }
            leaf vrf-filter {
              type empty;
              description
                "Request remote filtering using locally configured VRF import targets";
            }
          }
          container prefix-based {
            presence "enable prefix-based";
            description
              "Prefix-based outbound route filtering";
            uses apply-advanced;
            container accept {
              presence "enable accept";
              description
                "Honor Prefix-based ORFs from remote peers";
              uses apply-advanced;
              leaf inet {
                type empty;
                description
                  "Honor IPv4 prefix filters";
              }
              leaf inet6 {
                type empty;
                description
                  "Honor IPv6 prefix filters";
              }
            }
          }
        }
        container message-batching {
          status deprecated;
          description
            "DEPRECATED - Batching of outgoing messages";
          uses apply-advanced;
          choice enable-disable {
            case case_1 {
              leaf enable {
                type empty;
                description
                  "Enable parameter";
              }
            }
            case case_2 {
              leaf disable {
                type empty;
                description
                  "Disable parameter";
              }
            }
          }
          leaf interval {
            type union {
              type string {
                pattern "<.*>|$.*";
              }
              type uint32 {
                range "100 .. 1000";
              }
            }
            units "milliseconds";
            default "250";
            description
              "DEPRECATED - Interval over which to batch messages";
          }
        }
        container multipath {
          presence "enable multipath";
          description
            "Allow load sharing among multiple BGP paths";
          uses apply-advanced;
          leaf disable {
            type empty;
            description
              "Disable Multipath";
          }
          leaf multiple-as {
            type empty;
            description
              "Use paths received from different ASs";
          }
          leaf allow-protection {
            type empty;
            description
              "Allow protection for multipath legs";
          }
          leaf pause-computation-during-churn {
            type empty;
            description
              "Pause multipath job to absorb churn";
          }
          leaf list-nexthop {
            type empty;
            description
              "Use List-NH for homogenous nexthop-set also";
          }
          container allow-external-internal {
            presence "enable allow-external-internal";
            description
              "Allow multipath to mix EBGP and IBGP routes";
            uses apply-advanced;
            leaf-list prefix-policy {
              type jt:policy-algebra;
              ordered-by user;
              description
                "Policy to constrain prefixes that apply";
            }
          }
        }
        leaf tcp-mss {
          type union {
            type string {
              pattern "<.*>|$.*";
            }
            type uint32 {
              range "1 .. 4096";
            }
          }
          description
            "Maximum TCP segment size";
        }
        leaf bgp-identifier {
          type jt:ipv4addr;
          description
            "BGP Identifier";
        }
        leaf tcp-aggressive-transmission {
          type empty;
          description
            "Enable aggressive transmission of pure TCP ACKs and retransmissions";
        }
        container bmp {
          description
            "Specific settings to override the routing-options settings";
          uses apply-advanced;
          leaf monitor {
            type enumeration {
              enum "enable" {
                description
                  "Enable monitoring of BGP peer(s)";
              }
              enum "disable" {
                description
                  "Disable monitoring of BGP peer(s)";
              }
            }
            description
              "Enable/Disable monitoring";
          }
          container route-monitoring {
            description
              "Control route monitoring settings";
            uses apply-advanced;
            leaf none {
              type empty;
              description
                "Do not send route monitoring messages";
            }
            container pre-policy {
              presence "enable pre-policy";
              description
                "Send pre-policy route monitoring messages";
              leaf exclude-non-feasible {
                type empty;
                description
                  "Exclude looped routes, etc";
              }
            }
            container post-policy {
              presence "enable post-policy";
              description
                "Send post-policy route monitoring messages";
              leaf exclude-non-eligible {
                type empty;
                description
                  "Exclude unresolved routes, etc.";
              }
            }
            container rib-out {
              presence "enable rib-out";
              description
                "Send adj-ribs-out route monitoring messages";
              leaf pre-policy {
                type empty;
                description
                  "Send pre-policy adj-ribs-out route monitoring messages";
              }
              leaf post-policy {
                type empty;
                description
                  "Send post-policy adj-ribs-out route monitoring messages";
              }
            }
          }
        }
        container advertise-bgp-static {
          presence "enable advertise-bgp-static";
          description
            "Advertise bgp-static routes";
          uses apply-advanced;
          leaf-list policy {
            type jt:policy-algebra;
            ordered-by user;
            description
              "Static route advertisement policy";
          }
        }
        leaf add-path-display-ipv4-address {
          type empty;
          description
            "Display add-path path-id in IPv4 address format";
        }
        container domain-path-id {
          description
            "Domain path id attribute";
          uses apply-advanced;
          leaf send {
            type empty;
            description
              "Allow sending domain path id attribute";
          }
          leaf receive {
            type empty;
            description
              "Allow receiving domain path id attribute";
          }
        }
        container bfd-liveness-detection {
          description
            "Bidirectional Forwarding Detection (BFD) options";
          uses apply-advanced;
          leaf version {
            type enumeration {
              enum "0" {
                description
                  "BFD version 0 (deprecated)";
              }
              enum "1" {
                description
                  "BFD version 1";
              }
              enum "automatic" {
                description
                  "Choose BFD version automatically";
              }
            }
            default "automatic";
            description
              "BFD protocol version number";
          }
          leaf minimum-interval {
            type union {
              type string {
                pattern "<.*>|$.*";
              }
              type uint32 {
                range "1 .. 255000";
              }
            }
            units "milliseconds";
            description
              "Minimum transmit and receive interval";
          }
          leaf minimum-transmit-interval {
            type union {
              type string {
                pattern "<.*>|$.*";
              }
              type uint32 {
                range "1 .. 255000";
              }
            }
            units "milliseconds";
            status deprecated;
            description
              "Minimum transmit interval";
          }
          leaf minimum-receive-interval {
            type union {
              type string {
                pattern "<.*>|$.*";
              }
              type uint32 {
                range "1 .. 255000";
              }
            }
            units "milliseconds";
            description
              "Minimum receive interval";
          }
          leaf multiplier {
            type union {
              type string {
                pattern "<.*>|$.*";
              }
              type uint32 {
                range "1 .. 255";
              }
            }
            default "3";
            description
              "Detection time multiplier";
          }
          leaf inline-disable {
            type empty;
            description
              "Disable inline mode for this BFD session";
          }
          leaf pdu-size {
            type union {
              type string {
                pattern "<.*>|$.*";
              }
              type uint32 {
                range "24 .. 16000";
              }
            }
            default "24";
            description
              "BFD transport protocol payload size";
          }
          choice adaptation-choice {
            case case_1 {
              leaf no-adaptation {
                type empty;
                description
                  "Disable adaptation";
              }
            }
          }
          container transmit-interval {
            description
              "Transmit-interval options";
            uses apply-advanced;
            leaf minimum-interval {
              type union {
                type string {
                  pattern "<.*>|$.*";
                }
                type uint32 {
                  range "1 .. 255000";
                }
              }
              units "milliseconds";
              description
                "Minimum transmit interval";
            }
            leaf threshold {
              type union {
                type uint32;
                type string {
                  pattern "<.*>|$.*";
                }
              }
              units "milliseconds";
              description
                "High transmit interval triggering a trap";
            }
          }
          container detection-time {
            description
              "Detection-time options";
            uses apply-advanced;
            leaf threshold {
              type union {
                type uint32;
                type string {
                  pattern "<.*>|$.*";
                }
              }
              units "milliseconds";
              description
                "High detection-time triggering a trap";
            }
          }
          container authentication {
            description
              "Authentication options";
            uses apply-advanced;
            leaf key-chain {
              type string;
              description
                "Key chain name";
            }
            leaf algorithm {
              type enumeration {
                enum "simple-password" {
                  description
                    "Simple password";
                }
                enum "keyed-md5" {
                  description
                    "Keyed message Digest 5";
                }
                enum "meticulous-keyed-md5" {
                  description
                    "Meticulous keyed message Digest 5";
                }
                enum "keyed-sha-1" {
                  description
                    "Keyed secure hash algorithm (SHA1) ";
                }
                enum "meticulous-keyed-sha-1" {
                  description
                    "Meticulous keyed secure hash algorithm (SHA1) ";
                }
              }
              description
                "Algorithm name";
            }
            leaf loose-check {
              type empty;
              description
                "Verify authentication only if authentication is negotiated";
            }
          }
          leaf session-mode {
            type enumeration {
              enum "automatic" {
                description
                  "Choose session-mode automatically";
              }
              enum "single-hop" {
                description
                  "Use single-hop";
              }
              enum "multihop" {
                description
                  "Use multihop";
              }
            }
            default "automatic";
            description
              "BFD single-hop or multihop session-mode";
          }
          container echo {
            description
              "Echo mode parameters";
            uses apply-advanced;
            leaf minimum-interval {
              type union {
                type string {
                  pattern "<.*>|$.*";
                }
                type uint32 {
                  range "100 .. 255000";
                }
              }
              units "milliseconds";
              description
                "Minimum transmit and receive interval";
            }
          }
          container echo-lite {
            description
              "Echo-lite more parameters";
            uses apply-advanced;
            leaf minimum-interval {
              type union {
                type string {
                  pattern "<.*>|$.*";
                }
                type uint32 {
                  range "100 .. 255000";
                }
              }
              units "milliseconds";
              description
                "Minimum transmit and receive interval";
            }
          }
          container strict-bfd {
            presence "enable strict-bfd";
            description
              "Bgp session waits for bfd";
            uses apply-advanced;
            leaf bfd-up-wait-interval {
              type union {
                type string {
                  pattern "<.*>|$.*";
                }
                type uint32 {
                  range "10 .. 255";
                }
              }
              units "seconds";
              description
                "Time to wait for bfd to come up";
            }
          }
          leaf holddown-interval {
            type union {
              type string {
                pattern "<.*>|$.*";
              }
              type uint32 {
                range "0 .. 255000";
              }
            }
            units "milliseconds";
            description
              "Time to hold the session-UP notification to the client";
          }
        }
        leaf as-override {
          type empty;
          description
            "Replace neighbor AS number with our AS number";
        }
        container link-bandwidth {
          description
            "Configure link-bandwidth options";
          uses apply-advanced;
          container auto-sense {
            presence "enable auto-sense";
            uses apply-advanced;
            leaf hold-down {
              type union {
                type string {
                  pattern "<.*>|$.*";
                }
                type uint32 {
                  range "0 .. 3600";
                }
              }
              description
                "Hold down in secs for link bandwidth auto-sense";
            }
          }
        }
        leaf no-global-load-balancing {
          type empty;
          description
            "Disable glabl load balancing";
        }
        container egress-te-node-segment {
          description
            "Configure BGP-Peer-Node segment";
          uses apply-advanced;
          container label {
            description
              "BGP-Peer-Node SID label from static label pool";
            uses apply-advanced;
            leaf label-value {
              type union {
                type string {
                  pattern "<.*>|$.*";
                }
                type uint32 {
                  range "16 .. 1048575";
                }
              }
              description
                "BGP-Peer-Node SID label value from static label pool";
            }
          }
          container egress-te-set {
            description
              "Configure as a member of a SET segment";
            uses apply-advanced;
            leaf set-name {
              type string;
              description
                "Set name";
            }
            leaf weight {
              type union {
                type string {
                  pattern "<.*>|$.*";
                }
                type uint32 {
                  range "1 .. 255";
                }
              }
              description
                "Weight for set segment";
            }
          }
          container egress-te-backup-segment {
            description
              "Backup segment for FRR";
            uses apply-advanced;
            container label {
              description
                "Backup segment label from static label pool";
              uses apply-advanced;
              leaf label-value {
                type union {
                  type string {
                    pattern "<.*>|$.*";
                  }
                  type uint32 {
                    range "16 .. 1048575";
                  }
                }
                description
                  "Backup segment label value from static label pool";
              }
            }
          }
          container egress-te-backup-ip-forward {
            presence "enable egress-te-backup-ip-forward";
            description
              "Use IP-forward backup path for Egress TE";
            uses apply-advanced;
            leaf instance-name {
              type string;
              description
                "Routing-instance to use as IP forward backup-path";
            }
          }
        }
        list egress-te-adj-segment {
          key "name";
          description
            "Configure BGP-Peer-Adj segment";
          leaf name {
            type string;
            description
              "The BGP-Adj-Set segment name";
          }
          uses apply-advanced;
          container label {
            description
              "BGP-Peer-Adj SID label from static label pool";
            uses apply-advanced;
            leaf label-value {
              type union {
                type string {
                  pattern "<.*>|$.*";
                }
                type uint32 {
                  range "16 .. 1048575";
                }
              }
              description
                "BGP-Peer-Adj SID label value from static label pool";
            }
          }
          container next-hop {
            description
              "Address of directly connected next-hop to use";
            uses apply-advanced;
            leaf next-hop-addr {
              type jt:ipaddr;
              description
                "Address of directly connected next-hop";
            }
          }
          container egress-te-set {
            description
              "Configure as a member of a SET segment";
            uses apply-advanced;
            leaf set-name {
              type string;
              description
                "Set name";
            }
            leaf weight {
              type union {
                type string {
                  pattern "<.*>|$.*";
                }
                type uint32 {
                  range "1 .. 255";
                }
              }
              description
                "Weight for set segment";
            }
          }
          container egress-te-backup-segment {
            description
              "Backup segment for FRR";
            uses apply-advanced;
            container label {
              description
                "Backup segment label from static label pool";
              uses apply-advanced;
              leaf label-value {
                type union {
                  type string {
                    pattern "<.*>|$.*";
                  }
                  type uint32 {
                    range "16 .. 1048575";
                  }
                }
                description
                  "Backup segment label value from static label pool";
              }
            }
          }
          container egress-te-backup-ip-forward {
            presence "enable egress-te-backup-ip-forward";
            description
              "Use IP-forward backup path for Egress TE";
            uses apply-advanced;
            leaf instance-name {
              type string;
              description
                "Routing-instance to use as IP forward backup-path";
            }
          }
          container te-link-attribute {
            presence "enable te-link-attribute";
            description
              "Link attribute";
            uses apply-advanced;
            leaf te-metric {
              type union {
                type string {
                  pattern "<.*>|$.*";
                }
                type uint32 {
                  range "1 .. 4294967295";
                }
              }
              default "1";
              description
                "TE Metric value";
            }
            leaf igp-metric {
              type union {
                type string {
                  pattern "<.*>|$.*";
                }
                type uint32 {
                  range "1 .. 16777215";
                }
              }
              default "1";
              description
                "IGP Metric value";
            }
            leaf delay-metric {
              type union {
                type string {
                  pattern "<.*>|$.*";
                }
                type uint32 {
                  range "1 .. 16777215";
                }
              }
              units "microseconds";
              description
                "Delay Metric";
            }
            leaf-list admin-group {
              type string;
              max-elements 16;
              ordered-by user;
              description
                "Administrative groups";
            }
          }
        }
        leaf vpn-apply-export {
          type empty;
          description
            "Apply BGP export policy when exporting VPN routes";
        }
        container egress-te {
          presence "enable egress-te";
          description
            "Use Egress Peering traffic engineering";
          uses apply-advanced;
          leaf install-address {
            type jt:ipaddr;
            description
              "Address to use in egress-te created inet route";
          }
          container rib {
            description
              "Select primary table for Egress-TE routes";
            uses apply-advanced;
            leaf inet.0 {
              type empty;
              description
                "Install Egress-TE routes in inet.0";
            }
            leaf inet6.0 {
              type empty;
              description
                "Install Egress-TE routes in inet6.0";
            }
          }
          leaf no-install {
            type empty;
            description
              "Avoid installation to FIB or resolving over";
          }
          leaf-list import {
            type jt:policy-algebra;
            ordered-by user;
            description
              "Import policy to set attributes";
          }
          leaf backup-path {
            type string;
            description
              "The 'egress-te-backup-paths template' to use for this peer";
          }
        }
        leaf advertise-prefix-sid {
          type empty;
          description
            "Advertise prefix sid to E-BGP peers";
        }
        leaf accept-prefix-sid {
          type empty;
          description
            "Accept prefix sid from E-BGP peers";
        }
        leaf advertise-srgb {
          type empty;
          description
            "Advertise SRGB TLV";
        }
        leaf tcp-connect-port {
          type union {
            type string {
              pattern "<.*>|$.*";
            }
            type uint16 {
              range "1 .. 65535";
            }
          }
          description
            "TCP port number to connect with peer on";
        }
      }
      leaf vpn-apply-export {
        type empty;
        description
          "Apply BGP export policy when exporting VPN routes";
      }
      container egress-te {
        presence "enable egress-te";
        description
          "Use Egress Peering traffic engineering";
        uses apply-advanced;
        leaf install-address {
          type jt:ipaddr;
          description
            "Address to use in egress-te created inet route";
        }
        container rib {
          description
            "Select primary table for Egress-TE routes";
          uses apply-advanced;
          leaf inet.0 {
            type empty;
            description
              "Install Egress-TE routes in inet.0";
          }
          leaf inet6.0 {
            type empty;
            description
              "Install Egress-TE routes in inet6.0";
          }
        }
        leaf no-install {
          type empty;
          description
            "Avoid installation to FIB or resolving over";
        }
        leaf-list import {
          type jt:policy-algebra;
          ordered-by user;
          description
            "Import policy to set attributes";
        }
        leaf backup-path {
          type string;
          description
            "The 'egress-te-backup-paths template' to use for this peer";
        }
      }
      leaf advertise-prefix-sid {
        type empty;
        description
          "Advertise prefix sid to E-BGP peers";
      }
      leaf accept-prefix-sid {
        type empty;
        description
          "Accept prefix sid from E-BGP peers";
      }
      leaf advertise-srgb {
        type empty;
        description
          "Advertise SRGB TLV";
      }
      leaf tcp-connect-port {
        type union {
          type string {
            pattern "<.*>|$.*";
          }
          type uint16 {
            range "1 .. 65535";
          }
        }
        description
          "TCP port number to connect with peer on";
      }
      leaf no-global-load-balancing {
        type empty;
        description
          "Disable glabl load balancing";
      }
    }
    container traffic-statistics-labeled-path {
      presence "enable traffic-statistics-labeled-path";
      description
        "Collect periodic ingress labeled statistics for BGP label-switched paths ";
      uses apply-advanced;
      container file {
        description
          "Statistics file options";
        leaf filename {
          type string {
            length "1 .. 1024";
          }
          description
            "Name of file in which to write trace information";
        }
        leaf replace {
          type empty;
          status deprecated;
          description
            "Replace trace file rather than appending to it";
        }
        leaf size {
          type string;
          description
            "Maximum trace file size";
        }
        leaf files {
          type union {
            type string {
              pattern "<.*>|$.*";
            }
            type uint32 {
              range "2 .. 1000";
            }
          }
          default "10";
          description
            "Maximum number of trace files";
        }
        leaf no-stamp {
          type empty;
          status deprecated;
          description
            "Do not timestamp trace file";
        }
        choice world-readable-choice {
          leaf world-readable {
            type empty;
            description
              "Allow any user to read the log file";
          }
          leaf no-world-readable {
            type empty;
            description
              "Don't allow any user to read the log file";
          }
        }
      }
      leaf interval {
        type union {
          type string {
            pattern "<.*>|$.*";
          }
          type int32 {
            range "60 .. 65535";
          }
        }
        units "seconds";
        description
          "Time interval to collect statistics";
      }
    }
    container source-packet-routing {
      description
        "Enable Source Packet Routing (SPRING)";
      uses apply-advanced;
      container srgb {
        description
          "Set the SRGB global block in SPRING";
        leaf start-label {
          type union {
            type string {
              pattern "<.*>|$.*";
            }
            type uint32 {
              range "16 .. 1048575";
            }
          }
          description
            "Start range for SRGB label block";
        }
        leaf index-range {
          type union {
            type string {
              pattern "<.*>|$.*";
            }
            type uint32 {
              range "16 .. 1048575";
            }
          }
          description
            "Index to the SRGB start label block";
        }
      }
      container srv6 {
        description
          "Enable IPv6 Segment Routing (SRv6)";
        uses apply-advanced;
        list locator {
          key "name";
          ordered-by user;
          description
            "SRv6 Locator";
          leaf name {
            type string;
            description
              "Locator name";
          }
          uses apply-advanced;
          container end-dt4-sid {
            presence "enable end-dt4-sid";
            description
              "End dt4 sid with 128 bit address";
            uses apply-advanced;
            leaf sid {
              type jt:ipv6addr;
              description
                "Sid value";
            }
            leaf non-default {
              type empty;
              description
                "Non default sid for policy usage";
            }
          }
          container end-dt6-sid {
            presence "enable end-dt6-sid";
            description
              "End dt6 sid with 128 bit address";
            uses apply-advanced;
            leaf sid {
              type jt:ipv6addr;
              description
                "Sid value";
            }
            leaf non-default {
              type empty;
              description
                "Non default sid for policy usage";
            }
          }
          container end-dt46-sid {
            presence "enable end-dt46-sid";
            description
              "End dt46 sid with 128 bit address";
            uses apply-advanced;
            leaf sid {
              type jt:ipv6addr;
              description
                "Sid value";
            }
            leaf non-default {
              type empty;
              description
                "Non default sid for policy usage";
            }
          }
          container micro-dt4-sid {
            presence "enable micro-dt4-sid";
            description
              "Micro dt4 sid";
            uses apply-advanced;
            leaf micro-sid-value {
              type union {
                type uint32;
                type string {
                  pattern "<.*>|$.*";
                }
              }
              description
                "Static micro sid value 16-bit or 32-bit";
            }
            leaf non-default {
              type empty;
              description
                "Non default micro dt4 sid for policy usage";
            }
          }
          container micro-dt6-sid {
            presence "enable micro-dt6-sid";
            description
              "Micro dt6 sid";
            uses apply-advanced;
            leaf micro-sid-value {
              type union {
                type uint32;
                type string {
                  pattern "<.*>|$.*";
                }
              }
              description
                "Static micro sid value 16-bit or 32-bit";
            }
            leaf non-default {
              type empty;
              description
                "Non default micro dt6 sid for policy usage";
            }
          }
          container micro-dt46-sid {
            presence "enable micro-dt46-sid";
            description
              "Micro dt46 sid";
            uses apply-advanced;
            leaf micro-sid-value {
              type union {
                type uint32;
                type string {
                  pattern "<.*>|$.*";
                }
              }
              description
                "Static micro sid value 16-bit or 32-bit";
            }
            leaf non-default {
              type empty;
              description
                "Non default micro dt46 sid for policy usage";
            }
          }
        }
      }
    }
    choice enable-disable {
      case case_1 {
        leaf disable {
          type empty;
          description
            "Disable BGP";
        }
      }
    }
    leaf protocol-instance-name {
      type string;
      description
        "Name of protocol instance under routing instance";
    }
    choice precision-timers-choice {
      leaf precision-timers {
        type empty;
        description
          "Use precision timers for scheduling keepalives";
      }
      leaf no-precision-timers {
        type empty;
        description
          "Don't use precision timers for scheduling keepalives";
      }
    }
    container snmp-options {
      description
        "Customize SNMP behaviors specifically for BGP MIBs";
      uses apply-advanced;
      leaf backward-traps-only-from-established {
        type empty;
        description
          "Limit traps for backward transitions to only those moving from Established state.";
      }
      leaf emit-inet-address-length-in-oid {
        type empty;
        description
          "Emit Length in OID for InetAddress MIB type.";
      }
    }
    leaf route-age-bgp-view {
      type empty;
      description
        "Maintain BGP route's age based on Update messages only";
    }
    leaf prioritize-route-queueing {
      type empty;
      description
        "Let route-queue building happen without getting throttled";
    }
    container traceoptions {
      description
        "Trace options for BGP";
      uses apply-advanced;
      container file {
        description
          "Trace file options";
        leaf filename {
          type string {
            length "1 .. 1024";
          }
          description
            "Name of file in which to write trace information";
        }
        leaf replace {
          type empty;
          status deprecated;
          description
            "Replace trace file rather than appending to it";
        }
        leaf size {
          type string;
          description
            "Maximum trace file size";
        }
        leaf files {
          type union {
            type string {
              pattern "<.*>|$.*";
            }
            type uint32 {
              range "2 .. 1000";
            }
          }
          default "10";
          description
            "Maximum number of trace files";
        }
        leaf no-stamp {
          type empty;
          status deprecated;
          description
            "Do not timestamp trace file";
        }
        choice world-readable-choice {
          leaf world-readable {
            type empty;
            description
              "Allow any user to read the log file";
          }
          leaf no-world-readable {
            type empty;
            description
              "Don't allow any user to read the log file";
          }
        }
      }
      list flag {
        key "name";
        ordered-by user;
        description
          "Tracing parameters";
        leaf name {
          type enumeration {
            enum "damping" {
              description
                "Trace BGP damping information";
            }
            enum "packets" {
              description
                "Trace all BGP protocol packets";
            }
            enum "open" {
              description
                "Trace BGP open packets";
            }
            enum "update" {
              description
                "Trace BGP update packets";
            }
            enum "keepalive" {
              description
                "Trace BGP keepalive packets";
            }
            enum "refresh" {
              description
                "Trace BGP refresh packets";
            }
            enum "nsr-synchronization" {
              description
                "Trace NSR synchronization events";
            }
            enum "bfd" {
              description
                "Trace BFD events";
            }
            enum "4byte-as" {
              description
                "Trace 4 byte AS events";
            }
            enum "add-path" {
              description
                "Trace add-path events";
            }
            enum "graceful-restart" {
              description
                "Trace Graceful Restart events";
            }
            enum "egress-te" {
              description
                "Egress Peering Traffic-Engineering events";
            }
            enum "thread-io" {
              description
                "Trace threaded I/O processing";
            }
            enum "sharding" {
              description
                "Trace BGP rib sharding";
            }
            enum "glb" {
              description
                "Trace BGP global-load-balancing";
            }
            enum "thread-update-io" {
              description
                "Trace threaded update I/O processing";
            }
            enum "route-validation" {
              description
                "Trace route validation";
            }
            enum "ipsec" {
              description
                "Trace ipsec";
            }
            enum "route" {
              description
                "Trace routing information";
            }
            enum "normal" {
              description
                "Trace normal events";
            }
            enum "general" {
              description
                "Trace general events";
            }
            enum "state" {
              description
                "Trace state transitions";
            }
            enum "policy" {
              description
                "Trace policy processing";
            }
            enum "task" {
              description
                "Trace routing protocol task processing";
            }
            enum "timer" {
              description
                "Trace routing protocol timer processing";
            }
            enum "all" {
              description
                "Trace everything";
            }
          }
        }
        leaf send {
          type empty;
          description
            "Trace transmitted packets";
        }
        leaf receive {
          type empty;
          description
            "Trace received packets";
        }
        leaf detail {
          type empty;
          description
            "Trace detailed information";
        }
        leaf disable {
          type empty;
          description
            "Disable this trace flag";
        }
        container filter {
          presence "enable filter";
          description
            "Filter to apply to this flag";
          uses bgp_filter_obj;
        }
      }
    }
    leaf description {
      type string {
        length "1 .. 255";
      }
      description
        "Text description";
    }
    container metric-out {
      description
        "Route metric sent in MED";
      choice metric_param {
        case case_1 {
          leaf metric-value {
            type union {
              type string {
                pattern "<.*>|$.*";
              }
              type uint32 {
                range "0 .. 4294967295";
              }
            }
            description
              "Metric value";
          }
        }
        case case_2 {
          container minimum-igp {
            presence "enable minimum-igp";
            description
              "Track the minimum IGP metric";
            leaf metric-offset {
              type union {
                type int32;
                type string {
                  pattern "<.*>|$.*";
                }
              }
              description
                "Metric offset for MED";
            }
          }
        }
        case case_3 {
          container igp {
            presence "enable igp";
            description
              "Track the IGP metric";
            leaf metric-offset {
              type union {
                type int32;
                type string {
                  pattern "<.*>|$.*";
                }
              }
              description
                "Metric offset for MED";
            }
            leaf delay-med-update {
              type empty;
              description
                "Delay updating MED when IGP metric increases";
            }
          }
        }
        case case_4 {
          container effective-aigp {
            presence "enable effective-aigp";
            description
              "Track the effective AIGP metric";
            leaf metric-offset {
              type union {
                type int32;
                type string {
                  pattern "<.*>|$.*";
                }
              }
              description
                "Metric offset for MED";
            }
          }
        }
        case case_5 {
          container minimum-effective-aigp {
            presence "enable minimum-effective-aigp";
            description
              "Track the minimum effective AIGP metric";
            leaf metric-offset {
              type union {
                type int32;
                type string {
                  pattern "<.*>|$.*";
                }
              }
              description
                "Metric offset for MED";
            }
          }
        }
      }
    }
    container multihop {
      presence "enable multihop";
      description
        "Configure an EBGP multihop session";
      uses apply-advanced;
      leaf ttl {
        type union {
          type string {
            pattern "<.*>|$.*";
          }
          type uint8 {
            range "1 .. 255";
          }
        }
        description
          "TTL value for the session";
      }
      leaf no-nexthop-change {
        type empty;
        description
          "Do not change next hop to self in advertisements";
      }
    }
    container ebgp-community-cleanup {
      presence "enable ebgp-community-cleanup";
      description
        "Community specific cleanup for eBGP peers";
      uses apply-advanced;
      leaf origin-validation {
        type enumeration {
          enum "accept" {
            description
              "Accept Origin Validation State Community";
          }
          enum "reject" {
            description
              "Reject Origin Validation State Community";
          }
        }
        description
          "Origin Validation State receive behavior";
      }
    }
    leaf route-server-client {
      type empty;
      description
        "Enable route server client behavior";
    }
    leaf accept-remote-nexthop {
      type empty;
      description
        "Allow import policy to specify a non-directly connected next-hop";
    }
    leaf preference {
      type union {
        type uint32;
        type string {
          pattern "<.*>|$.*";
        }
      }
      description
        "Preference value";
    }
    leaf local-preference {
      type union {
        type uint32;
        type string {
          pattern "<.*>|$.*";
        }
      }
      description
        "Value of LOCAL_PREF path attribute";
    }
    leaf local-address {
      type jt:ipaddr;
      description
        "Address of local end of BGP session";
    }
    leaf local-interface {
      type union {
        type jt:interface-name;
        type string {
          pattern "<.*>|$.*";
        }
      }
      description
        "Local interface for IPv6 link local EBGP peering";
    }
    leaf forwarding-context {
      type string;
      description
        "Routing-instance used for data-forwarding and transport-session";
    }
    leaf hold-time {
      type union {
        type string {
          pattern "<.*>|$.*";
        }
        type uint32 {
          range "0 .. 65535";
        }
      }
      description
        "Hold time used when negotiating with a peer";
    }
    leaf minimum-hold-time {
      type union {
        type string {
          pattern "<.*>|$.*";
        }
        type uint32 {
          range "3 .. 65535";
        }
      }
      description
        "Minimum hold time accepted from the peer";
    }
    leaf passive {
      type empty;
      description
        "Do not send open messages to a peer";
    }
    leaf advertise-inactive {
      type empty;
      description
        "Advertise inactive routes";
    }
    choice advertise-peer-as-choice {
      leaf advertise-peer-as {
        type empty;
        description
          "Advertise routes received from the same autonomous system";
      }
      leaf no-advertise-peer-as {
        type empty;
        description
          "Don't advertise routes received from the same autonomous system";
      }
    }
    container advertise-external {
      presence "enable advertise-external";
      description
        "Advertise best external routes";
      leaf conditional {
        type empty;
        description
          "Route matches active route upto med-comparison rule";
      }
    }
    leaf keep {
      type enumeration {
        enum "all" {
          description
            "Retain all routes";
        }
        enum "none" {
          description
            "Retain no routes";
        }
      }
      description
        "How to retain routes in the routing table";
    }
    leaf rfc6514-compliant-safi129 {
      type empty;
      description
        "Compliant with RFC6514 SAFI129 format";
    }
    leaf no-aggregator-id {
      type empty;
      description
        "Set router ID in aggregator path attribute to 0";
    }
    leaf mtu-discovery {
      type empty;
      description
        "Enable TCP path MTU discovery";
    }
    leaf enforce-first-as {
      type empty;
      description
        "Enforce first AS in AS-path is the neighbor's AS";
    }
    leaf out-delay {
      type union {
        type string {
          pattern "<.*>|$.*";
        }
        type uint32 {
          range "0 .. 65535";
        }
      }
      description
        "How long before exporting routes from routing table";
    }
    leaf ttl {
      type enumeration {
        enum "1";
        enum "255";
      }
      description
        "TTL value for the single-hop peer";
    }
    leaf log-updown {
      type empty;
      description
        "Log a message for peer state transitions";
    }
    leaf damping {
      type empty;
      description
        "Enable route flap damping";
    }
    leaf-list import {
      type jt:policy-algebra;
      ordered-by user;
      description
        "Import policy";
    }
    leaf-list nlri {
      type enumeration {
        enum "unicast" {
          status deprecated;
          description
            "Include unicast NLRI";
        }
        enum "multicast" {
          status deprecated;
          description
            "Include multicast NLRI";
        }
        enum "any" {
          status deprecated;
          description
            "Include any kind of NLRI";
        }
      }
      ordered-by user;
      status deprecated;
      description
        "NLRI type to include in updates";
    }
    container bgp-error-tolerance {
      presence "enable bgp-error-tolerance";
      description
        "Handle BGP malformed updates softly, enabled by default. Configure logging parameters";
      uses apply-advanced;
      leaf malformed-update-log-interval {
        type union {
          type string {
            pattern "<.*>|$.*";
          }
          type uint32 {
            range "10 .. 65535";
          }
        }
        units "seconds";
        default "300";
        description
          "Time used when logging malformed update";
      }
      choice malformed-routes-limit-choice {
        case case_1 {
          leaf malformed-route-limit {
            type union {
              type string {
                pattern "<.*>|$.*";
              }
              type uint32 {
                range "0 .. 4294967295";
              }
            }
            default "1000";
            description
              "Maximum number of malformed routes from a peer";
          }
        }
        case case_2 {
          leaf no-malformed-route-limit {
            type empty;
            description
              "No malformed route limit";
          }
        }
      }
    }
    leaf authentication-key {
      type string {
        length "1 .. 126";
      }
      description
        "MD5 authentication key";
    }
    leaf authentication-algorithm {
      type enumeration {
        enum "md5" {
          description
            "Message Digest 5";
        }
        enum "hmac-sha-1-96" {
          description
            "Hash-based Message Authentication Code (SHA1) (96 bits)";
        }
        enum "aes-128-cmac-96" {
          description
            "Cipher-based Message Authentication Code (AES128) (96 bits)";
        }
        enum "ao" {
          description
            "TCP Authentication Option";
        }
      }
      default "hmac-sha-1-96";
      description
        "Authentication algorithm name";
    }
    leaf tcpao-auth-mismatch {
      type enumeration {
        enum "allow-without-tcpao" {
          description
            "Allow the connection establishment without TCP-AO";
        }
      }
      description
        "Continue without TCP-AO if any one TCP endpoint does not have TCP-AO configured";
    }
    leaf authentication-key-chain {
      type string {
        length "1 .. 128";
      }
      description
        "Key chain name";
    }
    leaf-list export {
      type jt:policy-algebra;
      ordered-by user;
      description
        "Export policy";
    }
    container remove-private {
      presence "enable remove-private";
      description
        "Remove well-known private AS numbers";
      uses apply-advanced;
      container all {
        presence "enable all";
        description
          "Remove all private AS numbers and do not stop at the first public AS number";
        container replace {
          presence "enable replace";
          description
            "Replace private AS numbers with the BGP Group's local AS number";
          leaf nearest {
            type empty;
            description
              "Use closest public AS number to replace a private AS number";
          }
        }
      }
      leaf no-peer-loop-check {
        type empty;
        description
          "Remove peer loop-check";
      }
    }
    leaf cluster {
      type jt:areaid;
      description
        "Cluster identifier";
    }
    leaf no-client-reflect {
      type empty;
      description
        "Disable intracluster route redistribution";
    }
    leaf peer-as {
      type string;
      description
        " Autonomous system number in plain number or 'higher 16bits'.'Lower 16 bits' (asdot notation) format";
    }
    container local-as {
      description
        "Local autonomous system number";
      leaf as-number {
        type string;
        description
          " Autonomous system number in plain number or 'higher 16bits'.'Lower 16 bits' (asdot notation) format";
      }
      leaf loops {
        type union {
          type string {
            pattern "<.*>|$.*";
          }
          type int32 {
            range "1 .. 10";
          }
        }
        description
          "Maximum number of times this AS can be in an AS path";
      }
      leaf private {
        type empty;
        description
          "Hide this local AS in paths learned from this peering";
      }
      leaf alias {
        type empty;
        description
          "Treat this AS as an alias to the system AS";
      }
      leaf no-prepend-global-as {
        type empty;
        description
          "Do not prepend global autonomous-system number in advertised paths";
      }
    }
    leaf ipsec-sa {
      type string {
        length "1 .. 32";
      }
      description
        "IPSec SA name";
    }
    container graceful-shutdown {
      description
        "BGP peer graceful shutdown option";
      uses apply-advanced;
      container receiver {
        presence "enable receiver";
        description
          "BGP peer graceful-shutdown receiver";
        uses apply-advanced;
        leaf disable {
          type empty;
          description
            "Disable graceful-shutdown receiver";
        }
        leaf local-preference {
          type union {
            type uint32;
            type string {
              pattern "<.*>|$.*";
            }
          }
          description
            "Value of receiver LOCAL_PREF path attribute";
        }
      }
      container sender {
        presence "enable sender";
        description
          "BGP peer graceful-shutdown sender";
        uses apply-advanced;
        leaf local-preference {
          type union {
            type uint32;
            type string {
              pattern "<.*>|$.*";
            }
          }
          description
            "Value of sender LOCAL_PREF path attribute";
        }
      }
    }
    container shutdown {
      presence "enable shutdown";
      description
        "Shutdown";
      uses apply-advanced;
      leaf notify-message {
        type string;
        description
          "Notification message";
      }
    }
    leaf unconfigured-peer-graceful-restart {
      type empty;
      description
        "BGP unconfigured peer graceful restart options";
    }
    container graceful-restart {
      presence "enable graceful-restart";
      description
        "BGP graceful restart options";
      uses apply-advanced;
      choice enable-disable {
        case case_1 {
          leaf disable {
            type empty;
            description
              "Disable graceful restart";
          }
        }
      }
      leaf restart-time {
        type union {
          type string {
            pattern "<.*>|$.*";
          }
          type uint32 {
            range "1 .. 1800";
          }
        }
        description
          "Restart time used when negotiating with a peer";
      }
      leaf stale-routes-time {
        type union {
          type string {
            pattern "<.*>|$.*";
          }
          type uint32 {
            range "1 .. 1800";
          }
        }
        description
          "Maximum time for which stale routes are kept";
      }
      container long-lived {
        description
          "Long-lived graceful restart options";
        uses apply-advanced;
        container receiver {
          description
            "Long-lived graceful restart receiver (helper) options";
          uses apply-advanced;
          choice enable-disable {
            case case_1 {
              leaf disable {
                type empty;
                description
                  "Disable receiver (helper) functionality";
              }
            }
          }
        }
        container advertise-to-non-llgr-neighbor {
          presence "enable advertise-to-non-llgr-neighbor";
          description
            "Advertise stale routes to non-LLGR neighbors";
          uses apply-advanced;
          leaf omit-no-export {
            type empty;
            description
              "Do not attach no-export community to stale routes";
          }
        }
      }
      leaf disable-notification-extensions {
        type empty;
        description
          "Disable notification extensions";
      }
      leaf forwarding-state-bit {
        type enumeration {
          enum "as-rr-client" {
            description
              "As for a route reflector client";
          }
          enum "from-fib" {
            description
              "Always use state of associated FIB(s)";
          }
        }
        description
          "Control forwarding-state flag negotiation";
      }
      leaf dont-help-shared-fate-bfd-down {
        type empty;
        description
          "Honor BFD-Down(C=0) if GR-restart not in progress";
      }
    }
    leaf include-mp-next-hop {
      type empty;
      description
        "Include NEXT-HOP attribute in multiprotocol updates";
    }
    leaf disable-4byte-as {
      type empty;
      description
        "Disable 4 byte AS capability advertisement";
    }
    container idle-after-switch-over {
      description
        "Stop peer session from coming up after nonstop-routing switch-over";
      choice idle-interval {
        case case_1 {
          leaf forever {
            type empty;
            description
              "Idle the peer until the user intervenes";
          }
        }
        case case_2 {
          leaf timeout {
            type union {
              type string {
                pattern "<.*>|$.*";
              }
              type uint32 {
                range "1 .. 4294967295";
              }
            }
            description
              "Timeout value, in seconds, for starting peer after switch over";
          }
        }
      }
    }
    container outbound-route-filter {
      description
        "Dynamically negotiated cooperative route filtering";
      uses apply-advanced;
      leaf bgp-orf-cisco-mode {
        type empty;
        description
          "Using BGP ORF capability code 130 and Prefix ORF type 128";
      }
      container extended-community {
        status deprecated;
        description
          "Extended community filtering";
        uses apply-advanced;
        choice accept-choice {
          leaf accept {
            type empty;
            description
              "Honor remote requests for extended community ORF";
          }
          leaf no-accept {
            type empty;
            description
              "Don't honor remote requests for extended community ORF";
          }
        }
        leaf vrf-filter {
          type empty;
          description
            "Request remote filtering using locally configured VRF import targets";
        }
      }
      container prefix-based {
        presence "enable prefix-based";
        description
          "Prefix-based outbound route filtering";
        uses apply-advanced;
        container accept {
          presence "enable accept";
          description
            "Honor Prefix-based ORFs from remote peers";
          uses apply-advanced;
          leaf inet {
            type empty;
            description
              "Honor IPv4 prefix filters";
          }
          leaf inet6 {
            type empty;
            description
              "Honor IPv6 prefix filters";
          }
        }
      }
    }
    container message-batching {
      status deprecated;
      description
        "DEPRECATED - Batching of outgoing messages";
      uses apply-advanced;
      choice enable-disable {
        case case_1 {
          leaf enable {
            type empty;
            description
              "Enable parameter";
          }
        }
        case case_2 {
          leaf disable {
            type empty;
            description
              "Disable parameter";
          }
        }
      }
      leaf interval {
        type union {
          type string {
            pattern "<.*>|$.*";
          }
          type uint32 {
            range "100 .. 1000";
          }
        }
        units "milliseconds";
        default "250";
        description
          "DEPRECATED - Interval over which to batch messages";
      }
    }
    container multipath {
      presence "enable multipath";
      description
        "Allow load sharing among multiple BGP paths";
      uses apply-advanced;
      leaf disable {
        type empty;
        description
          "Disable Multipath";
      }
      leaf multiple-as {
        type empty;
        description
          "Use paths received from different ASs";
      }
      leaf allow-protection {
        type empty;
        description
          "Allow protection for multipath legs";
      }
      leaf pause-computation-during-churn {
        type empty;
        description
          "Pause multipath job to absorb churn";
      }
      leaf list-nexthop {
        type empty;
        description
          "Use List-NH for homogenous nexthop-set also";
      }
      container allow-external-internal {
        presence "enable allow-external-internal";
        description
          "Allow multipath to mix EBGP and IBGP routes";
        uses apply-advanced;
        leaf-list prefix-policy {
          type jt:policy-algebra;
          ordered-by user;
          description
            "Policy to constrain prefixes that apply";
        }
      }
    }
    leaf tcp-mss {
      type union {
        type string {
          pattern "<.*>|$.*";
        }
        type uint32 {
          range "1 .. 4096";
        }
      }
      description
        "Maximum TCP segment size";
    }
    leaf bgp-identifier {
      type jt:ipv4addr;
      description
        "BGP Identifier";
    }
    leaf tcp-aggressive-transmission {
      type empty;
      description
        "Enable aggressive transmission of pure TCP ACKs and retransmissions";
    }
    container bmp {
      description
        "Specific settings to override the routing-options settings";
      uses apply-advanced;
      leaf monitor {
        type enumeration {
          enum "enable" {
            description
              "Enable monitoring of BGP peer(s)";
          }
          enum "disable" {
            description
              "Disable monitoring of BGP peer(s)";
          }
        }
        description
          "Enable/Disable monitoring";
      }
      container route-monitoring {
        description
          "Control route monitoring settings";
        uses apply-advanced;
        leaf none {
          type empty;
          description
            "Do not send route monitoring messages";
        }
        container pre-policy {
          presence "enable pre-policy";
          description
            "Send pre-policy route monitoring messages";
          leaf exclude-non-feasible {
            type empty;
            description
              "Exclude looped routes, etc";
          }
        }
        container post-policy {
          presence "enable post-policy";
          description
            "Send post-policy route monitoring messages";
          leaf exclude-non-eligible {
            type empty;
            description
              "Exclude unresolved routes, etc.";
          }
        }
        container rib-out {
          presence "enable rib-out";
          description
            "Send adj-ribs-out route monitoring messages";
          leaf pre-policy {
            type empty;
            description
              "Send pre-policy adj-ribs-out route monitoring messages";
          }
          leaf post-policy {
            type empty;
            description
              "Send post-policy adj-ribs-out route monitoring messages";
          }
        }
      }
    }
    container advertise-bgp-static {
      presence "enable advertise-bgp-static";
      description
        "Advertise bgp-static routes";
      uses apply-advanced;
      leaf-list policy {
        type jt:policy-algebra;
        ordered-by user;
        description
          "Static route advertisement policy";
      }
    }
    leaf add-path-display-ipv4-address {
      type empty;
      description
        "Display add-path path-id in IPv4 address format";
    }
    container domain-path-id {
      description
        "Domain path id attribute";
      uses apply-advanced;
      leaf send {
        type empty;
        description
          "Allow sending domain path id attribute";
      }
      leaf receive {
        type empty;
        description
          "Allow receiving domain path id attribute";
      }
    }
    container bfd-liveness-detection {
      description
        "Bidirectional Forwarding Detection (BFD) options";
      uses apply-advanced;
      leaf version {
        type enumeration {
          enum "0" {
            description
              "BFD version 0 (deprecated)";
          }
          enum "1" {
            description
              "BFD version 1";
          }
          enum "automatic" {
            description
              "Choose BFD version automatically";
          }
        }
        default "automatic";
        description
          "BFD protocol version number";
      }
      leaf minimum-interval {
        type union {
          type string {
            pattern "<.*>|$.*";
          }
          type uint32 {
            range "1 .. 255000";
          }
        }
        units "milliseconds";
        description
          "Minimum transmit and receive interval";
      }
      leaf minimum-transmit-interval {
        type union {
          type string {
            pattern "<.*>|$.*";
          }
          type uint32 {
            range "1 .. 255000";
          }
        }
        units "milliseconds";
        status deprecated;
        description
          "Minimum transmit interval";
      }
      leaf minimum-receive-interval {
        type union {
          type string {
            pattern "<.*>|$.*";
          }
          type uint32 {
            range "1 .. 255000";
          }
        }
        units "milliseconds";
        description
          "Minimum receive interval";
      }
      leaf multiplier {
        type union {
          type string {
            pattern "<.*>|$.*";
          }
          type uint32 {
            range "1 .. 255";
          }
        }
        default "3";
        description
          "Detection time multiplier";
      }
      leaf inline-disable {
        type empty;
        description
          "Disable inline mode for this BFD session";
      }
      leaf pdu-size {
        type union {
          type string {
            pattern "<.*>|$.*";
          }
          type uint32 {
            range "24 .. 16000";
          }
        }
        default "24";
        description
          "BFD transport protocol payload size";
      }
      choice adaptation-choice {
        case case_1 {
          leaf no-adaptation {
            type empty;
            description
              "Disable adaptation";
          }
        }
      }
      container transmit-interval {
        description
          "Transmit-interval options";
        uses apply-advanced;
        leaf minimum-interval {
          type union {
            type string {
              pattern "<.*>|$.*";
            }
            type uint32 {
              range "1 .. 255000";
            }
          }
          units "milliseconds";
          description
            "Minimum transmit interval";
        }
        leaf threshold {
          type union {
            type uint32;
            type string {
              pattern "<.*>|$.*";
            }
          }
          units "milliseconds";
          description
            "High transmit interval triggering a trap";
        }
      }
      container detection-time {
        description
          "Detection-time options";
        uses apply-advanced;
        leaf threshold {
          type union {
            type uint32;
            type string {
              pattern "<.*>|$.*";
            }
          }
          units "milliseconds";
          description
            "High detection-time triggering a trap";
        }
      }
      container authentication {
        description
          "Authentication options";
        uses apply-advanced;
        leaf key-chain {
          type string;
          description
            "Key chain name";
        }
        leaf algorithm {
          type enumeration {
            enum "simple-password" {
              description
                "Simple password";
            }
            enum "keyed-md5" {
              description
                "Keyed message Digest 5";
            }
            enum "meticulous-keyed-md5" {
              description
                "Meticulous keyed message Digest 5";
            }
            enum "keyed-sha-1" {
              description
                "Keyed secure hash algorithm (SHA1) ";
            }
            enum "meticulous-keyed-sha-1" {
              description
                "Meticulous keyed secure hash algorithm (SHA1) ";
            }
          }
          description
            "Algorithm name";
        }
        leaf loose-check {
          type empty;
          description
            "Verify authentication only if authentication is negotiated";
        }
      }
      leaf session-mode {
        type enumeration {
          enum "automatic" {
            description
              "Choose session-mode automatically";
          }
          enum "single-hop" {
            description
              "Use single-hop";
          }
          enum "multihop" {
            description
              "Use multihop";
          }
        }
        default "automatic";
        description
          "BFD single-hop or multihop session-mode";
      }
      container echo {
        description
          "Echo mode parameters";
        uses apply-advanced;
        leaf minimum-interval {
          type union {
            type string {
              pattern "<.*>|$.*";
            }
            type uint32 {
              range "100 .. 255000";
            }
          }
          units "milliseconds";
          description
            "Minimum transmit and receive interval";
        }
      }
      container echo-lite {
        description
          "Echo-lite more parameters";
        uses apply-advanced;
        leaf minimum-interval {
          type union {
            type string {
              pattern "<.*>|$.*";
            }
            type uint32 {
              range "100 .. 255000";
            }
          }
          units "milliseconds";
          description
            "Minimum transmit and receive interval";
        }
      }
      container strict-bfd {
        presence "enable strict-bfd";
        description
          "Bgp session waits for bfd";
        uses apply-advanced;
        leaf bfd-up-wait-interval {
          type union {
            type string {
              pattern "<.*>|$.*";
            }
            type uint32 {
              range "10 .. 255";
            }
          }
          units "seconds";
          description
            "Time to wait for bfd to come up";
        }
      }
      leaf holddown-interval {
        type union {
          type string {
            pattern "<.*>|$.*";
          }
          type uint32 {
            range "0 .. 255000";
          }
        }
        units "milliseconds";
        description
          "Time to hold the session-UP notification to the client";
      }
    }
    container output-queue-priority {
      description
        "BGP output queue priority scheduler for updates";
      uses apply-advanced;
      container expedited {
        presence "enable expedited";
        description
          "Expedited queue; highest priority";
        leaf update-tokens {
          type union {
            type string {
              pattern "<.*>|$.*";
            }
            type uint32 {
              range "1 .. 100";
            }
          }
          mandatory true;
          description
            "Number of tokens";
        }
      }
      list priority {
        key "name";
        description
          "Output queue priority 1..16; higher is better";
        leaf name {
          type union {
            type string {
              pattern "<.*>|$.*";
            }
            type uint32 {
              range "1 .. 16";
            }
          }
          description
            "Output queue priority; higher is better";
        }
        leaf update-tokens {
          type union {
            type string {
              pattern "<.*>|$.*";
            }
            type uint32 {
              range "1 .. 100";
            }
          }
          mandatory true;
          description
            "Number of tokens";
        }
      }
      container defaults {
        description
          "Map policy's priority class and BGP output-queue";
        uses apply-advanced;
        container low {
          description
            "Assign the 'low' priority class to this output-queue";
          uses bgp-output-queue-priority-class;
        }
        container medium {
          description
            "Assign the 'medium' priority class to this output-queue";
          uses bgp-output-queue-priority-class;
        }
        container high {
          description
            "Assign the 'high' priority class to this output-queue";
          uses bgp-output-queue-priority-class;
        }
      }
    }
    container multipath-build-priority {
      description
        "Configure the multipath build priority";
      uses apply-advanced;
      choice multipath-priority {
        case case_1 {
          leaf low {
            type empty;
            description
              "Do multipath build with low priority";
          }
        }
        case case_2 {
          leaf medium {
            type empty;
            description
              "Do multipath build with medium priority";
          }
        }
      }
    }
    leaf send-addpath-optimization {
      type empty;
      description
        "Enable BGP addpath advertisement optimization";
    }
    leaf rfc8950-compliant {
      type empty;
      description
        "Enable RFC8950 compliant";
    }
    container defaults {
      uses apply-advanced;
      container ebgp {
        description
          "Options impacting external BGP default behaviors";
        uses apply-advanced;
        container no-policy {
          description
            "Default ebgp behaviors in the absence of configured policy";
          uses apply-advanced;
          leaf receive {
            type enumeration {
              enum "accept" {
                description
                  "By default, accept routes from all address families";
              }
              enum "reject" {
                description
                  "By default, reject routes from IPv4/IPv6 unicast address families";
              }
              enum "reject-always" {
                description
                  "By default, reject routes from all address families";
              }
            }
            description
              "Default ebgp receive behavior";
          }
          leaf advertise {
            type enumeration {
              enum "accept" {
                description
                  "By default, advertise routes for all address families";
              }
              enum "reject" {
                description
                  "By default, do not advertise routes from IPv4/IPv6 unicast address families";
              }
              enum "reject-always" {
                description
                  "By default, do not advertise routes from any address families";
              }
            }
            description
              "Default ebgp advertise behavior";
          }
        }
      }
    }
  }

  grouping bgp-af-gr {
    uses apply-advanced;
    container long-lived {
      description
        "Long-lived graceful restart options";
      uses apply-advanced;
      container restarter {
        description
          "Long-lived graceful restart restarter options";
        uses apply-advanced;
        choice enable-disable {
          case case_1 {
            leaf disable {
              type empty;
              description
                "Disable restarter functionality";
            }
          }
        }
        leaf stale-time {
          type string;
          description
            "Stale time in seconds or dhms notation (1..16777215)";
        }
      }
      container extended-route-retention {
        description
          "Extended route retention (LLGR-helper extended) options";
        uses apply-advanced;
        choice enable-disable {
          case case_1 {
            leaf disable {
              type empty;
              description
                "Disable extended-route-retention (LLGR-helper) functionality";
            }
          }
        }
        leaf retention-time {
          type string;
          description
            "Retention time in seconds or dhms notation (1..16777215)";
        }
        leaf-list retention-policy {
          type jt:policy-algebra;
          ordered-by user;
          description
            "Retention policy for Extended Route Retention";
        }
      }
    }
    leaf forwarding-state-bit {
      type enumeration {
        enum "set" {
          description
            "Always set";
        }
        enum "from-fib" {
          description
            "Use state of associated FIB(s)";
        }
      }
      description
        "Control forwarding-state flag negotiation";
    }
  }

  grouping bgp-afi-default {
    uses apply-advanced;
    container prefix-limit {
      description
        "Limit maximum number of prefixes from a peer";
      uses bgpaf-prefix-limit;
    }
    container accepted-prefix-limit {
      description
        "Limit maximum number of prefixes accepted from a peer";
      uses bgpaf-accepted-prefix-limit;
    }
    container rib-group {
      description
        "Routing table group";
      uses rib_group_inet_type;
    }
    container add-path {
      description
        "Advertise multiple paths to peer";
      uses apath-options;
    }
    container aigp {
      presence "enable aigp";
      description
        "Allow sending and receiving of AIGP attribute";
      uses bgpaf-aigp-options;
    }
    leaf damping {
      type empty;
      description
        "Enable route flap damping";
    }
    leaf local-ipv4-address {
      type jt:ipv4addr;
      description
        "Local IPv4 address";
    }
    container loops {
      description
        "Allow local AS in received AS paths";
      uses bgpaf-loops;
    }
    container delay-route-advertisements {
      presence "enable delay-route-advertisements";
      description
        "Delay route updates for this family until FIB-sync";
      uses apply-advanced;
      leaf always-wait-for-krt-drain {
        type empty;
        description
          "Wait for KRT-queue drain for more-specific prefixes";
      }
      container minimum-delay {
        description
          "Minimum-delay to ensure KRT sees the route flash";
        uses apply-advanced;
        leaf routing-uptime {
          type union {
            type string {
              pattern "<.*>|$.*";
            }
            type uint32 {
              range "1 .. 36000";
            }
          }
          description
            "Min delay(sec) advertisement after RPD start";
        }
        leaf inbound-convergence {
          type union {
            type string {
              pattern "<.*>|$.*";
            }
            type uint32 {
              range "1 .. 36000";
            }
          }
          description
            "Min delay(sec) advertisement after source-peer sent all routes";
        }
      }
      container maximum-delay {
        description
          "Maximum delay deferring routes";
        uses apply-advanced;
        leaf route-age {
          type union {
            type string {
              pattern "<.*>|$.*";
            }
            type uint32 {
              range "1 .. 36000";
            }
          }
          description
            "Max delay(sec) advertisement route age";
        }
        leaf routing-uptime {
          type union {
            type string {
              pattern "<.*>|$.*";
            }
            type uint32 {
              range "1 .. 36000";
            }
          }
          description
            "Max delay(sec) advertisement after RPD start";
        }
      }
    }
    container nexthop-resolution {
      description
        "Configure nexthop resolution properties";
      uses apply-advanced;
      leaf no-resolution {
        type empty;
        description
          "Consider nexthop good without resolution attempt";
      }
      leaf preserve-nexthop-hierarchy {
        type empty;
        description
          "Attempt preserving resolved nexthop chain in forwarding";
      }
    }
    container defer-initial-multipath-build {
      presence "enable defer-initial-multipath-build";
      description
        "Defer initial multipath build until EOR is received";
      uses apply-advanced;
      leaf maximum-delay {
        type union {
          type string {
            pattern "<.*>|$.*";
          }
          type uint32 {
            range "1 .. 3600";
          }
        }
        description
          "Max delay(sec) multipath build after peer is up";
      }
    }
    container graceful-restart {
      description
        "BGP graceful restart options";
      uses bgp-af-gr;
    }
    leaf extended-nexthop {
      type empty;
      description
        "Extended nexthop encoding";
    }
    leaf extended-nexthop-color {
      type empty;
      description
        "Resolve using extended color nexthop";
    }
    leaf extended-nexthop-tunnel {
      type empty;
      description
        "Use BGP tunnel attribute";
    }
    leaf no-install {
      type empty;
      description
        "Dont install received routes in forwarding";
    }
    leaf route-age-bgp-view {
      type empty;
      description
        "Maintain BGP route's age based on Update messages only";
    }
    container output-queue-priority {
      description
        "Default output-queue to assign updates to";
      uses bgp-output-queue-priority-class;
    }
    container route-refresh-priority {
      description
        "Default output-queue to assign route refreshes to";
      uses bgp-output-queue-priority-class;
    }
    container withdraw-priority {
      description
        "Default output-queue to assign withdrawn routes to";
      uses bgp-output-queue-priority-class;
    }
    leaf advertise-srv6-service {
      type empty;
      description
        "Advertise SRv6 service";
    }
    leaf accept-srv6-service {
      type empty;
      description
        "Accept SRv6 service";
    }
    leaf-list import {
      type jt:policy-algebra;
      ordered-by user;
      description
        "Import policy";
    }
    leaf-list export {
      type jt:policy-algebra;
      ordered-by user;
      description
        "Export policy";
    }
  }

  grouping apath-options {
    description
      "Number of paths to advertise";
    uses apply-advanced;
    leaf receive {
      type empty;
      description
        "Receive multiple paths from peer";
    }
    container send {
      presence "enable send";
      description
        "Send multiple paths to peer";
      uses apply-advanced;
      container path-selection-mode {
        description
          "Configure how to select add-path routes";
        uses apply-advanced;
        choice mode {
          case case_1 {
            leaf all-paths {
              type empty;
              description
                "Advertise all paths allowed by path count";
            }
          }
          case case_2 {
            leaf equal-cost-paths {
              type empty;
              description
                "Advertise equal cost paths";
            }
          }
        }
      }
      leaf-list prefix-policy {
        type jt:policy-algebra;
        ordered-by user;
        description
          "Perform add-path only for prefixes that match policy";
      }
      leaf path-count {
        type union {
          type string {
            pattern "<.*>|$.*";
          }
          type int32 {
            range "2 .. 64";
          }
        }
        mandatory true;
        description
          "Number of paths to advertise";
      }
      leaf include-backup-path {
        type union {
          type string {
            pattern "<.*>|$.*";
          }
          type int32 {
            range "1 .. 2";
          }
        }
        description
          "Number of backup paths to advertise";
      }
      leaf multipath {
        type empty;
        description
          "Include only multipath contributor routes";
      }
    }
  }

  grouping bgp-afi-flow {
    uses apply-advanced;
    container prefix-limit {
      description
        "Limit maximum number of prefixes from a peer";
      uses bgpaf-prefix-limit;
    }
    container accepted-prefix-limit {
      description
        "Limit maximum number of prefixes accepted from a peer";
      uses bgpaf-accepted-prefix-limit;
    }
    container rib-group {
      description
        "Routing table group";
      uses rib_group_inet_type;
    }
    container add-path {
      description
        "Advertise multiple paths to peer";
      uses apath-options;
    }
    container aigp {
      presence "enable aigp";
      description
        "Allow sending and receiving of AIGP attribute";
      uses bgpaf-aigp-options;
    }
    leaf damping {
      type empty;
      description
        "Enable route flap damping";
    }
    leaf local-ipv4-address {
      type jt:ipv4addr;
      description
        "Local IPv4 address";
    }
    container loops {
      description
        "Allow local AS in received AS paths";
      uses bgpaf-loops;
    }
    container delay-route-advertisements {
      presence "enable delay-route-advertisements";
      description
        "Delay route updates for this family until FIB-sync";
      uses apply-advanced;
      leaf always-wait-for-krt-drain {
        type empty;
        description
          "Wait for KRT-queue drain for more-specific prefixes";
      }
      container minimum-delay {
        description
          "Minimum-delay to ensure KRT sees the route flash";
        uses apply-advanced;
        leaf routing-uptime {
          type union {
            type string {
              pattern "<.*>|$.*";
            }
            type uint32 {
              range "1 .. 36000";
            }
          }
          description
            "Min delay(sec) advertisement after RPD start";
        }
        leaf inbound-convergence {
          type union {
            type string {
              pattern "<.*>|$.*";
            }
            type uint32 {
              range "1 .. 36000";
            }
          }
          description
            "Min delay(sec) advertisement after source-peer sent all routes";
        }
      }
      container maximum-delay {
        description
          "Maximum delay deferring routes";
        uses apply-advanced;
        leaf route-age {
          type union {
            type string {
              pattern "<.*>|$.*";
            }
            type uint32 {
              range "1 .. 36000";
            }
          }
          description
            "Max delay(sec) advertisement route age";
        }
        leaf routing-uptime {
          type union {
            type string {
              pattern "<.*>|$.*";
            }
            type uint32 {
              range "1 .. 36000";
            }
          }
          description
            "Max delay(sec) advertisement after RPD start";
        }
      }
    }
    container nexthop-resolution {
      description
        "Configure nexthop resolution properties";
      uses apply-advanced;
      leaf no-resolution {
        type empty;
        description
          "Consider nexthop good without resolution attempt";
      }
      leaf preserve-nexthop-hierarchy {
        type empty;
        description
          "Attempt preserving resolved nexthop chain in forwarding";
      }
    }
    container defer-initial-multipath-build {
      presence "enable defer-initial-multipath-build";
      description
        "Defer initial multipath build until EOR is received";
      uses apply-advanced;
      leaf maximum-delay {
        type union {
          type string {
            pattern "<.*>|$.*";
          }
          type uint32 {
            range "1 .. 3600";
          }
        }
        description
          "Max delay(sec) multipath build after peer is up";
      }
    }
    container graceful-restart {
      description
        "BGP graceful restart options";
      uses bgp-af-gr;
    }
    leaf extended-nexthop {
      type empty;
      description
        "Extended nexthop encoding";
    }
    leaf extended-nexthop-color {
      type empty;
      description
        "Resolve using extended color nexthop";
    }
    leaf extended-nexthop-tunnel {
      type empty;
      description
        "Use BGP tunnel attribute";
    }
    leaf no-install {
      type empty;
      description
        "Dont install received routes in forwarding";
    }
    leaf route-age-bgp-view {
      type empty;
      description
        "Maintain BGP route's age based on Update messages only";
    }
    container output-queue-priority {
      description
        "Default output-queue to assign updates to";
      uses bgp-output-queue-priority-class;
    }
    container route-refresh-priority {
      description
        "Default output-queue to assign route refreshes to";
      uses bgp-output-queue-priority-class;
    }
    container withdraw-priority {
      description
        "Default output-queue to assign withdrawn routes to";
      uses bgp-output-queue-priority-class;
    }
    leaf advertise-srv6-service {
      type empty;
      description
        "Advertise SRv6 service";
    }
    leaf accept-srv6-service {
      type empty;
      description
        "Accept SRv6 service";
    }
    leaf-list import {
      type jt:policy-algebra;
      ordered-by user;
      description
        "Import policy";
    }
    leaf-list export {
      type jt:policy-algebra;
      ordered-by user;
      description
        "Export policy";
    }
    leaf-list no-validate {
      type jt:policy-algebra;
      ordered-by user;
      description
        "Bypass validation procedure for routes that match policy";
    }
    leaf strip-nexthop {
      type empty;
      description
        "Strip the next-hop from the outgoing flow update";
    }
    leaf allow-policy-add-nexthop {
      type empty;
      status deprecated;
      description
        "Allow policy to add nexthop to a route without nexthop";
    }
  }

  grouping bgp-afi-flow-with-redirect-ip-action {
    uses apply-advanced;
    container prefix-limit {
      description
        "Limit maximum number of prefixes from a peer";
      uses bgpaf-prefix-limit;
    }
    container accepted-prefix-limit {
      description
        "Limit maximum number of prefixes accepted from a peer";
      uses bgpaf-accepted-prefix-limit;
    }
    container rib-group {
      description
        "Routing table group";
      uses rib_group_inet_type;
    }
    container add-path {
      description
        "Advertise multiple paths to peer";
      uses apath-options;
    }
    container aigp {
      presence "enable aigp";
      description
        "Allow sending and receiving of AIGP attribute";
      uses bgpaf-aigp-options;
    }
    leaf damping {
      type empty;
      description
        "Enable route flap damping";
    }
    leaf local-ipv4-address {
      type jt:ipv4addr;
      description
        "Local IPv4 address";
    }
    container loops {
      description
        "Allow local AS in received AS paths";
      uses bgpaf-loops;
    }
    container delay-route-advertisements {
      presence "enable delay-route-advertisements";
      description
        "Delay route updates for this family until FIB-sync";
      uses apply-advanced;
      leaf always-wait-for-krt-drain {
        type empty;
        description
          "Wait for KRT-queue drain for more-specific prefixes";
      }
      container minimum-delay {
        description
          "Minimum-delay to ensure KRT sees the route flash";
        uses apply-advanced;
        leaf routing-uptime {
          type union {
            type string {
              pattern "<.*>|$.*";
            }
            type uint32 {
              range "1 .. 36000";
            }
          }
          description
            "Min delay(sec) advertisement after RPD start";
        }
        leaf inbound-convergence {
          type union {
            type string {
              pattern "<.*>|$.*";
            }
            type uint32 {
              range "1 .. 36000";
            }
          }
          description
            "Min delay(sec) advertisement after source-peer sent all routes";
        }
      }
      container maximum-delay {
        description
          "Maximum delay deferring routes";
        uses apply-advanced;
        leaf route-age {
          type union {
            type string {
              pattern "<.*>|$.*";
            }
            type uint32 {
              range "1 .. 36000";
            }
          }
          description
            "Max delay(sec) advertisement route age";
        }
        leaf routing-uptime {
          type union {
            type string {
              pattern "<.*>|$.*";
            }
            type uint32 {
              range "1 .. 36000";
            }
          }
          description
            "Max delay(sec) advertisement after RPD start";
        }
      }
    }
    container nexthop-resolution {
      description
        "Configure nexthop resolution properties";
      uses apply-advanced;
      leaf no-resolution {
        type empty;
        description
          "Consider nexthop good without resolution attempt";
      }
      leaf preserve-nexthop-hierarchy {
        type empty;
        description
          "Attempt preserving resolved nexthop chain in forwarding";
      }
    }
    container defer-initial-multipath-build {
      presence "enable defer-initial-multipath-build";
      description
        "Defer initial multipath build until EOR is received";
      uses apply-advanced;
      leaf maximum-delay {
        type union {
          type string {
            pattern "<.*>|$.*";
          }
          type uint32 {
            range "1 .. 3600";
          }
        }
        description
          "Max delay(sec) multipath build after peer is up";
      }
    }
    container graceful-restart {
      description
        "BGP graceful restart options";
      uses bgp-af-gr;
    }
    leaf extended-nexthop {
      type empty;
      description
        "Extended nexthop encoding";
    }
    leaf extended-nexthop-color {
      type empty;
      description
        "Resolve using extended color nexthop";
    }
    leaf extended-nexthop-tunnel {
      type empty;
      description
        "Use BGP tunnel attribute";
    }
    leaf no-install {
      type empty;
      description
        "Dont install received routes in forwarding";
    }
    leaf route-age-bgp-view {
      type empty;
      description
        "Maintain BGP route's age based on Update messages only";
    }
    container output-queue-priority {
      description
        "Default output-queue to assign updates to";
      uses bgp-output-queue-priority-class;
    }
    container route-refresh-priority {
      description
        "Default output-queue to assign route refreshes to";
      uses bgp-output-queue-priority-class;
    }
    container withdraw-priority {
      description
        "Default output-queue to assign withdrawn routes to";
      uses bgp-output-queue-priority-class;
    }
    leaf advertise-srv6-service {
      type empty;
      description
        "Advertise SRv6 service";
    }
    leaf accept-srv6-service {
      type empty;
      description
        "Accept SRv6 service";
    }
    leaf-list import {
      type jt:policy-algebra;
      ordered-by user;
      description
        "Import policy";
    }
    leaf-list export {
      type jt:policy-algebra;
      ordered-by user;
      description
        "Export policy";
    }
    leaf-list no-validate {
      type jt:policy-algebra;
      ordered-by user;
      description
        "Bypass validation procedure for routes that match policy";
    }
    leaf strip-nexthop {
      type empty;
      description
        "Strip the next-hop from the outgoing flow update";
    }
    container legacy-redirect-ip-action {
      presence "enable legacy-redirect-ip-action";
      description
        "Configure legacy redirect to IP support";
      uses apply-advanced;
      leaf receive {
        type empty;
        description
          "Accept legacy encoded redirect-to-ip action attribute";
      }
      leaf send {
        type empty;
        description
          "Advertise Redirect action as legacy redirect attribute";
      }
    }
    leaf secondary-independent-resolution {
      type empty;
      description
        "Resolve FLOW routes in VRF table independent of VPN FLOW route";
    }
  }

  grouping bgp-afi-inet-transport {
    uses apply-advanced;
    container prefix-limit {
      description
        "Limit maximum number of prefixes from a peer";
      uses bgpaf-prefix-limit;
    }
    container accepted-prefix-limit {
      description
        "Limit maximum number of prefixes accepted from a peer";
      uses bgpaf-accepted-prefix-limit;
    }
    container rib-group {
      description
        "Routing table group";
      uses rib_group_inet_type;
    }
    container add-path {
      description
        "Advertise multiple paths to peer";
      uses apath-options;
    }
    container aigp {
      presence "enable aigp";
      description
        "Allow sending and receiving of AIGP attribute";
      uses bgpaf-aigp-options;
    }
    leaf damping {
      type empty;
      description
        "Enable route flap damping";
    }
    leaf local-ipv4-address {
      type jt:ipv4addr;
      description
        "Local IPv4 address";
    }
    container loops {
      description
        "Allow local AS in received AS paths";
      uses bgpaf-loops;
    }
    container delay-route-advertisements {
      presence "enable delay-route-advertisements";
      description
        "Delay route updates for this family until FIB-sync";
      uses apply-advanced;
      leaf always-wait-for-krt-drain {
        type empty;
        description
          "Wait for KRT-queue drain for more-specific prefixes";
      }
      container minimum-delay {
        description
          "Minimum-delay to ensure KRT sees the route flash";
        uses apply-advanced;
        leaf routing-uptime {
          type union {
            type string {
              pattern "<.*>|$.*";
            }
            type uint32 {
              range "1 .. 36000";
            }
          }
          description
            "Min delay(sec) advertisement after RPD start";
        }
        leaf inbound-convergence {
          type union {
            type string {
              pattern "<.*>|$.*";
            }
            type uint32 {
              range "1 .. 36000";
            }
          }
          description
            "Min delay(sec) advertisement after source-peer sent all routes";
        }
      }
      container maximum-delay {
        description
          "Maximum delay deferring routes";
        uses apply-advanced;
        leaf route-age {
          type union {
            type string {
              pattern "<.*>|$.*";
            }
            type uint32 {
              range "1 .. 36000";
            }
          }
          description
            "Max delay(sec) advertisement route age";
        }
        leaf routing-uptime {
          type union {
            type string {
              pattern "<.*>|$.*";
            }
            type uint32 {
              range "1 .. 36000";
            }
          }
          description
            "Max delay(sec) advertisement after RPD start";
        }
      }
    }
    container nexthop-resolution {
      description
        "Configure nexthop resolution properties";
      uses apply-advanced;
      leaf no-resolution {
        type empty;
        description
          "Consider nexthop good without resolution attempt";
      }
      leaf preserve-nexthop-hierarchy {
        type empty;
        description
          "Attempt preserving resolved nexthop chain in forwarding";
      }
    }
    container defer-initial-multipath-build {
      presence "enable defer-initial-multipath-build";
      description
        "Defer initial multipath build until EOR is received";
      uses apply-advanced;
      leaf maximum-delay {
        type union {
          type string {
            pattern "<.*>|$.*";
          }
          type uint32 {
            range "1 .. 3600";
          }
        }
        description
          "Max delay(sec) multipath build after peer is up";
      }
    }
    container graceful-restart {
      description
        "BGP graceful restart options";
      uses bgp-af-gr;
    }
    leaf extended-nexthop {
      type empty;
      description
        "Extended nexthop encoding";
    }
    leaf extended-nexthop-color {
      type empty;
      description
        "Resolve using extended color nexthop";
    }
    leaf extended-nexthop-tunnel {
      type empty;
      description
        "Use BGP tunnel attribute";
    }
    leaf no-install {
      type empty;
      description
        "Dont install received routes in forwarding";
    }
    leaf route-age-bgp-view {
      type empty;
      description
        "Maintain BGP route's age based on Update messages only";
    }
    container output-queue-priority {
      description
        "Default output-queue to assign updates to";
      uses bgp-output-queue-priority-class;
    }
    container route-refresh-priority {
      description
        "Default output-queue to assign route refreshes to";
      uses bgp-output-queue-priority-class;
    }
    container withdraw-priority {
      description
        "Default output-queue to assign withdrawn routes to";
      uses bgp-output-queue-priority-class;
    }
    leaf advertise-srv6-service {
      type empty;
      description
        "Advertise SRv6 service";
    }
    leaf accept-srv6-service {
      type empty;
      description
        "Accept SRv6 service";
    }
    leaf-list import {
      type jt:policy-algebra;
      ordered-by user;
      description
        "Import policy";
    }
    leaf-list export {
      type jt:policy-algebra;
      ordered-by user;
      description
        "Export policy";
    }
    container aggregate-label {
      presence "enable aggregate-label";
      description
        "Aggregate labels of incoming routes with the same FEC";
      uses apply-advanced;
      leaf community {
        type string;
        mandatory true;
        description
          "Community to identify the FEC of incoming routes";
      }
    }
    leaf per-prefix-label {
      type empty;
      description
        "Allocate a unique label to each advertised prefix";
    }
    leaf per-group-label {
      type empty;
      description
        "Advertise prefixes with unique labels per group";
    }
    container traffic-statistics {
      presence "enable traffic-statistics";
      description
        "Collect statistics for BGP label-switched paths";
      uses bgpaf-traffic-statistics;
    }
    container protection {
      presence "enable protection";
      description
        "Compute backup path for active nexthop failure";
    }
  }

  grouping bgp-afi-inet6-labeled {
    uses apply-advanced;
    container prefix-limit {
      description
        "Limit maximum number of prefixes from a peer";
      uses bgpaf-prefix-limit;
    }
    container accepted-prefix-limit {
      description
        "Limit maximum number of prefixes accepted from a peer";
      uses bgpaf-accepted-prefix-limit;
    }
    container rib-group {
      description
        "Routing table group";
      uses rib_group_inet_type;
    }
    container add-path {
      description
        "Advertise multiple paths to peer";
      uses apath-options;
    }
    container aigp {
      presence "enable aigp";
      description
        "Allow sending and receiving of AIGP attribute";
      uses bgpaf-aigp-options;
    }
    leaf damping {
      type empty;
      description
        "Enable route flap damping";
    }
    leaf local-ipv4-address {
      type jt:ipv4addr;
      description
        "Local IPv4 address";
    }
    container loops {
      description
        "Allow local AS in received AS paths";
      uses bgpaf-loops;
    }
    container delay-route-advertisements {
      presence "enable delay-route-advertisements";
      description
        "Delay route updates for this family until FIB-sync";
      uses apply-advanced;
      leaf always-wait-for-krt-drain {
        type empty;
        description
          "Wait for KRT-queue drain for more-specific prefixes";
      }
      container minimum-delay {
        description
          "Minimum-delay to ensure KRT sees the route flash";
        uses apply-advanced;
        leaf routing-uptime {
          type union {
            type string {
              pattern "<.*>|$.*";
            }
            type uint32 {
              range "1 .. 36000";
            }
          }
          description
            "Min delay(sec) advertisement after RPD start";
        }
        leaf inbound-convergence {
          type union {
            type string {
              pattern "<.*>|$.*";
            }
            type uint32 {
              range "1 .. 36000";
            }
          }
          description
            "Min delay(sec) advertisement after source-peer sent all routes";
        }
      }
      container maximum-delay {
        description
          "Maximum delay deferring routes";
        uses apply-advanced;
        leaf route-age {
          type union {
            type string {
              pattern "<.*>|$.*";
            }
            type uint32 {
              range "1 .. 36000";
            }
          }
          description
            "Max delay(sec) advertisement route age";
        }
        leaf routing-uptime {
          type union {
            type string {
              pattern "<.*>|$.*";
            }
            type uint32 {
              range "1 .. 36000";
            }
          }
          description
            "Max delay(sec) advertisement after RPD start";
        }
      }
    }
    container nexthop-resolution {
      description
        "Configure nexthop resolution properties";
      uses apply-advanced;
      leaf no-resolution {
        type empty;
        description
          "Consider nexthop good without resolution attempt";
      }
      leaf preserve-nexthop-hierarchy {
        type empty;
        description
          "Attempt preserving resolved nexthop chain in forwarding";
      }
    }
    container defer-initial-multipath-build {
      presence "enable defer-initial-multipath-build";
      description
        "Defer initial multipath build until EOR is received";
      uses apply-advanced;
      leaf maximum-delay {
        type union {
          type string {
            pattern "<.*>|$.*";
          }
          type uint32 {
            range "1 .. 3600";
          }
        }
        description
          "Max delay(sec) multipath build after peer is up";
      }
    }
    container graceful-restart {
      description
        "BGP graceful restart options";
      uses bgp-af-gr;
    }
    leaf extended-nexthop {
      type empty;
      description
        "Extended nexthop encoding";
    }
    leaf extended-nexthop-color {
      type empty;
      description
        "Resolve using extended color nexthop";
    }
    leaf extended-nexthop-tunnel {
      type empty;
      description
        "Use BGP tunnel attribute";
    }
    leaf no-install {
      type empty;
      description
        "Dont install received routes in forwarding";
    }
    leaf route-age-bgp-view {
      type empty;
      description
        "Maintain BGP route's age based on Update messages only";
    }
    container output-queue-priority {
      description
        "Default output-queue to assign updates to";
      uses bgp-output-queue-priority-class;
    }
    container route-refresh-priority {
      description
        "Default output-queue to assign route refreshes to";
      uses bgp-output-queue-priority-class;
    }
    container withdraw-priority {
      description
        "Default output-queue to assign withdrawn routes to";
      uses bgp-output-queue-priority-class;
    }
    leaf advertise-srv6-service {
      type empty;
      description
        "Advertise SRv6 service";
    }
    leaf accept-srv6-service {
      type empty;
      description
        "Accept SRv6 service";
    }
    leaf-list import {
      type jt:policy-algebra;
      ordered-by user;
      description
        "Import policy";
    }
    leaf-list export {
      type jt:policy-algebra;
      ordered-by user;
      description
        "Export policy";
    }
    container aggregate-label {
      presence "enable aggregate-label";
      description
        "Aggregate labels of incoming routes with the same FEC";
      uses apply-advanced;
      leaf community {
        type string;
        mandatory true;
        description
          "Community to identify the FEC of incoming routes";
      }
    }
    leaf per-group-label {
      type empty;
      description
        "Advertise prefixes with unique labels per group";
    }
    container traffic-statistics {
      presence "enable traffic-statistics";
      description
        "Collect statistics for BGP label-switched paths";
      uses bgpaf-traffic-statistics;
    }
    container rib {
      description
        "Select table used by labeled unicast routes";
      uses apply-advanced;
      leaf inet6.3 {
        type empty;
        description
          "Use inet6.3 to exchange labeled unicast routes";
      }
    }
    container explicit-null {
      presence "enable explicit-null";
      description
        "Advertise explicit null";
      leaf connected-only {
        type empty;
        description
          "Advertise explicit null only for connected routes";
      }
    }
    container protection {
      presence "enable protection";
      description
        "Compute backup path for active nexthop failure";
    }
    list topology {
      key "name";
      ordered-by user;
      description
        "Multi topology routing tables";
      leaf name {
        type string;
        description
          "Topology name";
      }
      uses apply-advanced;
      leaf community {
        type string;
        mandatory true;
        description
          "Community to identify multi topology routes";
      }
    }
  }

  grouping bgp-afi-inet6-transport {
    uses apply-advanced;
    container prefix-limit {
      description
        "Limit maximum number of prefixes from a peer";
      uses bgpaf-prefix-limit;
    }
    container accepted-prefix-limit {
      description
        "Limit maximum number of prefixes accepted from a peer";
      uses bgpaf-accepted-prefix-limit;
    }
    container rib-group {
      description
        "Routing table group";
      uses rib_group_inet_type;
    }
    container add-path {
      description
        "Advertise multiple paths to peer";
      uses apath-options;
    }
    container aigp {
      presence "enable aigp";
      description
        "Allow sending and receiving of AIGP attribute";
      uses bgpaf-aigp-options;
    }
    leaf damping {
      type empty;
      description
        "Enable route flap damping";
    }
    leaf local-ipv4-address {
      type jt:ipv4addr;
      description
        "Local IPv4 address";
    }
    container loops {
      description
        "Allow local AS in received AS paths";
      uses bgpaf-loops;
    }
    container delay-route-advertisements {
      presence "enable delay-route-advertisements";
      description
        "Delay route updates for this family until FIB-sync";
      uses apply-advanced;
      leaf always-wait-for-krt-drain {
        type empty;
        description
          "Wait for KRT-queue drain for more-specific prefixes";
      }
      container minimum-delay {
        description
          "Minimum-delay to ensure KRT sees the route flash";
        uses apply-advanced;
        leaf routing-uptime {
          type union {
            type string {
              pattern "<.*>|$.*";
            }
            type uint32 {
              range "1 .. 36000";
            }
          }
          description
            "Min delay(sec) advertisement after RPD start";
        }
        leaf inbound-convergence {
          type union {
            type string {
              pattern "<.*>|$.*";
            }
            type uint32 {
              range "1 .. 36000";
            }
          }
          description
            "Min delay(sec) advertisement after source-peer sent all routes";
        }
      }
      container maximum-delay {
        description
          "Maximum delay deferring routes";
        uses apply-advanced;
        leaf route-age {
          type union {
            type string {
              pattern "<.*>|$.*";
            }
            type uint32 {
              range "1 .. 36000";
            }
          }
          description
            "Max delay(sec) advertisement route age";
        }
        leaf routing-uptime {
          type union {
            type string {
              pattern "<.*>|$.*";
            }
            type uint32 {
              range "1 .. 36000";
            }
          }
          description
            "Max delay(sec) advertisement after RPD start";
        }
      }
    }
    container nexthop-resolution {
      description
        "Configure nexthop resolution properties";
      uses apply-advanced;
      leaf no-resolution {
        type empty;
        description
          "Consider nexthop good without resolution attempt";
      }
      leaf preserve-nexthop-hierarchy {
        type empty;
        description
          "Attempt preserving resolved nexthop chain in forwarding";
      }
    }
    container defer-initial-multipath-build {
      presence "enable defer-initial-multipath-build";
      description
        "Defer initial multipath build until EOR is received";
      uses apply-advanced;
      leaf maximum-delay {
        type union {
          type string {
            pattern "<.*>|$.*";
          }
          type uint32 {
            range "1 .. 3600";
          }
        }
        description
          "Max delay(sec) multipath build after peer is up";
      }
    }
    container graceful-restart {
      description
        "BGP graceful restart options";
      uses bgp-af-gr;
    }
    leaf extended-nexthop {
      type empty;
      description
        "Extended nexthop encoding";
    }
    leaf extended-nexthop-color {
      type empty;
      description
        "Resolve using extended color nexthop";
    }
    leaf extended-nexthop-tunnel {
      type empty;
      description
        "Use BGP tunnel attribute";
    }
    leaf no-install {
      type empty;
      description
        "Dont install received routes in forwarding";
    }
    leaf route-age-bgp-view {
      type empty;
      description
        "Maintain BGP route's age based on Update messages only";
    }
    container output-queue-priority {
      description
        "Default output-queue to assign updates to";
      uses bgp-output-queue-priority-class;
    }
    container route-refresh-priority {
      description
        "Default output-queue to assign route refreshes to";
      uses bgp-output-queue-priority-class;
    }
    container withdraw-priority {
      description
        "Default output-queue to assign withdrawn routes to";
      uses bgp-output-queue-priority-class;
    }
    leaf advertise-srv6-service {
      type empty;
      description
        "Advertise SRv6 service";
    }
    leaf accept-srv6-service {
      type empty;
      description
        "Accept SRv6 service";
    }
    leaf-list import {
      type jt:policy-algebra;
      ordered-by user;
      description
        "Import policy";
    }
    leaf-list export {
      type jt:policy-algebra;
      ordered-by user;
      description
        "Export policy";
    }
    container aggregate-label {
      presence "enable aggregate-label";
      description
        "Aggregate labels of incoming routes with the same FEC";
      uses apply-advanced;
      leaf community {
        type string;
        mandatory true;
        description
          "Community to identify the FEC of incoming routes";
      }
    }
    leaf per-prefix-label {
      type empty;
      description
        "Allocate a unique label to each advertised prefix";
    }
    leaf per-group-label {
      type empty;
      description
        "Advertise prefixes with unique labels per group";
    }
    container traffic-statistics {
      presence "enable traffic-statistics";
      description
        "Collect statistics for BGP label-switched paths";
      uses bgpaf-traffic-statistics;
    }
    container lu-export {
      presence "enable lu-export";
      description
        "Install Classful Transport routes in inet6.3";
      uses apply-advanced;
    }
    container protection {
      presence "enable protection";
      description
        "Compute backup path for active nexthop failure";
    }
  }

  grouping bgp-afi-l2vpn {
    uses apply-advanced;
    container prefix-limit {
      description
        "Limit maximum number of prefixes from a peer";
      uses bgpaf-prefix-limit;
    }
    container accepted-prefix-limit {
      description
        "Limit maximum number of prefixes accepted from a peer";
      uses bgpaf-accepted-prefix-limit;
    }
    container rib-group {
      description
        "Routing table group";
      uses rib_group_inet_type;
    }
    container add-path {
      description
        "Advertise multiple paths to peer";
      uses apath-options;
    }
    container aigp {
      presence "enable aigp";
      description
        "Allow sending and receiving of AIGP attribute";
      uses bgpaf-aigp-options;
    }
    leaf damping {
      type empty;
      description
        "Enable route flap damping";
    }
    leaf local-ipv4-address {
      type jt:ipv4addr;
      description
        "Local IPv4 address";
    }
    container loops {
      description
        "Allow local AS in received AS paths";
      uses bgpaf-loops;
    }
    container delay-route-advertisements {
      presence "enable delay-route-advertisements";
      description
        "Delay route updates for this family until FIB-sync";
      uses apply-advanced;
      leaf always-wait-for-krt-drain {
        type empty;
        description
          "Wait for KRT-queue drain for more-specific prefixes";
      }
      container minimum-delay {
        description
          "Minimum-delay to ensure KRT sees the route flash";
        uses apply-advanced;
        leaf routing-uptime {
          type union {
            type string {
              pattern "<.*>|$.*";
            }
            type uint32 {
              range "1 .. 36000";
            }
          }
          description
            "Min delay(sec) advertisement after RPD start";
        }
        leaf inbound-convergence {
          type union {
            type string {
              pattern "<.*>|$.*";
            }
            type uint32 {
              range "1 .. 36000";
            }
          }
          description
            "Min delay(sec) advertisement after source-peer sent all routes";
        }
      }
      container maximum-delay {
        description
          "Maximum delay deferring routes";
        uses apply-advanced;
        leaf route-age {
          type union {
            type string {
              pattern "<.*>|$.*";
            }
            type uint32 {
              range "1 .. 36000";
            }
          }
          description
            "Max delay(sec) advertisement route age";
        }
        leaf routing-uptime {
          type union {
            type string {
              pattern "<.*>|$.*";
            }
            type uint32 {
              range "1 .. 36000";
            }
          }
          description
            "Max delay(sec) advertisement after RPD start";
        }
      }
    }
    container nexthop-resolution {
      description
        "Configure nexthop resolution properties";
      uses apply-advanced;
      leaf no-resolution {
        type empty;
        description
          "Consider nexthop good without resolution attempt";
      }
      leaf preserve-nexthop-hierarchy {
        type empty;
        description
          "Attempt preserving resolved nexthop chain in forwarding";
      }
    }
    container defer-initial-multipath-build {
      presence "enable defer-initial-multipath-build";
      description
        "Defer initial multipath build until EOR is received";
      uses apply-advanced;
      leaf maximum-delay {
        type union {
          type string {
            pattern "<.*>|$.*";
          }
          type uint32 {
            range "1 .. 3600";
          }
        }
        description
          "Max delay(sec) multipath build after peer is up";
      }
    }
    container graceful-restart {
      description
        "BGP graceful restart options";
      uses bgp-af-gr;
    }
    leaf extended-nexthop {
      type empty;
      description
        "Extended nexthop encoding";
    }
    leaf extended-nexthop-color {
      type empty;
      description
        "Resolve using extended color nexthop";
    }
    leaf extended-nexthop-tunnel {
      type empty;
      description
        "Use BGP tunnel attribute";
    }
    leaf no-install {
      type empty;
      description
        "Dont install received routes in forwarding";
    }
    leaf route-age-bgp-view {
      type empty;
      description
        "Maintain BGP route's age based on Update messages only";
    }
    container output-queue-priority {
      description
        "Default output-queue to assign updates to";
      uses bgp-output-queue-priority-class;
    }
    container route-refresh-priority {
      description
        "Default output-queue to assign route refreshes to";
      uses bgp-output-queue-priority-class;
    }
    container withdraw-priority {
      description
        "Default output-queue to assign withdrawn routes to";
      uses bgp-output-queue-priority-class;
    }
    leaf advertise-srv6-service {
      type empty;
      description
        "Advertise SRv6 service";
    }
    leaf accept-srv6-service {
      type empty;
      description
        "Accept SRv6 service";
    }
    leaf-list import {
      type jt:policy-algebra;
      ordered-by user;
      description
        "Import policy";
    }
    leaf-list export {
      type jt:policy-algebra;
      ordered-by user;
      description
        "Export policy";
    }
    container egress-protection {
      presence "enable egress-protection";
      description
        "Egress router protection";
      uses apply-advanced;
      container context-identifier {
        description
          "Context identifier";
        uses apply-advanced;
        leaf context-id {
          type jt:ipv4addr;
          description
            "IP address";
        }
      }
      leaf-list keep-import {
        type jt:policy-algebra;
        ordered-by user;
        description
          "Import policy";
      }
    }
  }

  grouping bgp-afi-l3vpn {
    uses apply-advanced;
    container prefix-limit {
      description
        "Limit maximum number of prefixes from a peer";
      uses bgpaf-prefix-limit;
    }
    container accepted-prefix-limit {
      description
        "Limit maximum number of prefixes accepted from a peer";
      uses bgpaf-accepted-prefix-limit;
    }
    container rib-group {
      description
        "Routing table group";
      uses rib_group_inet_type;
    }
    container add-path {
      description
        "Advertise multiple paths to peer";
      uses apath-options;
    }
    container aigp {
      presence "enable aigp";
      description
        "Allow sending and receiving of AIGP attribute";
      uses bgpaf-aigp-options;
    }
    leaf damping {
      type empty;
      description
        "Enable route flap damping";
    }
    leaf local-ipv4-address {
      type jt:ipv4addr;
      description
        "Local IPv4 address";
    }
    container loops {
      description
        "Allow local AS in received AS paths";
      uses bgpaf-loops;
    }
    container delay-route-advertisements {
      presence "enable delay-route-advertisements";
      description
        "Delay route updates for this family until FIB-sync";
      uses apply-advanced;
      leaf always-wait-for-krt-drain {
        type empty;
        description
          "Wait for KRT-queue drain for more-specific prefixes";
      }
      container minimum-delay {
        description
          "Minimum-delay to ensure KRT sees the route flash";
        uses apply-advanced;
        leaf routing-uptime {
          type union {
            type string {
              pattern "<.*>|$.*";
            }
            type uint32 {
              range "1 .. 36000";
            }
          }
          description
            "Min delay(sec) advertisement after RPD start";
        }
        leaf inbound-convergence {
          type union {
            type string {
              pattern "<.*>|$.*";
            }
            type uint32 {
              range "1 .. 36000";
            }
          }
          description
            "Min delay(sec) advertisement after source-peer sent all routes";
        }
      }
      container maximum-delay {
        description
          "Maximum delay deferring routes";
        uses apply-advanced;
        leaf route-age {
          type union {
            type string {
              pattern "<.*>|$.*";
            }
            type uint32 {
              range "1 .. 36000";
            }
          }
          description
            "Max delay(sec) advertisement route age";
        }
        leaf routing-uptime {
          type union {
            type string {
              pattern "<.*>|$.*";
            }
            type uint32 {
              range "1 .. 36000";
            }
          }
          description
            "Max delay(sec) advertisement after RPD start";
        }
      }
    }
    container nexthop-resolution {
      description
        "Configure nexthop resolution properties";
      uses apply-advanced;
      leaf no-resolution {
        type empty;
        description
          "Consider nexthop good without resolution attempt";
      }
      leaf preserve-nexthop-hierarchy {
        type empty;
        description
          "Attempt preserving resolved nexthop chain in forwarding";
      }
    }
    container defer-initial-multipath-build {
      presence "enable defer-initial-multipath-build";
      description
        "Defer initial multipath build until EOR is received";
      uses apply-advanced;
      leaf maximum-delay {
        type union {
          type string {
            pattern "<.*>|$.*";
          }
          type uint32 {
            range "1 .. 3600";
          }
        }
        description
          "Max delay(sec) multipath build after peer is up";
      }
    }
    container graceful-restart {
      description
        "BGP graceful restart options";
      uses bgp-af-gr;
    }
    leaf extended-nexthop {
      type empty;
      description
        "Extended nexthop encoding";
    }
    leaf extended-nexthop-color {
      type empty;
      description
        "Resolve using extended color nexthop";
    }
    leaf extended-nexthop-tunnel {
      type empty;
      description
        "Use BGP tunnel attribute";
    }
    leaf no-install {
      type empty;
      description
        "Dont install received routes in forwarding";
    }
    leaf route-age-bgp-view {
      type empty;
      description
        "Maintain BGP route's age based on Update messages only";
    }
    container output-queue-priority {
      description
        "Default output-queue to assign updates to";
      uses bgp-output-queue-priority-class;
    }
    container route-refresh-priority {
      description
        "Default output-queue to assign route refreshes to";
      uses bgp-output-queue-priority-class;
    }
    container withdraw-priority {
      description
        "Default output-queue to assign withdrawn routes to";
      uses bgp-output-queue-priority-class;
    }
    leaf advertise-srv6-service {
      type empty;
      description
        "Advertise SRv6 service";
    }
    leaf accept-srv6-service {
      type empty;
      description
        "Accept SRv6 service";
    }
    leaf-list import {
      type jt:policy-algebra;
      ordered-by user;
      description
        "Import policy";
    }
    leaf-list export {
      type jt:policy-algebra;
      ordered-by user;
      description
        "Export policy";
    }
    container aggregate-label {
      presence "enable aggregate-label";
      description
        "Aggregate labels of incoming routes with the same FEC";
      uses apply-advanced;
      leaf community {
        type string;
        mandatory true;
        description
          "Community to identify the FEC of incoming routes";
      }
    }
    container egress-protection {
      presence "enable egress-protection";
      description
        "Egress router protection";
      uses apply-advanced;
      container context-identifier {
        description
          "Context identifier";
        uses apply-advanced;
        leaf context-id {
          type jt:ipv4addr;
          description
            "IP address";
        }
      }
      leaf-list keep-import {
        type jt:policy-algebra;
        ordered-by user;
        description
          "Import policy";
      }
    }
    leaf accept-local-nexthop {
      type empty;
      description
        "Enable processing of routes with own nexthop";
    }
    leaf accept-own {
      type empty;
      description
        "Enable processing of routes with own originator-id or nexthop";
    }
  }

  grouping bgp-afi-labeled {
    uses apply-advanced;
    container prefix-limit {
      description
        "Limit maximum number of prefixes from a peer";
      uses bgpaf-prefix-limit;
    }
    container accepted-prefix-limit {
      description
        "Limit maximum number of prefixes accepted from a peer";
      uses bgpaf-accepted-prefix-limit;
    }
    container rib-group {
      description
        "Routing table group";
      uses rib_group_inet_type;
    }
    container add-path {
      description
        "Advertise multiple paths to peer";
      uses apath-options;
    }
    container aigp {
      presence "enable aigp";
      description
        "Allow sending and receiving of AIGP attribute";
      uses bgpaf-aigp-options;
    }
    leaf damping {
      type empty;
      description
        "Enable route flap damping";
    }
    leaf local-ipv4-address {
      type jt:ipv4addr;
      description
        "Local IPv4 address";
    }
    container loops {
      description
        "Allow local AS in received AS paths";
      uses bgpaf-loops;
    }
    container delay-route-advertisements {
      presence "enable delay-route-advertisements";
      description
        "Delay route updates for this family until FIB-sync";
      uses apply-advanced;
      leaf always-wait-for-krt-drain {
        type empty;
        description
          "Wait for KRT-queue drain for more-specific prefixes";
      }
      container minimum-delay {
        description
          "Minimum-delay to ensure KRT sees the route flash";
        uses apply-advanced;
        leaf routing-uptime {
          type union {
            type string {
              pattern "<.*>|$.*";
            }
            type uint32 {
              range "1 .. 36000";
            }
          }
          description
            "Min delay(sec) advertisement after RPD start";
        }
        leaf inbound-convergence {
          type union {
            type string {
              pattern "<.*>|$.*";
            }
            type uint32 {
              range "1 .. 36000";
            }
          }
          description
            "Min delay(sec) advertisement after source-peer sent all routes";
        }
      }
      container maximum-delay {
        description
          "Maximum delay deferring routes";
        uses apply-advanced;
        leaf route-age {
          type union {
            type string {
              pattern "<.*>|$.*";
            }
            type uint32 {
              range "1 .. 36000";
            }
          }
          description
            "Max delay(sec) advertisement route age";
        }
        leaf routing-uptime {
          type union {
            type string {
              pattern "<.*>|$.*";
            }
            type uint32 {
              range "1 .. 36000";
            }
          }
          description
            "Max delay(sec) advertisement after RPD start";
        }
      }
    }
    container nexthop-resolution {
      description
        "Configure nexthop resolution properties";
      uses apply-advanced;
      leaf no-resolution {
        type empty;
        description
          "Consider nexthop good without resolution attempt";
      }
      leaf preserve-nexthop-hierarchy {
        type empty;
        description
          "Attempt preserving resolved nexthop chain in forwarding";
      }
    }
    container defer-initial-multipath-build {
      presence "enable defer-initial-multipath-build";
      description
        "Defer initial multipath build until EOR is received";
      uses apply-advanced;
      leaf maximum-delay {
        type union {
          type string {
            pattern "<.*>|$.*";
          }
          type uint32 {
            range "1 .. 3600";
          }
        }
        description
          "Max delay(sec) multipath build after peer is up";
      }
    }
    container graceful-restart {
      description
        "BGP graceful restart options";
      uses bgp-af-gr;
    }
    leaf extended-nexthop {
      type empty;
      description
        "Extended nexthop encoding";
    }
    leaf extended-nexthop-color {
      type empty;
      description
        "Resolve using extended color nexthop";
    }
    leaf extended-nexthop-tunnel {
      type empty;
      description
        "Use BGP tunnel attribute";
    }
    leaf no-install {
      type empty;
      description
        "Dont install received routes in forwarding";
    }
    leaf route-age-bgp-view {
      type empty;
      description
        "Maintain BGP route's age based on Update messages only";
    }
    container output-queue-priority {
      description
        "Default output-queue to assign updates to";
      uses bgp-output-queue-priority-class;
    }
    container route-refresh-priority {
      description
        "Default output-queue to assign route refreshes to";
      uses bgp-output-queue-priority-class;
    }
    container withdraw-priority {
      description
        "Default output-queue to assign withdrawn routes to";
      uses bgp-output-queue-priority-class;
    }
    leaf advertise-srv6-service {
      type empty;
      description
        "Advertise SRv6 service";
    }
    leaf accept-srv6-service {
      type empty;
      description
        "Accept SRv6 service";
    }
    leaf-list import {
      type jt:policy-algebra;
      ordered-by user;
      description
        "Import policy";
    }
    leaf-list export {
      type jt:policy-algebra;
      ordered-by user;
      description
        "Export policy";
    }
    container aggregate-label {
      presence "enable aggregate-label";
      description
        "Aggregate labels of incoming routes with the same FEC";
      uses apply-advanced;
      leaf community {
        type string;
        mandatory true;
        description
          "Community to identify the FEC of incoming routes";
      }
    }
    leaf per-prefix-label {
      type empty;
      description
        "Allocate a unique label to each advertised prefix";
    }
    leaf per-group-label {
      type empty;
      description
        "Advertise prefixes with unique labels per group";
    }
    container traffic-statistics {
      presence "enable traffic-statistics";
      description
        "Collect statistics for BGP label-switched paths";
      uses bgpaf-traffic-statistics;
    }
    list topology {
      key "name";
      ordered-by user;
      description
        "Multi topology routing tables";
      leaf name {
        type string;
        description
          "Topology name";
      }
      uses apply-advanced;
      leaf community {
        type string;
        mandatory true;
        description
          "Community to identify multi topology routes";
      }
    }
    container rib {
      description
        "Select table used by labeled unicast routes";
      uses rib-inet3;
    }
    container explicit-null {
      presence "enable explicit-null";
      description
        "Advertise explicit null";
      leaf connected-only {
        type empty;
        mandatory true;
        description
          "Advertise explicit null only for connected routes";
      }
    }
    container protection {
      presence "enable protection";
      description
        "Compute backup path for active nexthop failure";
      uses apply-advanced;
    }
    container egress-protection {
      presence "enable egress-protection";
      description
        "Egress router protection";
      uses apply-advanced;
      container context-identifier {
        description
          "Context identifier";
        uses apply-advanced;
        leaf context-id {
          type jt:ipv4addr;
          description
            "IP address";
        }
      }
      leaf-list keep-import {
        type jt:policy-algebra;
        ordered-by user;
        description
          "Import policy";
      }
    }
    leaf resolve-vpn {
      type empty;
      description
        "Install received NLRI in inet.3 also";
    }
    container entropy-label {
      presence "enable entropy-label";
      description
        "Use entropy label for entropy label capable BGP LSPs";
      uses apply-advanced;
      leaf-list import {
        type jt:policy-algebra;
        ordered-by user;
        description
          "Policy to select BGP LSPs to use entropy label";
      }
      leaf no-next-hop-validation {
        type empty;
        description
          "Don't validate next hop field against route next hop";
      }
      leaf elc-v2-compatible {
        type empty;
        description
          "Send and accept ELCv2 in addition to ELCv3";
      }
    }
  }

  grouping bgp-afi-srte {
    uses apply-advanced;
    container prefix-limit {
      description
        "Limit maximum number of prefixes from a peer";
      uses bgpaf-prefix-limit;
    }
    container accepted-prefix-limit {
      description
        "Limit maximum number of prefixes accepted from a peer";
      uses bgpaf-accepted-prefix-limit;
    }
    leaf damping {
      type empty;
      description
        "Enable route flap damping";
    }
    container loops {
      description
        "Allow local AS in received AS paths";
      uses bgpaf-loops;
    }
    container graceful-restart {
      description
        "BGP graceful restart options";
      uses bgp-af-gr;
    }
    leaf no-install {
      type empty;
      description
        "Dont install received routes in forwarding";
    }
    container output-queue-priority {
      description
        "Default output-queue to assign updates to";
      uses bgp-output-queue-priority-class;
    }
    container route-refresh-priority {
      description
        "Default output-queue to assign route refreshes to";
      uses bgp-output-queue-priority-class;
    }
    container withdraw-priority {
      description
        "Default output-queue to assign withdrawn routes to";
      uses bgp-output-queue-priority-class;
    }
    leaf-list export {
      type jt:policy-algebra;
      ordered-by user;
      description
        "Export policy";
    }
    leaf-list import {
      type jt:policy-algebra;
      ordered-by user;
      description
        "Import policy";
    }
  }

  grouping bgp-afi-topo {
    uses apply-advanced;
    container prefix-limit {
      description
        "Limit maximum number of prefixes from a peer";
      uses bgpaf-prefix-limit;
    }
    container accepted-prefix-limit {
      description
        "Limit maximum number of prefixes accepted from a peer";
      uses bgpaf-accepted-prefix-limit;
    }
    container rib-group {
      description
        "Routing table group";
      uses rib_group_inet_type;
    }
    container add-path {
      description
        "Advertise multiple paths to peer";
      uses apath-options;
    }
    container aigp {
      presence "enable aigp";
      description
        "Allow sending and receiving of AIGP attribute";
      uses bgpaf-aigp-options;
    }
    leaf damping {
      type empty;
      description
        "Enable route flap damping";
    }
    leaf local-ipv4-address {
      type jt:ipv4addr;
      description
        "Local IPv4 address";
    }
    container loops {
      description
        "Allow local AS in received AS paths";
      uses bgpaf-loops;
    }
    container delay-route-advertisements {
      presence "enable delay-route-advertisements";
      description
        "Delay route updates for this family until FIB-sync";
      uses apply-advanced;
      leaf always-wait-for-krt-drain {
        type empty;
        description
          "Wait for KRT-queue drain for more-specific prefixes";
      }
      container minimum-delay {
        description
          "Minimum-delay to ensure KRT sees the route flash";
        uses apply-advanced;
        leaf routing-uptime {
          type union {
            type string {
              pattern "<.*>|$.*";
            }
            type uint32 {
              range "1 .. 36000";
            }
          }
          description
            "Min delay(sec) advertisement after RPD start";
        }
        leaf inbound-convergence {
          type union {
            type string {
              pattern "<.*>|$.*";
            }
            type uint32 {
              range "1 .. 36000";
            }
          }
          description
            "Min delay(sec) advertisement after source-peer sent all routes";
        }
      }
      container maximum-delay {
        description
          "Maximum delay deferring routes";
        uses apply-advanced;
        leaf route-age {
          type union {
            type string {
              pattern "<.*>|$.*";
            }
            type uint32 {
              range "1 .. 36000";
            }
          }
          description
            "Max delay(sec) advertisement route age";
        }
        leaf routing-uptime {
          type union {
            type string {
              pattern "<.*>|$.*";
            }
            type uint32 {
              range "1 .. 36000";
            }
          }
          description
            "Max delay(sec) advertisement after RPD start";
        }
      }
    }
    container nexthop-resolution {
      description
        "Configure nexthop resolution properties";
      uses apply-advanced;
      leaf no-resolution {
        type empty;
        description
          "Consider nexthop good without resolution attempt";
      }
      leaf preserve-nexthop-hierarchy {
        type empty;
        description
          "Attempt preserving resolved nexthop chain in forwarding";
      }
    }
    container defer-initial-multipath-build {
      presence "enable defer-initial-multipath-build";
      description
        "Defer initial multipath build until EOR is received";
      uses apply-advanced;
      leaf maximum-delay {
        type union {
          type string {
            pattern "<.*>|$.*";
          }
          type uint32 {
            range "1 .. 3600";
          }
        }
        description
          "Max delay(sec) multipath build after peer is up";
      }
    }
    container graceful-restart {
      description
        "BGP graceful restart options";
      uses bgp-af-gr;
    }
    leaf extended-nexthop {
      type empty;
      description
        "Extended nexthop encoding";
    }
    leaf extended-nexthop-color {
      type empty;
      description
        "Resolve using extended color nexthop";
    }
    leaf extended-nexthop-tunnel {
      type empty;
      description
        "Use BGP tunnel attribute";
    }
    leaf no-install {
      type empty;
      description
        "Dont install received routes in forwarding";
    }
    leaf route-age-bgp-view {
      type empty;
      description
        "Maintain BGP route's age based on Update messages only";
    }
    container output-queue-priority {
      description
        "Default output-queue to assign updates to";
      uses bgp-output-queue-priority-class;
    }
    container route-refresh-priority {
      description
        "Default output-queue to assign route refreshes to";
      uses bgp-output-queue-priority-class;
    }
    container withdraw-priority {
      description
        "Default output-queue to assign withdrawn routes to";
      uses bgp-output-queue-priority-class;
    }
    leaf advertise-srv6-service {
      type empty;
      description
        "Advertise SRv6 service";
    }
    leaf accept-srv6-service {
      type empty;
      description
        "Accept SRv6 service";
    }
    leaf-list import {
      type jt:policy-algebra;
      ordered-by user;
      description
        "Import policy";
    }
    leaf-list export {
      type jt:policy-algebra;
      ordered-by user;
      description
        "Export policy";
    }
    container protection {
      presence "enable protection";
      description
        "Compute backup path for active nexthop failure";
    }
    list topology {
      key "name";
      ordered-by user;
      description
        "Multi topology routing tables";
      leaf name {
        type string;
        description
          "Topology name";
      }
      uses apply-advanced;
      leaf community {
        type string;
        mandatory true;
        description
          "Community to identify multi topology routes";
      }
    }
  }

  grouping bgp-afi-vpn {
    uses apply-advanced;
    container prefix-limit {
      description
        "Limit maximum number of prefixes from a peer";
      uses bgpaf-prefix-limit;
    }
    container accepted-prefix-limit {
      description
        "Limit maximum number of prefixes accepted from a peer";
      uses bgpaf-accepted-prefix-limit;
    }
    container rib-group {
      description
        "Routing table group";
      uses rib_group_inet_type;
    }
    container add-path {
      description
        "Advertise multiple paths to peer";
      uses apath-options;
    }
    container aigp {
      presence "enable aigp";
      description
        "Allow sending and receiving of AIGP attribute";
      uses bgpaf-aigp-options;
    }
    leaf damping {
      type empty;
      description
        "Enable route flap damping";
    }
    leaf local-ipv4-address {
      type jt:ipv4addr;
      description
        "Local IPv4 address";
    }
    container loops {
      description
        "Allow local AS in received AS paths";
      uses bgpaf-loops;
    }
    container delay-route-advertisements {
      presence "enable delay-route-advertisements";
      description
        "Delay route updates for this family until FIB-sync";
      uses apply-advanced;
      leaf always-wait-for-krt-drain {
        type empty;
        description
          "Wait for KRT-queue drain for more-specific prefixes";
      }
      container minimum-delay {
        description
          "Minimum-delay to ensure KRT sees the route flash";
        uses apply-advanced;
        leaf routing-uptime {
          type union {
            type string {
              pattern "<.*>|$.*";
            }
            type uint32 {
              range "1 .. 36000";
            }
          }
          description
            "Min delay(sec) advertisement after RPD start";
        }
        leaf inbound-convergence {
          type union {
            type string {
              pattern "<.*>|$.*";
            }
            type uint32 {
              range "1 .. 36000";
            }
          }
          description
            "Min delay(sec) advertisement after source-peer sent all routes";
        }
      }
      container maximum-delay {
        description
          "Maximum delay deferring routes";
        uses apply-advanced;
        leaf route-age {
          type union {
            type string {
              pattern "<.*>|$.*";
            }
            type uint32 {
              range "1 .. 36000";
            }
          }
          description
            "Max delay(sec) advertisement route age";
        }
        leaf routing-uptime {
          type union {
            type string {
              pattern "<.*>|$.*";
            }
            type uint32 {
              range "1 .. 36000";
            }
          }
          description
            "Max delay(sec) advertisement after RPD start";
        }
      }
    }
    container nexthop-resolution {
      description
        "Configure nexthop resolution properties";
      uses apply-advanced;
      leaf no-resolution {
        type empty;
        description
          "Consider nexthop good without resolution attempt";
      }
      leaf preserve-nexthop-hierarchy {
        type empty;
        description
          "Attempt preserving resolved nexthop chain in forwarding";
      }
    }
    container defer-initial-multipath-build {
      presence "enable defer-initial-multipath-build";
      description
        "Defer initial multipath build until EOR is received";
      uses apply-advanced;
      leaf maximum-delay {
        type union {
          type string {
            pattern "<.*>|$.*";
          }
          type uint32 {
            range "1 .. 3600";
          }
        }
        description
          "Max delay(sec) multipath build after peer is up";
      }
    }
    container graceful-restart {
      description
        "BGP graceful restart options";
      uses bgp-af-gr;
    }
    leaf extended-nexthop {
      type empty;
      description
        "Extended nexthop encoding";
    }
    leaf extended-nexthop-color {
      type empty;
      description
        "Resolve using extended color nexthop";
    }
    leaf extended-nexthop-tunnel {
      type empty;
      description
        "Use BGP tunnel attribute";
    }
    leaf no-install {
      type empty;
      description
        "Dont install received routes in forwarding";
    }
    leaf route-age-bgp-view {
      type empty;
      description
        "Maintain BGP route's age based on Update messages only";
    }
    container output-queue-priority {
      description
        "Default output-queue to assign updates to";
      uses bgp-output-queue-priority-class;
    }
    container route-refresh-priority {
      description
        "Default output-queue to assign route refreshes to";
      uses bgp-output-queue-priority-class;
    }
    container withdraw-priority {
      description
        "Default output-queue to assign withdrawn routes to";
      uses bgp-output-queue-priority-class;
    }
    leaf advertise-srv6-service {
      type empty;
      description
        "Advertise SRv6 service";
    }
    leaf accept-srv6-service {
      type empty;
      description
        "Accept SRv6 service";
    }
    leaf-list import {
      type jt:policy-algebra;
      ordered-by user;
      description
        "Import policy";
    }
    leaf-list export {
      type jt:policy-algebra;
      ordered-by user;
      description
        "Export policy";
    }
    container aggregate-label {
      presence "enable aggregate-label";
      description
        "Aggregate labels of incoming routes with the same FEC";
      uses apply-advanced;
      leaf community {
        type string;
        mandatory true;
        description
          "Community to identify the FEC of incoming routes";
      }
    }
  }

  grouping bgp-afi-vpn-protection {
    uses apply-advanced;
    container prefix-limit {
      description
        "Limit maximum number of prefixes from a peer";
      uses bgpaf-prefix-limit;
    }
    container accepted-prefix-limit {
      description
        "Limit maximum number of prefixes accepted from a peer";
      uses bgpaf-accepted-prefix-limit;
    }
    container rib-group {
      description
        "Routing table group";
      uses rib_group_inet_type;
    }
    container add-path {
      description
        "Advertise multiple paths to peer";
      uses apath-options;
    }
    container aigp {
      presence "enable aigp";
      description
        "Allow sending and receiving of AIGP attribute";
      uses bgpaf-aigp-options;
    }
    leaf damping {
      type empty;
      description
        "Enable route flap damping";
    }
    leaf local-ipv4-address {
      type jt:ipv4addr;
      description
        "Local IPv4 address";
    }
    container loops {
      description
        "Allow local AS in received AS paths";
      uses bgpaf-loops;
    }
    container delay-route-advertisements {
      presence "enable delay-route-advertisements";
      description
        "Delay route updates for this family until FIB-sync";
      uses apply-advanced;
      leaf always-wait-for-krt-drain {
        type empty;
        description
          "Wait for KRT-queue drain for more-specific prefixes";
      }
      container minimum-delay {
        description
          "Minimum-delay to ensure KRT sees the route flash";
        uses apply-advanced;
        leaf routing-uptime {
          type union {
            type string {
              pattern "<.*>|$.*";
            }
            type uint32 {
              range "1 .. 36000";
            }
          }
          description
            "Min delay(sec) advertisement after RPD start";
        }
        leaf inbound-convergence {
          type union {
            type string {
              pattern "<.*>|$.*";
            }
            type uint32 {
              range "1 .. 36000";
            }
          }
          description
            "Min delay(sec) advertisement after source-peer sent all routes";
        }
      }
      container maximum-delay {
        description
          "Maximum delay deferring routes";
        uses apply-advanced;
        leaf route-age {
          type union {
            type string {
              pattern "<.*>|$.*";
            }
            type uint32 {
              range "1 .. 36000";
            }
          }
          description
            "Max delay(sec) advertisement route age";
        }
        leaf routing-uptime {
          type union {
            type string {
              pattern "<.*>|$.*";
            }
            type uint32 {
              range "1 .. 36000";
            }
          }
          description
            "Max delay(sec) advertisement after RPD start";
        }
      }
    }
    container nexthop-resolution {
      description
        "Configure nexthop resolution properties";
      uses apply-advanced;
      leaf no-resolution {
        type empty;
        description
          "Consider nexthop good without resolution attempt";
      }
      leaf preserve-nexthop-hierarchy {
        type empty;
        description
          "Attempt preserving resolved nexthop chain in forwarding";
      }
    }
    container defer-initial-multipath-build {
      presence "enable defer-initial-multipath-build";
      description
        "Defer initial multipath build until EOR is received";
      uses apply-advanced;
      leaf maximum-delay {
        type union {
          type string {
            pattern "<.*>|$.*";
          }
          type uint32 {
            range "1 .. 3600";
          }
        }
        description
          "Max delay(sec) multipath build after peer is up";
      }
    }
    container graceful-restart {
      description
        "BGP graceful restart options";
      uses bgp-af-gr;
    }
    leaf extended-nexthop {
      type empty;
      description
        "Extended nexthop encoding";
    }
    leaf extended-nexthop-color {
      type empty;
      description
        "Resolve using extended color nexthop";
    }
    leaf extended-nexthop-tunnel {
      type empty;
      description
        "Use BGP tunnel attribute";
    }
    leaf no-install {
      type empty;
      description
        "Dont install received routes in forwarding";
    }
    leaf route-age-bgp-view {
      type empty;
      description
        "Maintain BGP route's age based on Update messages only";
    }
    container output-queue-priority {
      description
        "Default output-queue to assign updates to";
      uses bgp-output-queue-priority-class;
    }
    container route-refresh-priority {
      description
        "Default output-queue to assign route refreshes to";
      uses bgp-output-queue-priority-class;
    }
    container withdraw-priority {
      description
        "Default output-queue to assign withdrawn routes to";
      uses bgp-output-queue-priority-class;
    }
    leaf advertise-srv6-service {
      type empty;
      description
        "Advertise SRv6 service";
    }
    leaf accept-srv6-service {
      type empty;
      description
        "Accept SRv6 service";
    }
    leaf-list import {
      type jt:policy-algebra;
      ordered-by user;
      description
        "Import policy";
    }
    leaf-list export {
      type jt:policy-algebra;
      ordered-by user;
      description
        "Export policy";
    }
    container aggregate-label {
      presence "enable aggregate-label";
      description
        "Aggregate labels of incoming routes with the same FEC";
      uses apply-advanced;
      leaf community {
        type string;
        mandatory true;
        description
          "Community to identify the FEC of incoming routes";
      }
    }
    container egress-protection {
      presence "enable egress-protection";
      description
        "Egress router protection";
      uses apply-advanced;
      container context-identifier {
        description
          "Context identifier";
        uses apply-advanced;
        leaf context-id {
          type jt:ipv4addr;
          description
            "IP address";
        }
      }
      leaf-list keep-import {
        type jt:policy-algebra;
        ordered-by user;
        description
          "Import policy";
      }
    }
  }

  grouping bgp-output-queue-priority-class {
    choice class {
      case case_1 {
        leaf priority {
          type union {
            type string {
              pattern "<.*>|$.*";
            }
            type uint32 {
              range "1 .. 16";
            }
          }
          description
            "Output queue priority; higher is better";
        }
      }
      case case_2 {
        leaf expedited {
          type empty;
          description
            "Expedited queue; highest priority";
        }
      }
    }
  }

  grouping bgp_filter_obj {
    description
      "Filter to apply to tracing";
    leaf match-on {
      type enumeration {
        enum "prefix" {
          description
            "Filter based on prefix";
        }
      }
      mandatory true;
      description
        "Argument on which to match";
    }
    leaf-list policy {
      type jt:policy-algebra;
      ordered-by user;
      description
        "Filter policy";
    }
  }

  grouping bgpaf-accepted-prefix-limit {
    uses apply-advanced;
    leaf maximum {
      type union {
        type string {
          pattern "<.*>|$.*";
        }
        type uint32 {
          range "1 .. 4294967295";
        }
      }
      description
        "Maximum number of prefixes accepted from a peer";
    }
    container teardown {
      presence "enable teardown";
      description
        "Clear peer connection on reaching limit";
      uses apply-advanced;
      leaf limit-threshold {
        type union {
          type string {
            pattern "<.*>|$.*";
          }
          type uint32 {
            range "1 .. 100";
          }
        }
        description
          "Percentage of prefix-limit to start warnings";
      }
      container idle-timeout {
        presence "enable idle-timeout";
        description
          "Timeout before attempting to restart peer";
        choice idle-parm {
          case case_1 {
            leaf forever {
              type empty;
              description
                "Idle the peer until the user intervenes";
            }
          }
          case case_2 {
            leaf timeout {
              type union {
                type string {
                  pattern "<.*>|$.*";
                }
                type uint32 {
                  range "1 .. 2400";
                }
              }
              description
                "Timeout value, in minutes, for restarting peer";
            }
          }
        }
      }
    }
    container drop-excess {
      presence "enable drop-excess";
      description
        "Drop routes from peer on reaching limit";
      uses apply-advanced;
      leaf limit-threshold {
        type union {
          type string {
            pattern "<.*>|$.*";
          }
          type uint32 {
            range "1 .. 100";
          }
        }
        description
          "Percentage of prefix-limit to start warnings";
      }
    }
    container hide-excess {
      presence "enable hide-excess";
      description
        "Hide routes from peer on reaching limit";
      uses apply-advanced;
      leaf limit-threshold {
        type union {
          type string {
            pattern "<.*>|$.*";
          }
          type uint32 {
            range "1 .. 100";
          }
        }
        description
          "Percentage of prefix-limit to start warnings";
      }
    }
  }

  grouping bgpaf-aigp-options {
    uses apply-advanced;
    leaf disable {
      type empty;
      description
        "Disable sending and receiving of AIGP attribute";
    }
  }

  grouping bgpaf-loops {
    uses apply-advanced;
    leaf loops {
      type union {
        type string {
          pattern "<.*>|$.*";
        }
        type int32 {
          range "1 .. 10";
        }
      }
      description
        "AS-Path loop count";
    }
  }

  grouping bgpaf-prefix-limit {
    uses apply-advanced;
    leaf maximum {
      type union {
        type string {
          pattern "<.*>|$.*";
        }
        type uint32 {
          range "1 .. 4294967295";
        }
      }
      description
        "Maximum number of prefixes from a peer";
    }
    container teardown {
      presence "enable teardown";
      description
        "Clear peer connection on reaching limit";
      uses apply-advanced;
      leaf limit-threshold {
        type union {
          type string {
            pattern "<.*>|$.*";
          }
          type uint32 {
            range "1 .. 100";
          }
        }
        description
          "Percentage of prefix-limit to start warnings";
      }
      container idle-timeout {
        presence "enable idle-timeout";
        description
          "Timeout before attempting to restart peer";
        choice idle-parm {
          case case_1 {
            leaf forever {
              type empty;
              description
                "Idle the peer until the user intervenes";
            }
          }
          case case_2 {
            leaf timeout {
              type union {
                type string {
                  pattern "<.*>|$.*";
                }
                type uint32 {
                  range "1 .. 2400";
                }
              }
              description
                "Timeout value, in minutes, for restarting peer";
            }
          }
        }
      }
    }
    container drop-excess {
      presence "enable drop-excess";
      description
        "Drop routes from peer on reaching limit";
      uses apply-advanced;
      leaf limit-threshold {
        type union {
          type string {
            pattern "<.*>|$.*";
          }
          type uint32 {
            range "1 .. 100";
          }
        }
        description
          "Percentage of prefix-limit to start warnings";
      }
    }
    container hide-excess {
      presence "enable hide-excess";
      description
        "Hide routes from peer on reaching limit";
      uses apply-advanced;
      leaf limit-threshold {
        type union {
          type string {
            pattern "<.*>|$.*";
          }
          type uint32 {
            range "1 .. 100";
          }
        }
        description
          "Percentage of prefix-limit to start warnings";
      }
    }
  }

  grouping bgpaf-traffic-statistics {
    uses apply-advanced;
    leaf labeled-path {
      type empty;
      description
        "Ingress labeled path statistics";
    }
    container file {
      description
        "Statistics file options";
      leaf filename {
        type string {
          length "1 .. 1024";
        }
        description
          "Name of file in which to write trace information";
      }
      leaf replace {
        type empty;
        status deprecated;
        description
          "Replace trace file rather than appending to it";
      }
      leaf size {
        type string;
        description
          "Maximum trace file size";
      }
      leaf files {
        type union {
          type string {
            pattern "<.*>|$.*";
          }
          type uint32 {
            range "2 .. 1000";
          }
        }
        default "10";
        description
          "Maximum number of trace files";
      }
      leaf no-stamp {
        type empty;
        status deprecated;
        description
          "Do not timestamp trace file";
      }
      choice world-readable-choice {
        leaf world-readable {
          type empty;
          description
            "Allow any user to read the log file";
        }
        leaf no-world-readable {
          type empty;
          description
            "Don't allow any user to read the log file";
        }
      }
    }
    leaf interval {
      type union {
        type string {
          pattern "<.*>|$.*";
        }
        type int32 {
          range "60 .. 65535";
        }
      }
      description
        "Time to collect statistics (seconds)";
    }
  }

  grouping juniper-protocols-isis {
    uses apply-advanced;
    list interface {
      key "name";
      description
        "Interface configuration";
      leaf name {
        type union {
          type jt:interface-name;
          type string {
            pattern "<.*>|$.*";
          }
        }
        description
          "Interface name";
      }
      uses apply-advanced;
      container ldp-synchronization {
        presence "enable ldp-synchronization";
        description
          "Advertise maximum metric until LDP is operational";
        uses ldp-sync-obj;
      }
      list level {
        key "name";
        ordered-by user;
        description
          "Configure levels on this interface";
        leaf name {
          type union {
            type string {
              pattern "<.*>|$.*";
            }
            type uint32 {
              range "1 .. 2";
            }
          }
          description
            "IS-IS level number";
        }
        uses apply-advanced;
        leaf te-metric {
          type union {
            type string {
              pattern "<.*>|$.*";
            }
            type uint32 {
              range "0 .. 16777215";
            }
          }
          description
            "Traffic engineering metric";
        }
        leaf no-advertise-adjacency-segment {
          type empty;
          description
            "Do not advertise an adjacency segment for this level";
        }
        container ipv4-adjacency-segment {
          description
            "Configure ipv4 adjacency segment";
          uses apply-advanced;
          container protected {
            description
              "Adjacency SID is eligible for protection";
            choice adjsid-type {
              case case_1 {
                container index {
                  description
                    "Adjacency SID indexed from SRGB";
                  leaf index-number {
                    type union {
                      type string {
                        pattern "<.*>|$.*";
                      }
                      type uint32 {
                        range "0 .. 1048575";
                      }
                    }
                  }
                }
              }
              case case_2 {
                leaf label {
                  type union {
                    type string {
                      pattern "<.*>|$.*";
                    }
                    type uint32 {
                      range "16 .. 1048575";
                    }
                  }
                  description
                    "Adjacency SID from static label pool";
                }
              }
              case case_3 {
                leaf dynamic {
                  type empty;
                  description
                    "Dynamically allocate an adjacency segment";
                }
              }
            }
          }
          container unprotected {
            description
              "Adjacency SID uneligible for protection";
            choice adjsid-type {
              case case_1 {
                container index {
                  description
                    "Adjacency SID indexed from SRGB";
                  leaf index-number {
                    type union {
                      type string {
                        pattern "<.*>|$.*";
                      }
                      type uint32 {
                        range "0 .. 1048575";
                      }
                    }
                  }
                }
              }
              case case_2 {
                leaf label {
                  type union {
                    type string {
                      pattern "<.*>|$.*";
                    }
                    type uint32 {
                      range "16 .. 1048575";
                    }
                  }
                  description
                    "Adjacency SID from static label pool";
                }
              }
              case case_3 {
                leaf dynamic {
                  type empty;
                  description
                    "Dynamically allocate an adjacency segment";
                }
              }
            }
          }
        }
        container ipv6-adjacency-segment {
          description
            "Configure ipv6 adjacency segment";
          uses apply-advanced;
          container protected {
            description
              "Adjacency SID is eligible for protection";
            choice adjsid-type {
              case case_1 {
                container index {
                  description
                    "Adjacency SID indexed from SRGB";
                  leaf index-number {
                    type union {
                      type string {
                        pattern "<.*>|$.*";
                      }
                      type uint32 {
                        range "0 .. 1048575";
                      }
                    }
                  }
                }
              }
              case case_2 {
                leaf label {
                  type union {
                    type string {
                      pattern "<.*>|$.*";
                    }
                    type uint32 {
                      range "16 .. 1048575";
                    }
                  }
                  description
                    "Adjacency SID from static label pool";
                }
              }
              case case_3 {
                leaf dynamic {
                  type empty;
                  description
                    "Dynamically allocate an adjacency segment";
                }
              }
            }
          }
          container unprotected {
            description
              "Adjacency SID uneligible for protection";
            choice adjsid-type {
              case case_1 {
                container index {
                  description
                    "Adjacency SID indexed from SRGB";
                  leaf index-number {
                    type union {
                      type string {
                        pattern "<.*>|$.*";
                      }
                      type uint32 {
                        range "0 .. 1048575";
                      }
                    }
                  }
                }
              }
              case case_2 {
                leaf label {
                  type union {
                    type string {
                      pattern "<.*>|$.*";
                    }
                    type uint32 {
                      range "16 .. 1048575";
                    }
                  }
                  description
                    "Adjacency SID from static label pool";
                }
              }
              case case_3 {
                leaf dynamic {
                  type empty;
                  description
                    "Dynamically allocate an adjacency segment";
                }
              }
            }
          }
        }
        container srv6-adjacency-segment {
          description
            "Configure srv6 adjacency segment";
          uses apply-advanced;
          container unprotected {
            presence "enable unprotected";
            description
              "SRv6 Adjacency segment is uneligible for protection";
            uses apply-advanced;
            list locator {
              key "name";
              ordered-by user;
              description
                "Locator to bind SRv6 adjacency segment";
              leaf name {
                type string;
                mandatory true;
                description
                  "Locator name";
              }
              uses apply-advanced;
              list end-x-sid {
                key "name";
                ordered-by user;
                description
                  "Endpoint 128 bit address";
                leaf name {
                  type jt:ipv6addr;
                }
                uses apply-advanced;
              }
              container micro-adjacency-sid {
                presence "enable micro-adjacency-sid";
                description
                  "Micro-adjacency-SID";
                uses apply-advanced;
                leaf static-sid {
                  type union {
                    type uint32;
                    type string {
                      pattern "<.*>|$.*";
                    }
                  }
                  description
                    "Static micro-adjacency-SID";
                }
              }
              container dynamic-end-x-sid {
                presence "enable dynamic-end-x-sid";
                description
                  "Allocate end-x-SID dynamically";
                uses apply-advanced;
                container flavor {
                  presence "enable flavor";
                  description
                    "Configure end-x-SID flavor";
                  uses apply-advanced;
                  leaf psp {
                    type empty;
                    description
                      "Penultimate segment pop of the SRH";
                  }
                  leaf usp {
                    type empty;
                    description
                      "Ultimate segment pop of the SRH";
                  }
                  leaf usd {
                    type empty;
                    description
                      "Ultimate segment decapsulation";
                  }
                }
              }
            }
          }
        }
        list lan-neighbor {
          key "name";
          ordered-by user;
          description
            "Configuration specific to a LAN neighbor";
          leaf name {
            type jt:sysid;
            description
              "Neighbor's sysid";
          }
          uses apply-advanced;
          container ipv4-adjacency-segment {
            description
              "Configure ipv4 adjacency segment";
            uses apply-advanced;
            container protected {
              description
                "Adjacency SID is eligible for protection";
              choice adjsid-type {
                case case_1 {
                  container index {
                    description
                      "Adjacency SID indexed from SRGB";
                    leaf index-number {
                      type union {
                        type string {
                          pattern "<.*>|$.*";
                        }
                        type uint32 {
                          range "0 .. 1048575";
                        }
                      }
                    }
                  }
                }
                case case_2 {
                  leaf label {
                    type union {
                      type string {
                        pattern "<.*>|$.*";
                      }
                      type uint32 {
                        range "16 .. 1048575";
                      }
                    }
                    description
                      "Adjacency SID from static label pool";
                  }
                }
                case case_3 {
                  leaf dynamic {
                    type empty;
                    description
                      "Dynamically allocate an adjacency segment";
                  }
                }
              }
            }
            container unprotected {
              description
                "Adjacency SID uneligible for protection";
              choice adjsid-type {
                case case_1 {
                  container index {
                    description
                      "Adjacency SID indexed from SRGB";
                    leaf index-number {
                      type union {
                        type string {
                          pattern "<.*>|$.*";
                        }
                        type uint32 {
                          range "0 .. 1048575";
                        }
                      }
                    }
                  }
                }
                case case_2 {
                  leaf label {
                    type union {
                      type string {
                        pattern "<.*>|$.*";
                      }
                      type uint32 {
                        range "16 .. 1048575";
                      }
                    }
                    description
                      "Adjacency SID from static label pool";
                  }
                }
                case case_3 {
                  leaf dynamic {
                    type empty;
                    description
                      "Dynamically allocate an adjacency segment";
                  }
                }
              }
            }
          }
          container ipv6-adjacency-segment {
            description
              "Configure ipv6 adjacency segment";
            uses apply-advanced;
            container protected {
              description
                "Adjacency SID is eligible for protection";
              choice adjsid-type {
                case case_1 {
                  container index {
                    description
                      "Adjacency SID indexed from SRGB";
                    leaf index-number {
                      type union {
                        type string {
                          pattern "<.*>|$.*";
                        }
                        type uint32 {
                          range "0 .. 1048575";
                        }
                      }
                    }
                  }
                }
                case case_2 {
                  leaf label {
                    type union {
                      type string {
                        pattern "<.*>|$.*";
                      }
                      type uint32 {
                        range "16 .. 1048575";
                      }
                    }
                    description
                      "Adjacency SID from static label pool";
                  }
                }
                case case_3 {
                  leaf dynamic {
                    type empty;
                    description
                      "Dynamically allocate an adjacency segment";
                  }
                }
              }
            }
            container unprotected {
              description
                "Adjacency SID uneligible for protection";
              choice adjsid-type {
                case case_1 {
                  container index {
                    description
                      "Adjacency SID indexed from SRGB";
                    leaf index-number {
                      type union {
                        type string {
                          pattern "<.*>|$.*";
                        }
                        type uint32 {
                          range "0 .. 1048575";
                        }
                      }
                    }
                  }
                }
                case case_2 {
                  leaf label {
                    type union {
                      type string {
                        pattern "<.*>|$.*";
                      }
                      type uint32 {
                        range "16 .. 1048575";
                      }
                    }
                    description
                      "Adjacency SID from static label pool";
                  }
                }
                case case_3 {
                  leaf dynamic {
                    type empty;
                    description
                      "Dynamically allocate an adjacency segment";
                  }
                }
              }
            }
          }
          container srv6-adjacency-segment {
            description
              "Configure srv6 adjacency segment";
            uses apply-advanced;
            container unprotected {
              presence "enable unprotected";
              description
                "SRv6 Adjacency segment is uneligible for protection";
              uses apply-advanced;
              list locator {
                key "name";
                ordered-by user;
                description
                  "Locator to bind SRv6 adjacency segment";
                leaf name {
                  type string;
                  mandatory true;
                  description
                    "Locator name";
                }
                uses apply-advanced;
                list end-x-sid {
                  key "name";
                  ordered-by user;
                  description
                    "Endpoint 128 bit address";
                  leaf name {
                    type jt:ipv6addr;
                  }
                  uses apply-advanced;
                  container flavor {
                    presence "enable flavor";
                    description
                      "Configure end-x-SID flavor";
                    uses apply-advanced;
                    leaf psp {
                      type empty;
                      description
                        "Penultimate segment pop of the SRH";
                    }
                    leaf usp {
                      type empty;
                      description
                        "Ultimate segment pop of the SRH";
                    }
                    leaf usd {
                      type empty;
                      description
                        "Ultimate segment decapsulation";
                    }
                  }
                }
                container micro-adjacency-sid {
                  presence "enable micro-adjacency-sid";
                  description
                    "Micro-adjacency-SID";
                  uses apply-advanced;
                  leaf static-sid {
                    type union {
                      type uint32;
                      type string {
                        pattern "<.*>|$.*";
                      }
                    }
                    description
                      "Static micro-adjacency-SID";
                  }
                }
                container dynamic-end-x-sid {
                  presence "enable dynamic-end-x-sid";
                  description
                    "Allocate end-x-SID dynamically";
                  uses apply-advanced;
                  container flavor {
                    presence "enable flavor";
                    description
                      "Configure end-x-SID flavor";
                    uses apply-advanced;
                    leaf psp {
                      type empty;
                      description
                        "Penultimate segment pop of the SRH";
                    }
                    leaf usp {
                      type empty;
                      description
                        "Ultimate segment pop of the SRH";
                    }
                    leaf usd {
                      type empty;
                      description
                        "Ultimate segment decapsulation";
                    }
                  }
                }
              }
            }
          }
        }
        container post-convergence-lfa {
          presence "enable post-convergence-lfa";
          description
            "Configure backup along post convergence on this interface";
          uses apply-advanced;
        }
        choice enable-disable {
          case case_1 {
            leaf disable {
              type empty;
              description
                "Disable IS-IS for this level";
            }
          }
        }
        leaf metric {
          type union {
            type string {
              pattern "<.*>|$.*";
            }
            type uint32 {
              range "0 .. 16777215";
            }
          }
          description
            "Metric for this level";
        }
        leaf ipv4-multicast-metric {
          type union {
            type string {
              pattern "<.*>|$.*";
            }
            type uint32 {
              range "0 .. 16777215";
            }
          }
          description
            "IPv4 multicast metric for this level";
        }
        leaf ipv6-unicast-metric {
          type union {
            type string {
              pattern "<.*>|$.*";
            }
            type uint32 {
              range "0 .. 16777215";
            }
          }
          description
            "IPv6 unicast metric for this level";
        }
        leaf ipv6-multicast-metric {
          type union {
            type string {
              pattern "<.*>|$.*";
            }
            type uint32 {
              range "0 .. 16777215";
            }
          }
          description
            "IPv6 multicast metric for this level";
        }
        list topology {
          key "name";
          ordered-by user;
          description
            "Topology specific attributes";
          leaf name {
            type enumeration {
              enum "default" {
                description
                  "Default topology";
              }
              enum "ipv4-multicast" {
                description
                  "IPv4 multicast topology";
              }
              enum "ipv6-unicast" {
                description
                  "IPv6 unicast topology";
              }
              enum "ipv6-multicast" {
                description
                  "IPv6 multicast topology";
              }
            }
            description
              "Topology name";
          }
          uses apply-advanced;
          leaf metric {
            type union {
              type string {
                pattern "<.*>|$.*";
              }
              type uint32 {
                range "0 .. 16777215";
              }
            }
            description
              "Topology metric";
          }
          container bandwidth-based-metrics {
            description
              "Configure bandwidth based metrics";
            uses apply-advanced;
            list bandwidth {
              key "name";
              description
                "Bandwidth threshold";
              leaf name {
                type string;
              }
              leaf metric {
                type union {
                  type string {
                    pattern "<.*>|$.*";
                  }
                  type uint32 {
                    range "0 .. 16777215";
                  }
                }
                mandatory true;
                description
                  "Metric associated with specified bandwidth";
              }
            }
          }
        }
        leaf authentication-key {
          type jt:unreadable;
          status deprecated;
          description
            "Authentication key (password)";
        }
        leaf authentication-type {
          type enumeration {
            enum "md5" {
              status deprecated;
              description
                "MD5 authentication";
            }
            enum "simple" {
              status deprecated;
              description
                "Simple password authentication";
            }
          }
          status deprecated;
          description
            "Authentication type";
        }
        leaf hello-authentication-key {
          type jt:unreadable;
          description
            "Authentication key (password) for hello packets";
        }
        leaf hello-authentication-type {
          type enumeration {
            enum "md5" {
              description
                "MD5 authentication";
            }
            enum "simple" {
              description
                "Simple password authentication";
            }
          }
          description
            "Authentication type for hello packets";
        }
        leaf hello-authentication-key-chain {
          type string {
            length "1 .. 128";
          }
          description
            "Key chain name";
        }
        leaf hello-interval {
          type union {
            type string {
              pattern "<.*>|$.*";
            }
            type uint32 {
              range "1 .. 21845";
            }
          }
          units "seconds";
          description
            "Interval between hello packet transmissions";
        }
        leaf hold-time {
          type union {
            type string {
              pattern "<.*>|$.*";
            }
            type uint32 {
              range "1 .. 65535";
            }
          }
          units "seconds";
          description
            "Time after which neighbors think the interface is down";
        }
        leaf priority {
          type union {
            type string {
              pattern "<.*>|$.*";
            }
            type uint32 {
              range "0 .. 127";
            }
          }
          description
            "Designated router election priority";
        }
        container flood-reflector {
          presence "enable flood-reflector";
          description
            "Configure interface as flood-reflector";
          uses apply-advanced;
          leaf cluster-id {
            type union {
              type string {
                pattern "<.*>|$.*";
              }
              type uint32 {
                range "1 .. 4294967295";
              }
            }
            description
              "Cluster-ID";
          }
        }
        container passive {
          presence "enable passive";
          description
            "Do not run IS-IS at this level, but advertise it";
          uses apply-advanced;
          leaf remote-node-iso {
            type jt:sysid;
            description
              "ISO System-ID of the remote node";
          }
          leaf remote-node-id {
            type jt:ipv4addr;
            description
              "Remote address of the link";
          }
        }
        leaf strict-bfd-old {
          type empty;
          description
            "Enable strict bfd over this interface";
        }
      }
      leaf delay-metric {
        type union {
          type string {
            pattern "<.*>|$.*";
          }
          type uint32 {
            range "0 .. 16777215";
          }
        }
        units "microseconds";
        description
          "Delay metric";
      }
      container delay-measurement {
        presence "enable delay-measurement";
        description
          "Enable delay measurement";
        uses apply-advanced;
        leaf probe-interval {
          type union {
            type string {
              pattern "<.*>|$.*";
            }
            type uint32 {
              range "1 .. 255";
            }
          }
          units "seconds";
          description
            "Probe interval";
        }
        leaf probe-count {
          type union {
            type string {
              pattern "<.*>|$.*";
            }
            type uint32 {
              range "1 .. 15";
            }
          }
          description
            "Probe count";
        }
        container normalize {
          description
            "Normalize Measured Link Delay";
          leaf interval {
            type union {
              type string {
                pattern "<.*>|$.*";
              }
              type uint32 {
                range "1 .. 5000000";
              }
            }
            units "microseconds";
            mandatory true;
            description
              "The value of the normalized interval in microseconds.";
          }
          leaf offset {
            type union {
              type string {
                pattern "<.*>|$.*";
              }
              type uint32 {
                range "1 .. 5000000";
              }
            }
            units "microseconds";
            mandatory true;
            description
              "The value of the normalized offset in microseconds (Must be < normalized interval).";
          }
        }
        container advertisement {
          description
            "Delay advertisement";
          uses apply-advanced;
          container periodic {
            description
              "Periodic advertisement parameters";
            uses apply-advanced;
            leaf threshold {
              type union {
                type string {
                  pattern "<.*>|$.*";
                }
                type uint32 {
                  range "0 .. 100";
                }
              }
              units "percentage";
              description
                "Threshold";
            }
            leaf interval {
              type union {
                type string {
                  pattern "<.*>|$.*";
                }
                type uint32 {
                  range "30 .. 3600";
                }
              }
              units "seconds";
              description
                "Interval";
            }
          }
          container accelerated {
            presence "enable accelerated";
            description
              "Accelerated advertisement parameters";
            uses apply-advanced;
            leaf threshold {
              type union {
                type string {
                  pattern "<.*>|$.*";
                }
                type uint32 {
                  range "0 .. 100";
                }
              }
              units "percentage";
              description
                "Threshold";
            }
          }
        }
      }
      leaf no-advertise-adjacency-segment {
        type empty;
        description
          "Do not advertise an adjacency segment for this interface";
      }
      choice protection-type {
        case case_1 {
          leaf link-protection {
            type empty;
            description
              "Protect interface from link faults only";
          }
        }
        case case_2 {
          leaf node-link-protection {
            type empty;
            description
              "Protect interface from both link and node faults";
          }
        }
      }
      leaf no-eligible-backup {
        type empty;
        description
          "Not eligible for backup traffic from protected interfaces";
      }
      leaf no-eligible-remote-backup {
        type empty;
        description
          "Not eligible for Remote-LFA backup traffic from protected interfaces";
      }
      container link-degradation-threshold {
        presence "enable link-degradation-threshold";
        description
          "Link up and down thresholds (in %) for proactive link protection";
        leaf link-down {
          type union {
            type string {
              pattern "<.*>|$.*";
            }
            type uint32 {
              range "0 .. 100";
            }
          }
          mandatory true;
          description
            "Signal degradation threshold above which link marked down";
        }
        leaf link-up {
          type union {
            type string {
              pattern "<.*>|$.*";
            }
            type uint32 {
              range "0 .. 100";
            }
          }
          mandatory true;
          description
            "Signal degradation threshold below which link is marked up.";
        }
      }
      choice enable-disable {
        case case_1 {
          leaf disable {
            type empty;
            description
              "Disable IS-IS on this interface";
          }
        }
      }
      leaf authentication-key {
        type jt:unreadable;
        status deprecated;
        description
          "Authentication key (password)";
      }
      leaf authentication-type {
        type enumeration {
          enum "md5" {
            status deprecated;
            description
              "MD5 authentication";
          }
          enum "simple" {
            status deprecated;
            description
              "Simple password authentication";
          }
        }
        status deprecated;
        description
          "Authentication type";
      }
      leaf flood-group {
        type string;
        description
          "ISO Area that this interface should send LSPs to";
      }
      leaf hello-authentication-key {
        type jt:unreadable;
        status deprecated;
        description
          "Authentication key (password) for hello packets";
      }
      leaf hello-authentication-type {
        type enumeration {
          enum "md5" {
            status deprecated;
            description
              "MD5 authentication";
          }
          enum "simple" {
            status deprecated;
            description
              "Simple password authentication";
          }
        }
        status deprecated;
        description
          "Authentication type for hello packets";
      }
      leaf hello-padding-type {
        type enumeration {
          enum "strict" {
            description
              "Padding for all adjacency states";
          }
          enum "adaptive" {
            description
              "Padding until state of neighbor adjacency is 'up'";
          }
          enum "loose" {
            description
              "Padding until state of adjacency is 'initializing'";
          }
          enum "disable" {
            description
              "Do not add any padding for hello packets";
          }
        }
        default "loose";
        description
          "Type of padding for hello packets";
      }
      leaf interface-group-holddown-delay {
        type union {
          type string {
            pattern "<.*>|$.*";
          }
          type uint32 {
            range "0 .. 60";
          }
        }
        units "seconds";
        description
          "Time to wait before including in BBM calculation";
      }
      leaf max-hello-size {
        type union {
          type string {
            pattern "<.*>|$.*";
          }
          type uint32 {
            range "512 .. 16000";
          }
        }
        description
          "Maximum size allowed for ISIS Hello PDUs";
      }
      leaf lsp-interval {
        type union {
          type string {
            pattern "<.*>|$.*";
          }
          type uint32 {
            range "1 .. 1000";
          }
        }
        units "milliseconds";
        default "100";
        description
          "Interval between LSP transmissions";
      }
      container csnp-interval {
        description
          "Rate of CSN packets (for LAN interfaces only)";
        choice csnp_interval_option {
          case case_1 {
            leaf csnp-interval-number {
              type union {
                type string {
                  pattern "<.*>|$.*";
                }
                type uint32 {
                  range "1 .. 65535";
                }
              }
              units "seconds";
              description
                "Interval between CSN packets";
            }
          }
          case case_2 {
            leaf disable {
              type empty;
              description
                "Do not send CSN packets on this interface";
            }
          }
        }
      }
      container strict-dual-isis {
        presence "enable strict-dual-isis";
        description
          "Enable dual isis if spf computation is required for both ipv4 and ipv6 family";
        uses apply-advanced;
        leaf holdown {
          type union {
            type string {
              pattern "<.*>|$.*";
            }
            type uint32 {
              range "1 .. 65535";
            }
          }
          default "12";
          status deprecated;
          description
            "Time to wait for ipv4 and ipv6 connectivity";
        }
        leaf holddown {
          type union {
            type string {
              pattern "<.*>|$.*";
            }
            type uint32 {
              range "1 .. 65535";
            }
          }
          default "12";
          description
            "Time to wait for ipv4 and ipv6 connectivity";
        }
      }
      container mesh-group {
        description
          "Add the interface to a mesh group";
        choice mesh_group_option {
          case case_1 {
            leaf mesh-group-number {
              type union {
                type uint32;
                type string {
                  pattern "<.*>|$.*";
                }
              }
              description
                "Mesh group number for this interface";
            }
          }
          case case_2 {
            leaf blocked {
              type empty;
              description
                "Do not flood new LSPs on this interface";
            }
          }
        }
      }
      leaf point-to-point {
        type empty;
        description
          "Treat interface as point to point";
      }
      container passive {
        presence "enable passive";
        description
          "Do not run IS-IS, but advertise it";
        uses apply-advanced;
        leaf remote-node-iso {
          type jt:sysid;
          description
            "ISO System-ID of the remote node";
        }
        leaf remote-node-id {
          type jt:ipv4addr;
          description
            "Remote address of the link";
        }
      }
      leaf checksum {
        type empty;
        description
          "Enable checksum for packets on this interface";
      }
      leaf no-unicast-topology {
        type empty;
        description
          "Do not include this interface in the unicast topology";
      }
      leaf no-ipv4-multicast {
        type empty;
        description
          "Do not include this interface in the IPv4 multicast topology";
      }
      leaf no-ipv6-unicast {
        type empty;
        description
          "Do not include this interface in the IPv6 unicast topology";
      }
      leaf no-ipv6-multicast {
        type empty;
        description
          "Do not include this interface in the IPv6 multicast topology";
      }
      leaf no-adjacency-down-notification {
        type empty;
        description
          "Do not inform other protocols about adjacency down events";
      }
      container bfd-liveness-detection {
        status deprecated;
        description
          "Bidirectional Forwarding Detection options";
        uses apply-advanced;
        leaf version {
          type enumeration {
            enum "0" {
              description
                "BFD version 0 (deprecated)";
            }
            enum "1" {
              description
                "BFD version 1";
            }
            enum "automatic" {
              description
                "Choose BFD version automatically";
            }
          }
          default "automatic";
          description
            "BFD protocol version number";
        }
        leaf minimum-interval {
          type union {
            type string {
              pattern "<.*>|$.*";
            }
            type uint32 {
              range "1 .. 255000";
            }
          }
          units "milliseconds";
          description
            "Minimum transmit and receive interval";
        }
        leaf minimum-transmit-interval {
          type union {
            type string {
              pattern "<.*>|$.*";
            }
            type uint32 {
              range "1 .. 255000";
            }
          }
          units "milliseconds";
          status deprecated;
          description
            "Minimum transmit interval";
        }
        leaf minimum-receive-interval {
          type union {
            type string {
              pattern "<.*>|$.*";
            }
            type uint32 {
              range "1 .. 255000";
            }
          }
          units "milliseconds";
          description
            "Minimum receive interval";
        }
        leaf multiplier {
          type union {
            type string {
              pattern "<.*>|$.*";
            }
            type uint32 {
              range "1 .. 255";
            }
          }
          default "3";
          description
            "Detection time multiplier";
        }
        leaf inline-disable {
          type empty;
          description
            "Disable inline mode for this BFD session";
        }
        leaf pdu-size {
          type union {
            type string {
              pattern "<.*>|$.*";
            }
            type uint32 {
              range "24 .. 16000";
            }
          }
          default "24";
          description
            "BFD transport protocol payload size";
        }
        choice adaptation-choice {
          case case_1 {
            leaf no-adaptation {
              type empty;
              description
                "Disable adaptation";
            }
          }
        }
        container transmit-interval {
          description
            "Transmit-interval options";
          uses apply-advanced;
          leaf minimum-interval {
            type union {
              type string {
                pattern "<.*>|$.*";
              }
              type uint32 {
                range "1 .. 255000";
              }
            }
            units "milliseconds";
            description
              "Minimum transmit interval";
          }
          leaf threshold {
            type union {
              type uint32;
              type string {
                pattern "<.*>|$.*";
              }
            }
            units "milliseconds";
            description
              "High transmit interval triggering a trap";
          }
        }
        container detection-time {
          description
            "Detection-time options";
          uses apply-advanced;
          leaf threshold {
            type union {
              type uint32;
              type string {
                pattern "<.*>|$.*";
              }
            }
            units "milliseconds";
            description
              "High detection-time triggering a trap";
          }
        }
        container authentication {
          description
            "Authentication options";
          uses apply-advanced;
          leaf key-chain {
            type string;
            description
              "Key chain name";
          }
          leaf algorithm {
            type enumeration {
              enum "simple-password" {
                description
                  "Simple password";
              }
              enum "keyed-md5" {
                description
                  "Keyed message Digest 5";
              }
              enum "meticulous-keyed-md5" {
                description
                  "Meticulous keyed message Digest 5";
              }
              enum "keyed-sha-1" {
                description
                  "Keyed secure hash algorithm (SHA1) ";
              }
              enum "meticulous-keyed-sha-1" {
                description
                  "Meticulous keyed secure hash algorithm (SHA1) ";
              }
            }
            description
              "Algorithm name";
          }
          leaf loose-check {
            type empty;
            description
              "Verify authentication only if authentication is negotiated";
          }
        }
      }
      list family {
        key "name";
        ordered-by user;
        description
          "Address family specific interface attributes";
        leaf name {
          type enumeration {
            enum "inet" {
              description
                "IPv4 family";
            }
            enum "inet6" {
              description
                "IPv6 family";
            }
          }
        }
        uses apply-advanced;
        container bfd-liveness-detection {
          description
            "Bidirectional Forwarding Detection options";
          uses apply-advanced;
          leaf version {
            type enumeration {
              enum "0" {
                description
                  "BFD version 0 (deprecated)";
              }
              enum "1" {
                description
                  "BFD version 1";
              }
              enum "automatic" {
                description
                  "Choose BFD version automatically";
              }
            }
            default "automatic";
            description
              "BFD protocol version number";
          }
          leaf minimum-interval {
            type union {
              type string {
                pattern "<.*>|$.*";
              }
              type uint32 {
                range "1 .. 255000";
              }
            }
            units "milliseconds";
            description
              "Minimum transmit and receive interval";
          }
          leaf minimum-transmit-interval {
            type union {
              type string {
                pattern "<.*>|$.*";
              }
              type uint32 {
                range "1 .. 255000";
              }
            }
            units "milliseconds";
            status deprecated;
            description
              "Minimum transmit interval";
          }
          leaf minimum-receive-interval {
            type union {
              type string {
                pattern "<.*>|$.*";
              }
              type uint32 {
                range "1 .. 255000";
              }
            }
            units "milliseconds";
            description
              "Minimum receive interval";
          }
          leaf multiplier {
            type union {
              type string {
                pattern "<.*>|$.*";
              }
              type uint32 {
                range "1 .. 255";
              }
            }
            default "3";
            description
              "Detection time multiplier";
          }
          leaf inline-disable {
            type empty;
            description
              "Disable inline mode for this BFD session";
          }
          leaf pdu-size {
            type union {
              type string {
                pattern "<.*>|$.*";
              }
              type uint32 {
                range "24 .. 16000";
              }
            }
            default "24";
            description
              "BFD transport protocol payload size";
          }
          choice adaptation-choice {
            case case_1 {
              leaf no-adaptation {
                type empty;
                description
                  "Disable adaptation";
              }
            }
          }
          container transmit-interval {
            description
              "Transmit-interval options";
            uses apply-advanced;
            leaf minimum-interval {
              type union {
                type string {
                  pattern "<.*>|$.*";
                }
                type uint32 {
                  range "1 .. 255000";
                }
              }
              units "milliseconds";
              description
                "Minimum transmit interval";
            }
            leaf threshold {
              type union {
                type uint32;
                type string {
                  pattern "<.*>|$.*";
                }
              }
              units "milliseconds";
              description
                "High transmit interval triggering a trap";
            }
          }
          container detection-time {
            description
              "Detection-time options";
            uses apply-advanced;
            leaf threshold {
              type union {
                type uint32;
                type string {
                  pattern "<.*>|$.*";
                }
              }
              units "milliseconds";
              description
                "High detection-time triggering a trap";
            }
          }
          container authentication {
            description
              "Authentication options";
            uses apply-advanced;
            leaf key-chain {
              type string;
              description
                "Key chain name";
            }
            leaf algorithm {
              type enumeration {
                enum "simple-password" {
                  description
                    "Simple password";
                }
                enum "keyed-md5" {
                  description
                    "Keyed message Digest 5";
                }
                enum "meticulous-keyed-md5" {
                  description
                    "Meticulous keyed message Digest 5";
                }
                enum "keyed-sha-1" {
                  description
                    "Keyed secure hash algorithm (SHA1) ";
                }
                enum "meticulous-keyed-sha-1" {
                  description
                    "Meticulous keyed secure hash algorithm (SHA1) ";
                }
              }
              description
                "Algorithm name";
            }
            leaf loose-check {
              type empty;
              description
                "Verify authentication only if authentication is negotiated";
            }
          }
          container echo {
            description
              "Echo mode parameters";
            uses apply-advanced;
            leaf minimum-interval {
              type union {
                type string {
                  pattern "<.*>|$.*";
                }
                type uint32 {
                  range "100 .. 255000";
                }
              }
              units "milliseconds";
              description
                "Minimum transmit and receive interval";
            }
          }
          container echo-lite {
            description
              "Echo-lite more parameters";
            uses apply-advanced;
            leaf minimum-interval {
              type union {
                type string {
                  pattern "<.*>|$.*";
                }
                type uint32 {
                  range "100 .. 255000";
                }
              }
              units "milliseconds";
              description
                "Minimum transmit and receive interval";
            }
          }
          leaf holddown-interval {
            type union {
              type string {
                pattern "<.*>|$.*";
              }
              type uint32 {
                range "0 .. 255000";
              }
            }
            units "milliseconds";
            description
              "Time to hold the session-UP notification to the client";
          }
        }
      }
      leaf strict-bfd {
        type empty;
        description
          "Enable strict bfd over this interface";
      }
    }
    list bier-sub-domain {
      key "name";
      description
        "Configuration of bier subdomain";
      leaf name {
        type union {
          type uint8;
          type string {
            pattern "<.*>|$.*";
          }
        }
        description
          "Enable bier subdomain id";
      }
    }
    container prefix-unreachable {
      presence "enable prefix-unreachable";
      description
        "Configure unreachable prefix advertisement parameters";
      uses apply-advanced;
      container originator {
        description
          "Parameters for originating unreachable prefix advertisements";
        uses apply-advanced;
        leaf unplanned-lifetime {
          type union {
            type string {
              pattern "<.*>|$.*";
            }
            type uint32 {
              range "30 .. 65535";
            }
          }
          units "seconds";
          description
            "Lifetime of unplanned UPA";
        }
        leaf metric {
          type union {
            type string {
              pattern "<.*>|$.*";
            }
            type uint32 {
              range "4261412865 .. 4294967295";
            }
          }
          description
            "Metric value of unplanned UPA";
        }
        leaf max-advertisements {
          type union {
            type string {
              pattern "<.*>|$.*";
            }
            type uint32 {
              range "1 .. 10000";
            }
          }
          description
            "Maximum UPAs that can be originated at any point of time";
        }
      }
      leaf use-only-for-leaking {
        type empty;
        description
          "Do not use this UPA route for resolution";
      }
    }
    container source-packet-routing {
      presence "enable source-packet-routing";
      description
        "Enable Source Packet Routing (SPRING)";
      uses apply-advanced;
      container adjacency-segment {
        description
          "Configure attributes for Adjacency Segments in SPRING";
        uses apply-advanced;
        leaf hold-time {
          type union {
            type string {
              pattern "<.*>|$.*";
            }
            type uint32 {
              range "180000 .. 900000";
            }
          }
          description
            "Duration(ms) for which adjacency segments will be retained after isolating from an interface";
        }
      }
      container udp-tunneling {
        description
          "Enable SR over UDP feature";
        uses apply-advanced;
        leaf encapsulation {
          type empty;
          description
            "Enable UDP Tunnel Encapsulation";
        }
        leaf decapsulation {
          type empty;
          description
            "Enable UDP Tunnel decapsulation";
        }
      }
      container srgb {
        description
          "Set the SRGB global block in SPRING";
        leaf start-label {
          type union {
            type string {
              pattern "<.*>|$.*";
            }
            type uint32 {
              range "16 .. 1048575";
            }
          }
          description
            "Start range for SRGB label block";
        }
        leaf index-range {
          type union {
            type string {
              pattern "<.*>|$.*";
            }
            type uint32 {
              range "32 .. 1048559";
            }
          }
          description
            "Index to the SRGB start label block";
        }
      }
      container node-segment {
        description
          "Enable support for Node segments in SPRING";
        uses apply-advanced;
        leaf ipv4-index {
          type union {
            type string {
              pattern "<.*>|$.*";
            }
            type uint32 {
              range "0 .. 1048575";
            }
          }
          description
            "Set IPv4 Node Segment index";
        }
        leaf ipv6-index {
          type union {
            type string {
              pattern "<.*>|$.*";
            }
            type uint32 {
              range "0 .. 1048575";
            }
          }
          description
            "Set IPv6 Node Segment index";
        }
        leaf index-range {
          type union {
            type string {
              pattern "<.*>|$.*";
            }
            type uint32 {
              range "32 .. 16385";
            }
          }
          description
            "Set Range of Node Segment indices allowed";
        }
      }
      leaf-list flex-algorithm {
        type union {
          type string {
            pattern "<.*>|$.*";
          }
          type uint32 {
            range "128 .. 255";
          }
        }
        max-elements 16;
        description
          "Flex-algorithms we would like to participate in";
      }
      leaf use-flex-algorithm-metric-always {
        type empty;
        description
          "Use flex-algo prefix metric whenever available";
      }
      leaf strict-asla-based-flex-algorithm {
        type empty;
        description
          "Flex-Algorithm to ignore links not having ASLA sub-TLVs";
      }
      leaf new-capability-subtlv {
        type empty;
        description
          "Advertise all ranges in single spring capability subtlv";
      }
      leaf explicit-null {
        type empty;
        description
          "Set E and P bits in all Prefix SID advertisements";
      }
      leaf mapping-server {
        type string;
        description
          "Mapping server name";
      }
      leaf no-strict-spf {
        type empty;
        description
          " Disable strict spf algo 1 advertisement";
      }
      leaf no-binding-sid-leaking {
        type empty;
        description
          " Disable SRMS binding sid leaking";
      }
      leaf ldp-stitching {
        type empty;
        description
          "Enable SR to LDP stitching";
      }
      leaf entropy-label {
        type empty;
        description
          " Enable entropy label";
      }
      container srv6 {
        presence "enable srv6";
        description
          "Enable IPv6 Segment Routing (SRv6)";
        uses apply-advanced;
        list locator {
          key "name";
          ordered-by user;
          description
            "SRv6 Locator";
          leaf name {
            type string;
            mandatory true;
            description
              "Locator name";
          }
          uses apply-advanced;
          leaf anycast {
            type empty;
            description
              "Set A flag in the Prefix-Attribute sub-TLV";
          }
          list end-sid {
            key "name";
            ordered-by user;
            leaf name {
              type jt:ipv6addr;
            }
            uses apply-advanced;
          }
          container dynamic-end-sid {
            presence "enable dynamic-end-sid";
            description
              "Allocate end SID dynamically";
            uses apply-advanced;
            container flavor {
              presence "enable flavor";
              description
                "Configure end-SID flavor";
              uses apply-advanced;
              leaf psp {
                type empty;
                description
                  "Penultimate segment pop of the SRH";
              }
              leaf usp {
                type empty;
                description
                  "Ultimate segment pop of the SRH";
              }
              leaf usd {
                type empty;
                description
                  "Ultimate segment decapsulation";
              }
            }
          }
          leaf micro-node-sid {
            type empty;
            description
              "Program and advertise micro-node-SID";
          }
        }
      }
    }
    list level {
      key "name";
      ordered-by user;
      description
        "Configure global level attributes";
      leaf name {
        type union {
          type string {
            pattern "<.*>|$.*";
          }
          type uint32 {
            range "1 .. 2";
          }
        }
        description
          "IS-IS level number";
      }
      uses apply-advanced;
      leaf labeled-preference {
        type union {
          type uint32;
          type string {
            pattern "<.*>|$.*";
          }
        }
        description
          "Preference of labeled IS-IS routes";
      }
      leaf srv6-preference {
        type union {
          type uint32;
          type string {
            pattern "<.*>|$.*";
          }
        }
        description
          "Preference of SRV6 IS-IS routes";
      }
      leaf flex-algorithm-preference {
        type union {
          type uint32;
          type string {
            pattern "<.*>|$.*";
          }
        }
        description
          "Preference of flex-algorithm L-ISIS routes";
      }
      container source-packet-routing {
        presence "enable source-packet-routing";
        description
          "Enable Source Packet Routing (SPRING)";
        uses apply-advanced;
        choice enable-disable {
          case case_1 {
            leaf disable {
              type empty;
              description
                "Disable Source Packet Routing on this level";
            }
          }
        }
        leaf srms-preference {
          type union {
            type string {
              pattern "<.*>|$.*";
            }
            type uint32 {
              range "0 .. 255";
            }
          }
          description
            "Set SRMS preference value";
        }
      }
      choice enable-disable {
        case case_1 {
          leaf disable {
            type empty;
            description
              "Disable IS-IS on this level";
          }
        }
      }
      leaf authentication-key {
        type jt:unreadable;
        description
          "Authentication key (password)";
      }
      leaf authentication-type {
        type enumeration {
          enum "md5" {
            description
              "MD5 authentication";
          }
          enum "simple" {
            description
              "Simple password authentication";
          }
        }
        description
          "Authentication type";
      }
      leaf purge-originator {
        type enumeration {
          enum "self" {
            description
              "Add POI only for self-originated purge LSPs";
          }
          enum "empty" {
            description
              "Add POI for purge LSPs who do not have POI information";
          }
        }
        description
          "Add Purge Originator information";
      }
      leaf no-hello-authentication {
        type empty;
        description
          "Disable authentication for hello packets";
      }
      leaf no-csnp-authentication {
        type empty;
        description
          "Disable authentication for CSN packets";
      }
      leaf no-psnp-authentication {
        type empty;
        description
          "Disable authentication for PSN packets";
      }
      leaf no-lsp-authentication {
        type empty;
        description
          "Disable authentication for LSP packets";
      }
      leaf authentication-key-chain {
        type string {
          length "1 .. 128";
        }
        description
          "Key chain name";
      }
      leaf wide-metrics-only {
        type empty;
        description
          "Generate wide metrics only";
      }
      leaf preference {
        type union {
          type uint32;
          type string {
            pattern "<.*>|$.*";
          }
        }
        description
          "Preference of internal routes";
      }
      leaf external-preference {
        type union {
          type uint32;
          type string {
            pattern "<.*>|$.*";
          }
        }
        description
          "Preference of external routes";
      }
      leaf prefix-export-limit {
        type union {
          type string {
            pattern "<.*>|$.*";
          }
          type uint32 {
            range "0 .. 4294967295";
          }
        }
        description
          "Maximum number of external prefixes that can be exported";
      }
      leaf max-lsp-size {
        type union {
          type string {
            pattern "<.*>|$.*";
          }
          type uint32 {
            range "512 .. 9192";
          }
        }
        description
          "Maximum size allowed for LSPs";
      }
      container flood-reflector {
        description
          "Enable flood-reflector";
        uses apply-advanced;
        choice flood-reflector-choice {
          case case_1 {
            container reflector {
              description
                "Configure this as a flood-reflector";
              uses apply-advanced;
              leaf cluster-id {
                type union {
                  type string {
                    pattern "<.*>|$.*";
                  }
                  type uint32 {
                    range "1 .. 4294967295";
                  }
                }
                mandatory true;
                description
                  "Cluster-ID";
              }
            }
          }
          case case_2 {
            leaf client {
              type empty;
              description
                "Configure interface as flood-reflector client";
            }
          }
        }
      }
    }
    list interface-group {
      key "name";
      description
        "Interface grouping configuration";
      leaf name {
        type string;
        description
          "Interface group name";
      }
      uses apply-advanced;
      list level {
        key "name";
        ordered-by user;
        description
          "Configure levels on this interface-group";
        leaf name {
          type union {
            type string {
              pattern "<.*>|$.*";
            }
            type uint32 {
              range "1 .. 2";
            }
          }
          description
            "IS-IS level number";
        }
        uses apply-advanced;
        container ipv4-adjacency-segment {
          description
            "Configure ipv4 adjacency segment";
          uses apply-advanced;
          container protected {
            description
              "Adjacency SID is eligible for protection";
            choice adjsid-type {
              case case_1 {
                container index {
                  description
                    "Adjacency SID indexed from SRGB";
                  leaf index-number {
                    type union {
                      type string {
                        pattern "<.*>|$.*";
                      }
                      type uint32 {
                        range "0 .. 1048575";
                      }
                    }
                  }
                }
              }
              case case_2 {
                leaf label {
                  type union {
                    type string {
                      pattern "<.*>|$.*";
                    }
                    type uint32 {
                      range "16 .. 1048575";
                    }
                  }
                  description
                    "Adjacency SID from static label pool";
                }
              }
              case case_3 {
                leaf dynamic {
                  type empty;
                  description
                    "Dynamically allocate an adjacency segment";
                }
              }
            }
          }
          container unprotected {
            description
              "Adjacency SID uneligible for protection";
            choice adjsid-type {
              case case_1 {
                container index {
                  description
                    "Adjacency SID indexed from SRGB";
                  leaf index-number {
                    type union {
                      type string {
                        pattern "<.*>|$.*";
                      }
                      type uint32 {
                        range "0 .. 1048575";
                      }
                    }
                  }
                }
              }
              case case_2 {
                leaf label {
                  type union {
                    type string {
                      pattern "<.*>|$.*";
                    }
                    type uint32 {
                      range "16 .. 1048575";
                    }
                  }
                  description
                    "Adjacency SID from static label pool";
                }
              }
              case case_3 {
                leaf dynamic {
                  type empty;
                  description
                    "Dynamically allocate an adjacency segment";
                }
              }
            }
          }
        }
        container ipv6-adjacency-segment {
          description
            "Configure ipv6 adjacency segment";
          uses apply-advanced;
          container protected {
            description
              "Adjacency SID is eligible for protection";
            choice adjsid-type {
              case case_1 {
                container index {
                  description
                    "Adjacency SID indexed from SRGB";
                  leaf index-number {
                    type union {
                      type string {
                        pattern "<.*>|$.*";
                      }
                      type uint32 {
                        range "0 .. 1048575";
                      }
                    }
                  }
                }
              }
              case case_2 {
                leaf label {
                  type union {
                    type string {
                      pattern "<.*>|$.*";
                    }
                    type uint32 {
                      range "16 .. 1048575";
                    }
                  }
                  description
                    "Adjacency SID from static label pool";
                }
              }
              case case_3 {
                leaf dynamic {
                  type empty;
                  description
                    "Dynamically allocate an adjacency segment";
                }
              }
            }
          }
          container unprotected {
            description
              "Adjacency SID uneligible for protection";
            choice adjsid-type {
              case case_1 {
                container index {
                  description
                    "Adjacency SID indexed from SRGB";
                  leaf index-number {
                    type union {
                      type string {
                        pattern "<.*>|$.*";
                      }
                      type uint32 {
                        range "0 .. 1048575";
                      }
                    }
                  }
                }
              }
              case case_2 {
                leaf label {
                  type union {
                    type string {
                      pattern "<.*>|$.*";
                    }
                    type uint32 {
                      range "16 .. 1048575";
                    }
                  }
                  description
                    "Adjacency SID from static label pool";
                }
              }
              case case_3 {
                leaf dynamic {
                  type empty;
                  description
                    "Dynamically allocate an adjacency segment";
                }
              }
            }
          }
        }
        list topology {
          key "name";
          ordered-by user;
          description
            "Topology specific attributes";
          leaf name {
            type enumeration {
              enum "default" {
                description
                  "Default topology";
              }
              enum "ipv4-multicast" {
                description
                  "IPv4 multicast topology";
              }
              enum "ipv6-unicast" {
                description
                  "IPv6 unicast topology";
              }
              enum "ipv6-multicast" {
                description
                  "IPv6 multicast topology";
              }
            }
            description
              "Topology name";
          }
          uses apply-advanced;
          leaf metric {
            type union {
              type string {
                pattern "<.*>|$.*";
              }
              type uint32 {
                range "0 .. 16777215";
              }
            }
            description
              "Topology metric";
          }
          container bandwidth-based-metrics {
            description
              "Configure bandwidth based metrics";
            uses apply-advanced;
            list bandwidth {
              key "name";
              description
                "Bandwidth threshold";
              leaf name {
                type string;
              }
              leaf metric {
                type union {
                  type string {
                    pattern "<.*>|$.*";
                  }
                  type uint32 {
                    range "0 .. 16777215";
                  }
                }
                mandatory true;
                description
                  "Metric associated with specified bandwidth";
              }
            }
          }
        }
      }
      container link-group-protection {
        description
          "Configure link group protection";
        uses apply-advanced;
        leaf minimum-bandwidth {
          type string;
          description
            "Minimum bandwidth to carry traffic";
        }
        leaf revert-bandwidth {
          type string;
          description
            "Revert bandwidth to carry traffic";
        }
      }
      list interface {
        key "name";
        description
          "List interfaces for this group";
        leaf name {
          type union {
            type jt:interface-name;
            type string {
              pattern "<.*>|$.*";
            }
          }
          description
            "Interface name";
        }
        uses apply-advanced;
        leaf weight {
          type union {
            type string {
              pattern "<.*>|$.*";
            }
            type uint32 {
              range "1 .. 255";
            }
          }
          description
            "Interface weight for adjacency set";
        }
      }
    }
    container spf-options {
      description
        "Configure SPF attributes";
      uses apply-advanced;
      container microloop-avoidance {
        description
          "Configure microloop avoidance mechanisms";
        uses apply-advanced;
        container post-convergence-path {
          presence "enable post-convergence-path";
          description
            "Temporarily install post-convergence path for routes potentially affected by microloops";
          uses apply-advanced;
          leaf delay {
            type union {
              type string {
                pattern "<.*>|$.*";
              }
              type uint32 {
                range "500 .. 60000";
              }
            }
            units "milliseconds";
            description
              "Time after which temporary post-convergence paths are removed";
          }
          leaf maximum-labels {
            type union {
              type string {
                pattern "<.*>|$.*";
              }
              type uint32 {
                range "2 .. 8";
              }
            }
            description
              "Set maximum number of label supported for Micro-Loop-Avoidance calculations";
          }
          leaf maximum-srv6-sids {
            type union {
              type string {
                pattern "<.*>|$.*";
              }
              type uint32 {
                range "2 .. 12";
              }
            }
            description
              "Set maximum number of SRV6 SIDs supported for Micro-Loop-Avoidance calculations";
          }
        }
      }
      leaf delay {
        type union {
          type string {
            pattern "<.*>|$.*";
          }
          type uint32 {
            range "50 .. 1000";
          }
        }
        units "milliseconds";
        description
          "Time to wait before running an SPF";
      }
      leaf holddown {
        type union {
          type string {
            pattern "<.*>|$.*";
          }
          type uint32 {
            range "1000 .. 10000";
          }
        }
        units "milliseconds";
        description
          "Time to hold down before running an SPF";
      }
      leaf rapid-runs {
        type union {
          type string {
            pattern "<.*>|$.*";
          }
          type uint32 {
            range "1 .. 5";
          }
        }
        description
          "Number of rapid SPF runs before SPF holddown";
      }
      container multipath {
        description
          "Configure multipath options";
        uses apply-advanced;
        container weighted {
          description
            "Weighted multipath options";
          uses apply-advanced;
          leaf one-hop {
            type empty;
            description
              "Enable load balancing on onehop multipath based on interface bandwidth";
          }
        }
      }
    }
    container traceoptions {
      description
        "Trace options for IS-IS";
      uses apply-advanced;
      container file {
        description
          "Trace file options";
        leaf filename {
          type string {
            length "1 .. 1024";
          }
          description
            "Name of file in which to write trace information";
        }
        leaf replace {
          type empty;
          status deprecated;
          description
            "Replace trace file rather than appending to it";
        }
        leaf size {
          type string;
          description
            "Maximum trace file size";
        }
        leaf files {
          type union {
            type string {
              pattern "<.*>|$.*";
            }
            type uint32 {
              range "2 .. 1000";
            }
          }
          default "10";
          description
            "Maximum number of trace files";
        }
        leaf no-stamp {
          type empty;
          status deprecated;
          description
            "Do not timestamp trace file";
        }
        choice world-readable-choice {
          leaf world-readable {
            type empty;
            description
              "Allow any user to read the log file";
          }
          leaf no-world-readable {
            type empty;
            description
              "Don't allow any user to read the log file";
          }
        }
      }
      list flag {
        key "name";
        ordered-by user;
        description
          "Tracing parameters";
        leaf name {
          type enumeration {
            enum "post-convergence-lfa" {
              description
                "Trace post-convergence-lfa related events";
            }
            enum "error" {
              description
                "Trace errored packets";
            }
            enum "spf" {
              description
                "Trace SPF events";
            }
            enum "packets" {
              description
                "Trace IS-IS packets";
            }
            enum "hello" {
              description
                "Trace hello packets";
            }
            enum "lsp" {
              description
                "Trace link-state packets";
            }
            enum "psn" {
              description
                "Trace partial sequence number (PSN) packets";
            }
            enum "csn" {
              description
                "Trace complete sequence number (CSN) packets";
            }
            enum "layer2-map" {
              description
                "Trace ARP/ND kernel state manipulation";
            }
            enum "lsp-generation" {
              description
                "Trace LSP generation";
            }
            enum "graceful-restart" {
              description
                "Trace graceful restart events";
            }
            enum "ldp-synchronization" {
              description
                "Trace synchronization between IS-IS and LDP";
            }
            enum "nsr-synchronization" {
              description
                "Trace NSR synchronization events";
            }
            enum "spring" {
              description
                "Trace source packet routing";
            }
            enum "prefix-sid" {
              description
                "Trace source packet routing, prefix-sids";
            }
            enum "flex-algorithm" {
              description
                "Trace flex-algorithm related events";
            }
            enum "adj-sid" {
              description
                "Trace adj-sid related events";
            }
            enum "route" {
              description
                "Trace routing information";
            }
            enum "normal" {
              description
                "Trace normal events";
            }
            enum "general" {
              description
                "Trace general events";
            }
            enum "state" {
              description
                "Trace state transitions";
            }
            enum "policy" {
              description
                "Trace policy processing";
            }
            enum "task" {
              description
                "Trace routing protocol task processing";
            }
            enum "timer" {
              description
                "Trace routing protocol timer processing";
            }
            enum "srv6" {
              description
                "Trace srv6 related events";
            }
            enum "rmopd" {
              description
                "Trace rmopd interactions";
            }
            enum "mapping-server" {
              description
                "Trace mapping server related events";
            }
            enum "prefix-unreachable" {
              description
                "Trace unreachable prefix advertisement related events";
            }
            enum "all" {
              description
                "Trace everything";
            }
          }
        }
        leaf send {
          type empty;
          description
            "Trace transmitted packets";
        }
        leaf receive {
          type empty;
          description
            "Trace received packets";
        }
        leaf detail {
          type empty;
          description
            "Trace detailed information";
        }
        leaf disable {
          type empty;
          description
            "Disable this trace flag";
        }
      }
    }
    container backup-spf-options {
      description
        "Configure backup SPF attributes";
      uses apply-advanced;
      container remote-backup-calculation {
        presence "enable remote-backup-calculation";
        description
          "Calculate Remote LFA backup nexthops";
        uses apply-advanced;
      }
      container use-post-convergence-lfa {
        presence "enable use-post-convergence-lfa";
        description
          "Calculate Post Convergence Backup Nexthops";
        uses apply-advanced;
        leaf maximum-labels {
          type union {
            type string {
              pattern "<.*>|$.*";
            }
            type uint32 {
              range "2 .. 8";
            }
          }
          description
            "Set maximum number of label supported for post convergence path calculations";
        }
        leaf maximum-srv6-sids {
          type union {
            type string {
              pattern "<.*>|$.*";
            }
            type uint32 {
              range "2 .. 12";
            }
          }
          description
            "Set maximum number of SRV6 SIDs for post convergence path calculations";
        }
      }
      container use-source-packet-routing {
        presence "enable use-source-packet-routing";
        description
          "Use SPRING routed paths for protection";
        uses apply-advanced;
      }
      leaf per-prefix-calculation {
        type empty;
        description
          "Calculate backup nexthops for non-best prefix originators";
      }
      leaf node-link-degradation {
        type empty;
        description
          "Degrade to link protection when nodelink protection not available";
      }
    }
    list context-identifier {
      key "name";
      ordered-by user;
      description
        "Configuration for advertisement of a context-identifier ";
      leaf name {
        type jt:ipprefix;
        description
          "Context identifier range";
      }
      uses apply-advanced;
      list level {
        key "name";
        ordered-by user;
        description
          "Configure global level attributes";
        leaf name {
          type union {
            type string {
              pattern "<.*>|$.*";
            }
            type uint32 {
              range "1 .. 2";
            }
          }
          description
            "IS-IS level number";
        }
        uses apply-advanced;
        choice enable-disable {
          case case_1 {
            leaf disable {
              type empty;
              description
                "Disable advertisements to this level";
            }
          }
        }
      }
    }
    choice enable-disable {
      case case_1 {
        leaf disable {
          type empty;
          description
            "Disable IS-IS";
        }
      }
    }
    leaf-list export {
      type jt:policy-algebra;
      ordered-by user;
      description
        "Export policy";
    }
    leaf-list import {
      type jt:policy-algebra;
      ordered-by user;
      description
        "Import policy";
    }
    leaf reference-bandwidth {
      type string;
      description
        "Bandwidth for calculating metric defaults";
    }
    leaf job-stats {
      type empty;
      description
        "Collect job statistics";
    }
    leaf lsp-lifetime {
      type union {
        type string {
          pattern "<.*>|$.*";
        }
        type uint32 {
          range "350 .. 65535";
        }
      }
      units "seconds";
      description
        "Lifetime of LSPs";
    }
    leaf max-lsp-size {
      type union {
        type string {
          pattern "<.*>|$.*";
        }
        type uint32 {
          range "512 .. 9192";
        }
      }
      default "1492";
      description
        "Maximum size allowed for LSPs";
    }
    leaf max-hello-size {
      type union {
        type string {
          pattern "<.*>|$.*";
        }
        type uint32 {
          range "512 .. 16000";
        }
      }
      default "1492";
      description
        "Maximum size allowed for ISIS Hello PDUs";
    }
    leaf max-snp-size {
      type union {
        type string {
          pattern "<.*>|$.*";
        }
        type uint32 {
          range "512 .. 1400";
        }
      }
      default "1400";
      description
        "Maximum size allowed for Sequence Number (Complete/Partial) PDUs";
    }
    leaf spf-delay {
      type union {
        type string {
          pattern "<.*>|$.*";
        }
        type uint32 {
          range "50 .. 120000";
        }
      }
      units "milliseconds";
      status deprecated;
      description
        "Time to wait before running an SPF";
    }
    leaf authentication-key {
      type jt:unreadable;
      status deprecated;
      description
        "Authentication key (password)";
    }
    leaf authentication-type {
      type enumeration {
        enum "md5" {
          status deprecated;
          description
            "MD5 authentication";
        }
        enum "simple" {
          status deprecated;
          description
            "Simple password authentication";
        }
      }
      status deprecated;
      description
        "Authentication type";
    }
    leaf loose-authentication-check {
      type empty;
      description
        "Verify authentication only if PDU has authentication TLV";
    }
    leaf max-areas {
      type union {
        type string {
          pattern "<.*>|$.*";
        }
        type uint32 {
          range "3 .. 64";
        }
      }
      default "3";
      description
        "Maximum number of advertised Areas";
    }
    leaf no-authentication-check {
      type empty;
      description
        "Disable authentication checking";
    }
    leaf no-ipv4-routing {
      type empty;
      description
        "Disable IPv4 routing";
    }
    leaf no-ipv6-routing {
      type empty;
      description
        "Disable IPv6 routing";
    }
    leaf no-adjacency-holddown {
      type empty;
      description
        "Disable adjacency hold down";
    }
    leaf multicast-topology {
      type empty;
      status deprecated;
      description
        "Enable multicast topology";
    }
    leaf ignore-attached-bit {
      type empty;
      description
        "Ignore the attached bit in Level 1 LSPs";
    }
    container rib-group {
      description
        "Routing table group for importing IS-IS routes";
      uses rib_group_type;
    }
    container no-external-export {
      description
        "No external export";
      uses apply-advanced;
      list protocol {
        key "name";
        ordered-by user;
        description
          "Protocol parameters";
        leaf name {
          type enumeration {
            enum "bgp" {
              description
                "BGP";
            }
            enum "ospf" {
              description
                "OSPF";
            }
            enum "isis" {
              description
                "ISIS";
            }
            enum "l-isis" {
              description
                "Labelled ISIS";
            }
            enum "l-ospf" {
              description
                "Labelled OSPF";
            }
            enum "static" {
              description
                "Static";
            }
          }
        }
      }
    }
    container strict-dual-isis {
      presence "enable strict-dual-isis";
      description
        "Enable dual isis if spf computation is required for both ipv4 and ipv6 family";
      uses apply-advanced;
      leaf holdown {
        type union {
          type string {
            pattern "<.*>|$.*";
          }
          type uint32 {
            range "1 .. 65535";
          }
        }
        default "12";
        status deprecated;
        description
          "Time to wait for ipv4 and ipv6 connectivity";
      }
      leaf holddown {
        type union {
          type string {
            pattern "<.*>|$.*";
          }
          type uint32 {
            range "1 .. 65535";
          }
        }
        default "12";
        description
          "Time to wait for ipv4 and ipv6 connectivity";
      }
    }
    container topologies {
      description
        "Enable topologies";
      uses apply-advanced;
      leaf ipv4-multicast {
        type empty;
        description
          "Enable IPv4-multicast topology";
      }
      leaf ipv6-unicast {
        type empty;
        description
          "Enable IPv6-unicast topology";
      }
      leaf ipv6-multicast {
        type empty;
        description
          "Enable IPv6-multicast topology";
      }
    }
    container overload {
      presence "enable overload";
      description
        "Set the overload bit (no transit traffic)";
      uses apply-advanced;
      leaf timeout {
        type union {
          type string {
            pattern "<.*>|$.*";
          }
          type uint32 {
            range "60 .. 3600";
          }
        }
        units "seconds";
        description
          "Time after which overload bit is reset";
      }
      leaf advertise-high-metrics {
        type empty;
        description
          "Advertise high metrics instead of setting the overload bit";
      }
      leaf allow-route-leaking {
        type empty;
        description
          "Allow routes to be leaked when overload is configured";
      }
      leaf internal-prefixes {
        type empty;
        description
          "Allow internal prefixes to be advertised with high metric";
      }
      leaf external-prefixes {
        type empty;
        description
          "Allow external prefixes to be advertised with high metric";
      }
    }
    container dynamic-overload {
      description
        "Set the dynamic overload options";
      uses apply-advanced;
      leaf no-overload-on-prefix-export-limit {
        type empty;
        description
          "Do not set overload bit when prefix export limit is reached";
      }
      leaf auto-recovery {
        type empty;
        description
          "Enable Auto recovery to recover from dynamic overload state";
      }
    }
    container graceful-restart {
      description
        "IS-IS graceful restart options";
      choice enable-disable {
        case case_1 {
          leaf disable {
            type empty;
            description
              "Disable graceful restart";
          }
        }
      }
      leaf helper-disable {
        type empty;
        description
          "Disable graceful restart helper capability";
      }
      leaf restart-duration {
        type union {
          type string {
            pattern "<.*>|$.*";
          }
          type uint32 {
            range "30 .. 300";
          }
        }
        units "seconds";
        description
          "Maximum time for graceful restart to finish";
      }
    }
    list net {
      key "name";
      description
        "Assign Network Entity Title (NET) configuration";
      leaf name {
        type jt:isoaddr;
        description
          "Assign Network Entity Title (NET) address to an IS-IS router";
      }
    }
    leaf rfc7775-compliance {
      type empty;
      description
        "RFC 7775 compliance for up/down bit and prefix attribute sub-tlv";
    }
  }

  grouping juniper-protocols-l2control {
    uses apply-advanced;
    container traceoptions {
      description
        "Global tracing options for STP";
      uses apply-advanced;
      container file {
        description
          "Trace file options";
        leaf filename {
          type string {
            length "1 .. 1024";
          }
          description
            "Name of file in which to write trace information";
        }
        leaf replace {
          type empty;
          status deprecated;
          description
            "Replace trace file rather than appending to it";
        }
        leaf size {
          type string;
          description
            "Maximum trace file size";
        }
        leaf files {
          type union {
            type string {
              pattern "<.*>|$.*";
            }
            type uint32 {
              range "2 .. 1000";
            }
          }
          default "10";
          description
            "Maximum number of trace files";
        }
        leaf no-stamp {
          type empty;
          status deprecated;
          description
            "Do not timestamp trace file";
        }
        choice world-readable-choice {
          leaf world-readable {
            type empty;
            description
              "Allow any user to read the log file";
          }
          leaf no-world-readable {
            type empty;
            description
              "Don't allow any user to read the log file";
          }
        }
      }
      list flag {
        key "name";
        ordered-by user;
        description
          "Tracing parameters";
        leaf name {
          type enumeration {
            enum "parse" {
              description
                "Trace configuration parsing";
            }
            enum "regex-parse" {
              description
                "Trace regular-expression parsing";
            }
            enum "config-internal" {
              description
                "Trace configuration internals";
            }
            enum "normal" {
              description
                "Trace normal events";
            }
            enum "general" {
              description
                "Trace general events";
            }
            enum "state" {
              description
                "Trace state transitions";
            }
            enum "task" {
              description
                "Trace routing protocol task processing";
            }
            enum "timer" {
              description
                "Trace routing protocol task timer processing";
            }
            enum "ppmlite" {
              description
                "Trace libppmlite processing";
            }
            enum "all" {
              description
                "Trace everything";
            }
          }
        }
        leaf disable {
          type empty;
          description
            "Disable this trace flag";
        }
      }
    }
  }

  grouping juniper-protocols-ldp {
    uses apply-advanced;
    container traceoptions {
      description
        "Trace options for LDP";
      uses apply-advanced;
      container file {
        description
          "Trace file options";
        leaf filename {
          type string {
            length "1 .. 1024";
          }
          description
            "Name of file in which to write trace information";
        }
        leaf replace {
          type empty;
          status deprecated;
          description
            "Replace trace file rather than appending to it";
        }
        leaf size {
          type string;
          description
            "Maximum trace file size";
        }
        leaf files {
          type union {
            type string {
              pattern "<.*>|$.*";
            }
            type uint32 {
              range "2 .. 1000";
            }
          }
          default "10";
          description
            "Maximum number of trace files";
        }
        leaf no-stamp {
          type empty;
          status deprecated;
          description
            "Do not timestamp trace file";
        }
        choice world-readable-choice {
          leaf world-readable {
            type empty;
            description
              "Allow any user to read the log file";
          }
          leaf no-world-readable {
            type empty;
            description
              "Don't allow any user to read the log file";
          }
        }
      }
      list flag {
        key "name";
        ordered-by user;
        description
          "Tracing parameters";
        leaf name {
          type enumeration {
            enum "error" {
              description
                "Trace errored packets";
            }
            enum "event" {
              description
                "Trace LDP state machine events";
            }
            enum "packet-dump" {
              description
                "Dump the contents of selected packet types";
            }
            enum "packets" {
              description
                "Trace all LDP packets";
            }
            enum "periodic" {
              description
                "Trace periodic (hello and keepalive) packets";
            }
            enum "initialization" {
              description
                "Trace initialization packets";
            }
            enum "notification" {
              description
                "Trace notification packets";
            }
            enum "address" {
              description
                "Trace address packets";
            }
            enum "label" {
              description
                "Trace label packets";
            }
            enum "binding" {
              description
                "Trace label binding state";
            }
            enum "path" {
              description
                "Trace label path state";
            }
            enum "ppmd" {
              description
                "Trace state and events for ppmd process";
            }
            enum "nsr-synchronization" {
              description
                "Trace NSR synchronization events";
            }
            enum "link-protection" {
              description
                "Trace link protection events";
            }
            enum "p2mp-nsr-synchronization" {
              description
                "Trace p2mp NSR synchronization events";
            }
            enum "route" {
              description
                "Trace routing information";
            }
            enum "normal" {
              description
                "Trace normal events";
            }
            enum "general" {
              description
                "Trace general events";
            }
            enum "state" {
              description
                "Trace state transitions";
            }
            enum "policy" {
              description
                "Trace policy processing";
            }
            enum "task" {
              description
                "Trace routing protocol task processing";
            }
            enum "timer" {
              description
                "Trace routing protocol timer processing";
            }
            enum "all" {
              description
                "Trace everything";
            }
          }
        }
        leaf send {
          type empty;
          description
            "Trace transmitted packets";
        }
        leaf receive {
          type empty;
          description
            "Trace received packets";
        }
        leaf detail {
          type empty;
          description
            "Trace detailed information";
        }
        leaf disable {
          type empty;
          description
            "Disable this trace flag";
        }
        container filter {
          presence "enable filter";
          description
            "Filter to apply to this flag";
          uses ldp_filter_obj;
        }
      }
    }
    container auto-targeted-session {
      presence "enable auto-targeted-session";
      description
        "Configure auto targeted session parameters";
      uses apply-advanced;
      leaf teardown-delay {
        type union {
          type string {
            pattern "<.*>|$.*";
          }
          type uint32 {
            range "1 .. 300";
          }
        }
        units "seconds";
        default "90";
        description
          "Auto targeted session tear down delay";
      }
      leaf maximum-sessions {
        type union {
          type string {
            pattern "<.*>|$.*";
          }
          type uint32 {
            range "1 .. 1000";
          }
        }
        default "100";
        description
          "Auto targeted maximum sessions";
      }
      leaf no-rlfa {
        type empty;
        description
          "Do not allow RLFA in auto targeted sessions";
      }
      leaf no-dynamic-tunnels {
        type empty;
        description
          "Do not allow dynamic tunnels in auto targeted sessions";
      }
    }
    leaf preference {
      type union {
        type uint32;
        type string {
          pattern "<.*>|$.*";
        }
      }
      description
        "Route preference";
    }
    leaf no-forwarding {
      type empty;
      description
        "Do not use LDP ingress routes for forwarding";
    }
    leaf rib-group {
      type string;
      description
        "Routing table group for importing ingress routes";
    }
    leaf rib-group6 {
      type string;
      description
        "Routing table group for importing ingress v6 routes";
    }
    leaf l2-smart-policy {
      type empty;
      description
        "Do not export or import Layer 3 FECs for Layer 2 sessions";
    }
    leaf track-igp-metric {
      type empty;
      description
        "Track the IGP metric";
    }
    leaf strict-targeted-hellos {
      type empty;
      description
        "Do not send targeted hellos to unconfigured neighbors";
    }
    container longest-match {
      presence "enable longest-match";
      description
        "Configure longest match";
      uses apply-advanced;
      leaf-list policy {
        type jt:policy-algebra;
        ordered-by user;
        description
          "Longest match import policy";
      }
    }
    leaf-list import {
      type jt:policy-algebra;
      ordered-by user;
      description
        "Import policy";
    }
    leaf-list export {
      type jt:policy-algebra;
      ordered-by user;
      description
        "Export policy";
    }
    leaf-list egress-policy {
      type jt:policy-algebra;
      ordered-by user;
      description
        "Configure LSP egress policy";
    }
    leaf-list dod-request-policy {
      type jt:policy-algebra;
      ordered-by user;
      description
        "Configure DoD label request policy";
    }
    choice deaggregate-choice {
      leaf deaggregate {
        type empty;
        description
          "Deaggregate FECs into separate labels";
      }
      leaf no-deaggregate {
        type empty;
        description
          "Don't deaggregate FECs into separate labels";
      }
    }
    leaf explicit-null {
      type empty;
      description
        "Advertise the EXPLICIT_NULL label for egress FECs";
    }
    leaf label-withdrawal-delay {
      type union {
        type string {
          pattern "<.*>|$.*";
        }
        type uint32 {
          range "0 .. 120";
        }
      }
      units "seconds";
      default "60";
      description
        "Delay label withdrawal for FECs to avoid label churn";
    }
    container transport-address {
      description
        "Address used for TCP sessions";
      choice address-choice {
        case case_1 {
          leaf router-id {
            type empty;
            description
              "Use router ID for TCP connections";
          }
        }
        case case_2 {
          leaf interface {
            type empty;
            description
              "Use interface address for TCP connections";
          }
        }
        case case_3 {
          leaf address {
            type jt:ipaddr;
            description
              "Use specified address for TCP connections";
          }
        }
      }
    }
    leaf keepalive-interval {
      type union {
        type string {
          pattern "<.*>|$.*";
        }
        type uint32 {
          range "1 .. 65535";
        }
      }
      description
        "Keepalive interval (seconds)";
    }
    leaf keepalive-timeout {
      type union {
        type string {
          pattern "<.*>|$.*";
        }
        type uint32 {
          range "1 .. 65535";
        }
      }
      description
        "Keepalive timeout (seconds)";
    }
    list interface {
      key "name";
      description
        "Enable LDP on this interface";
      leaf name {
        type union {
          type jt:interface-name;
          type string {
            pattern "<.*>|$.*";
          }
        }
        description
          "Interface name";
      }
      uses apply-advanced;
      choice enable-disable {
        case case_1 {
          leaf disable {
            type empty;
            description
              "Disable LDP on this interface";
          }
        }
      }
      leaf hello-interval {
        type union {
          type string {
            pattern "<.*>|$.*";
          }
          type uint32 {
            range "1 .. 65535";
          }
        }
        description
          "Hello interval (seconds)";
      }
      leaf hold-time {
        type union {
          type string {
            pattern "<.*>|$.*";
          }
          type uint32 {
            range "1 .. 65535";
          }
        }
        description
          "Hello hold time (seconds)";
      }
      container transport-address {
        description
          "Address used for TCP sessions";
        choice address-choice {
          case case_1 {
            leaf router-id {
              type empty;
              description
                "Use router ID for TCP connections";
            }
          }
          case case_2 {
            leaf interface {
              type empty;
              description
                "Use interface address for TCP connections";
            }
          }
          case case_3 {
            leaf address {
              type jt:ipaddr;
              description
                "Use specified address for TCP connections";
            }
          }
        }
      }
    }
    list neighbor {
      key "name";
      description
        "Configure a remote LDP neighbor";
      leaf name {
        type jt:ipaddr;
        description
          "Neighbor address";
      }
      uses apply-advanced;
    }
    list session {
      key "name";
      description
        "Configure session parameters";
      leaf name {
        type jt:ipaddr;
        description
          "Session destination address";
      }
      uses apply-advanced;
      leaf authentication-key {
        type string {
          length "1 .. 126";
        }
        description
          "MD5 authentication key";
      }
      leaf downstream-on-demand {
        type empty;
        description
          "Configure downstream on demand label distribution mode";
      }
      leaf transport-address {
        type jt:ipaddr;
        description
          "Address used for TCP sessions to the neighbor";
      }
    }
    list session-group {
      key "name";
      description
        "Configure session group parameters";
      leaf name {
        type jt:ipprefix;
        description
          "Session destination address/prefix length";
      }
      uses apply-advanced;
      leaf authentication-key {
        type string {
          length "1 .. 126";
        }
        description
          "MD5 authentication key";
      }
      leaf downstream-on-demand {
        type empty;
        description
          "Configure downstream on demand label distribution mode";
      }
      leaf transport-address {
        type jt:ipaddr;
        description
          "Address used for TCP sessions to the neighbor";
      }
    }
    container session-protection {
      presence "enable session-protection";
      description
        "Configure session protection";
      leaf timeout {
        type union {
          type string {
            pattern "<.*>|$.*";
          }
          type uint16 {
            range "1 .. 65535";
          }
        }
        units "seconds";
        description
          "Session protection timeout";
      }
    }
    container igp-synchronization {
      description
        "Configure IGP synchronization parameters";
      uses apply-advanced;
      leaf holddown-interval {
        type union {
          type string {
            pattern "<.*>|$.*";
          }
          type uint32 {
            range "10 .. 300";
          }
        }
        units "seconds";
        description
          "Time to hold the up notification to the IGPs";
      }
    }
    container targeted-hello {
      description
        "Configure targeted hello parameters";
      uses apply-advanced;
      leaf hello-interval {
        type union {
          type string {
            pattern "<.*>|$.*";
          }
          type uint32 {
            range "1 .. 65535";
          }
        }
        description
          "Hello interval (seconds)";
      }
      leaf hold-time {
        type union {
          type string {
            pattern "<.*>|$.*";
          }
          type uint32 {
            range "1 .. 65535";
          }
        }
        description
          "Hold interval (seconds)";
      }
    }
    container sr-mapping-client {
      presence "enable sr-mapping-client";
      description
        "Enable LDP to SR mapping-client functionality";
      uses apply-advanced;
      leaf-list policy {
        type jt:policy-algebra;
        ordered-by user;
        description
          "SR mapping-client policy";
      }
    }
    leaf upstream-label-assignment {
      type empty;
      description
        "Allow Upstream Label Assignment capability";
    }
    list family {
      key "name";
      ordered-by user;
      description
        "Address family";
      leaf name {
        type enumeration {
          enum "inet" {
            description
              "IPv4 family";
          }
          enum "inet6" {
            description
              "IPv6 family";
          }
        }
      }
      uses apply-advanced;
    }
    leaf transport-preference {
      type enumeration {
        enum "ipv4" {
          description
            "Use IPv4 for TCP connections";
        }
        enum "ipv6" {
          description
            "Use IPv6 for TCP connections";
        }
      }
      description
        "TCP transport preference";
    }
    container dual-transport {
      presence "enable dual-transport";
      description
        "Use separate IPv4 and IPv6 TCP transport";
      uses apply-advanced;
      leaf inet-lsr-id {
        type jt:ipv4addr;
        mandatory true;
        description
          "LSR identifier for address family inet";
      }
      leaf inet6-lsr-id {
        type jt:ipv4addr;
        mandatory true;
        description
          "LSR identifier for address family inet6";
      }
    }
    leaf no-propagate-ttl {
      type empty;
      description
        "Disable TTL propagation from IP to MPLS (on push) and MPLS to IP (on pop)";
    }
  }

  grouping juniper-protocols-mpls {
    description
      "Multiprotocol Label Switching options";
    uses apply-advanced;
    list lsp-external-controller {
      key "name";
      ordered-by user;
      description
        "External path computing entity";
      leaf name {
        type string;
        description
          "Name of the external path computing entity";
      }
      uses apply-advanced;
      container label-switched-path-template {
        description
          "Template for externally provisioned LSP parameters";
        uses apply-advanced;
        choice dynamic-template {
          case case_1 {
            leaf template-name {
              type string {
                length "1 .. 32";
              }
              description
                "Name of point-to-point LSP template";
            }
          }
          case case_2 {
            leaf default-template {
              type empty;
              description
                "Use default parameters";
            }
          }
        }
      }
      container label-switched-path-p2mp-template {
        description
          "Template for externally provisioned P2MP LSP parameters";
        uses apply-advanced;
        choice dynamic-template {
          case case_1 {
            leaf template-name {
              type string {
                length "1 .. 32";
              }
              description
                "Name of point-to-multipoint LSP template";
            }
          }
          case case_2 {
            leaf default-template {
              type empty;
              description
                "Use default parameters";
            }
          }
        }
      }
      list pce-controlled-lsp {
        key "name";
        ordered-by user;
        description
          "Template for externally provisioned LSP using regular expression";
        leaf name {
          type string;
          description
            "Template regular expression";
        }
        uses apply-advanced;
        container label-switched-path-template {
          description
            "Template for externally provisioned LSP parameters";
          uses apply-advanced;
          leaf template-name {
            type string {
              length "1 .. 64";
            }
            description
              "Name of point-to-point LSP template";
          }
        }
        container label-switched-path-p2mp-template {
          description
            "Template for externally provisioned P2MP LSP parameters";
          uses apply-advanced;
          leaf template-name {
            type string {
              length "1 .. 64";
            }
            description
              "Name of point-to-multipoint LSP template";
          }
        }
      }
    }
    container path-mtu {
      presence "enable path-mtu";
      description
        "Path MTU configuration";
      uses apply-advanced;
      leaf allow-fragmentation {
        type empty;
        description
          "If needed, fragment IP before encapsulating in MPLS";
      }
      container rsvp {
        presence "enable rsvp";
        description
          "RSVP-specific path MTU options";
        uses apply-advanced;
        leaf mtu-signaling {
          type empty;
          description
            "Enable RSVP path MTU signaling";
        }
      }
    }
    container diffserv-te {
      description
        "Global diffserv-traffic-engineering options";
      uses apply-advanced;
      leaf bandwidth-model {
        type enumeration {
          enum "extended-mam" {
            description
              "Maximum allocation model with support for E-LSPs";
          }
          enum "mam" {
            description
              "Maximum allocation model";
          }
          enum "rdm" {
            description
              "Russian dolls model";
          }
        }
        description
          "Bandwidth constraint model supported";
      }
      container te-class-matrix {
        description
          "Supported combinations of traffic-class and preemption";
        uses apply-advanced;
        container te0 {
          description
            "Definition for traffic-engineering class te0";
          uses te-class-object;
        }
        container te1 {
          description
            "Definition for traffic-engineering class te1";
          uses te-class-object;
        }
        container te2 {
          description
            "Definition for traffic-engineering class te2";
          uses te-class-object;
        }
        container te3 {
          description
            "Definition for traffic-engineering class te3";
          uses te-class-object;
        }
        container te4 {
          description
            "Definition for traffic-engineering class te4";
          uses te-class-object;
        }
        container te5 {
          description
            "Definition for traffic-engineering class te5";
          uses te-class-object;
        }
        container te6 {
          description
            "Definition for traffic-engineering class te6";
          uses te-class-object;
        }
        container te7 {
          description
            "Definition for traffic-engineering class te7";
          uses te-class-object;
        }
      }
    }
    container auto-policing {
      description
        "Automatic policing of LSPs";
      uses apply-advanced;
      list class {
        key "name";
        ordered-by user;
        description
          "Forwarding class";
        leaf name {
          type enumeration {
            enum "all" {
              description
                "All forwarding classes";
            }
            enum "ct0" {
              description
                "Forwarding class 0";
            }
            enum "ct1" {
              description
                "Forwarding class 1";
            }
            enum "ct2" {
              description
                "Forwarding class 2";
            }
            enum "ct3" {
              description
                "Forwarding class 3";
            }
          }
        }
        uses apply-advanced;
        choice policing-action {
          case case_1 {
            leaf drop {
              type empty;
              description
                "Drop packets if bandwidth is exceeded";
            }
          }
          case case_2 {
            leaf loss-priority-high {
              type empty;
              description
                "Set loss priority to high if bandwidth is exceeded";
            }
          }
          case case_3 {
            leaf loss-priority-low {
              type empty;
              description
                "Set loss priority to low if bandwidth is exceeded";
            }
          }
        }
      }
    }
    container statistics {
      description
        "Collect statistics for signaled label-switched paths";
      uses apply-advanced;
      container file {
        presence "enable file";
        description
          "Statistics file options";
        leaf filename {
          type string {
            length "1 .. 1024";
          }
          description
            "Name of file in which to write trace information";
        }
        leaf replace {
          type empty;
          status deprecated;
          description
            "Replace trace file rather than appending to it";
        }
        leaf size {
          type string;
          description
            "Maximum trace file size";
        }
        leaf files {
          type union {
            type string {
              pattern "<.*>|$.*";
            }
            type uint32 {
              range "2 .. 1000";
            }
          }
          default "10";
          description
            "Maximum number of trace files";
        }
        leaf no-stamp {
          type empty;
          status deprecated;
          description
            "Do not timestamp trace file";
        }
        choice world-readable-choice {
          leaf world-readable {
            type empty;
            description
              "Allow any user to read the log file";
          }
          leaf no-world-readable {
            type empty;
            description
              "Don't allow any user to read the log file";
          }
        }
      }
      leaf interval {
        type union {
          type string {
            pattern "<.*>|$.*";
          }
          type int32 {
            range "1 .. 65535";
          }
        }
        description
          "Time to collect statistics (seconds)";
      }
      leaf auto-bandwidth {
        type empty;
        description
          "Enable auto bandwidth allocation";
      }
      leaf no-transit-statistics {
        type empty;
        description
          "Disable transit LSP statistics collection";
      }
      choice transit-polling-type {
        case case_1 {
          leaf transit-statistics-polling {
            type empty;
            description
              "Enable polling and display of transit lsp statistics";
          }
        }
      }
      leaf no-bypass-statistics-polling {
        type empty;
        description
          "Disable polling and display of bypass lsp statistics";
      }
      leaf statistics-query-batch-size {
        type union {
          type string {
            pattern "<.*>|$.*";
          }
          type int32 {
            range "1 .. 25";
          }
        }
        description
          "Number of LSPs for which statistics will be queried together";
      }
    }
    container p2mp-lsp {
      description
        "P2MP LSP control configuration";
      uses apply-advanced;
      leaf single-abr {
        type empty;
        description
          "Try to use same exit node for all inter-domain sub LSPs";
      }
      leaf no-re-merge {
        type empty;
        description
          "Avoid LSP CSPF creating remerge";
      }
    }
    container log-updown {
      description
        "Logging actions for LSP up/down events";
      uses apply-advanced;
      choice syslog-choice {
        leaf syslog {
          type empty;
          description
            "Send syslog messages";
        }
        leaf no-syslog {
          type empty;
          description
            "Don't send syslog messages";
        }
      }
      choice trap-choice {
        case case_1 {
          leaf trap {
            type empty;
            description
              "Send SNMP traps";
          }
        }
        case case_2 {
          container no-trap {
            presence "enable no-trap";
            description
              "Don't send SNMP traps";
            uses apply-advanced;
            leaf mpls-lsp-traps {
              type empty;
              description
                "Dont send mpls lsp up/down traps";
            }
            leaf rfc3812-traps {
              type empty;
              description
                "Dont send rfc3812 traps";
            }
          }
        }
      }
      leaf trap-path-down {
        type empty;
        description
          "Send SNMP traps when a path goes down";
      }
      leaf trap-path-up {
        type empty;
        description
          "Send SNMP traps when a path goes up";
      }
    }
    container optimize-adaptive-teardown {
      description
        "Post make before break adaptive teardown";
      uses apply-advanced;
      leaf p2p {
        type empty;
        description
          "Turn on post make before break adaptive teardown for p2p";
      }
      leaf timeout {
        type union {
          type string {
            pattern "<.*>|$.*";
          }
          type int32 {
            range "1 .. 65535";
          }
        }
        units "seconds";
        description
          "Timeout for adaptive teardown to clean up LSP";
      }
      container delay {
        description
          "Delay tearing down old optimized path after adaptive-teardown kicks in";
        uses apply-advanced;
        leaf delay-value {
          type union {
            type string {
              pattern "<.*>|$.*";
            }
            type int32 {
              range "3 .. 65535";
            }
          }
          units "seconds";
          description
            "Delay tearing down old optimized path after adaptive-teardown kicks in";
        }
      }
    }
    container traffic-engineering {
      presence "enable traffic-engineering";
      description
        "Traffic-engineering control";
      uses apply-advanced;
      choice protocols {
        case case_1 {
          leaf bgp {
            type empty;
            description
              "BGP destinations only";
          }
        }
        case case_2 {
          leaf bgp-igp {
            type empty;
            description
              "BGP and IGP destinations";
          }
        }
        case case_3 {
          leaf bgp-igp-both-ribs {
            type empty;
            description
              "BGP and IGP destinations with routes in both routing tables";
          }
        }
        case case_4 {
          leaf mpls-forwarding {
            type empty;
            description
              "Use MPLS routes for forwarding, not routing";
          }
        }
      }
      container database {
        description
          "Traffic engineering database";
        uses apply-advanced;
        container import {
          description
            "Configure TED import parameters";
          uses apply-advanced;
          container l3-unicast-topology {
            presence "enable l3-unicast-topology";
            description
              "Download L3-Unicast topology into RIB";
            uses apply-advanced;
            leaf bgp-link-state {
              type empty;
              description
                "Export L3-Unicast topology, instead of TE topology, into BGP-LS";
            }
          }
          leaf-list policy {
            type jt:policy-algebra;
            ordered-by user;
            description
              "Configure import policy";
          }
          leaf identifier {
            type union {
              type string {
                pattern "<.*>|$.*";
              }
              type uint64 {
                range "2 .. 18446744073709551615";
              }
            }
            description
              "BGP-TE identifier";
          }
          leaf bgp-ls-identifier {
            type union {
              type uint32;
              type string {
                pattern "<.*>|$.*";
              }
            }
            description
              "BGP-TE domain identifier";
          }
          leaf ipv6 {
            type empty;
            description
              "Import ipv6 addresses";
          }
        }
        container export {
          description
            "Configure TED export related parameters";
          uses apply-advanced;
          leaf-list policy {
            type jt:policy-algebra;
            ordered-by user;
            description
              "Export policy";
          }
          container credibility {
            description
              "TED credibility value for entries from BGP-TE";
            uses apply-advanced;
            leaf unknown {
              type union {
                type string {
                  pattern "<.*>|$.*";
                }
                type uint32 {
                  range "0 .. 512";
                }
              }
              description
                "Entries sourced from unknown entities";
            }
            leaf direct {
              type union {
                type string {
                  pattern "<.*>|$.*";
                }
                type uint32 {
                  range "0 .. 512";
                }
              }
              description
                "Entries sourced from directly connected links";
            }
            leaf static {
              type union {
                type string {
                  pattern "<.*>|$.*";
                }
                type uint32 {
                  range "0 .. 512";
                }
              }
              description
                "Entries sourced from static configuration";
            }
            leaf ospf {
              type union {
                type string {
                  pattern "<.*>|$.*";
                }
                type uint32 {
                  range "0 .. 512";
                }
              }
              description
                "Entries sourced from ospf";
            }
            leaf isis-level-1 {
              type union {
                type string {
                  pattern "<.*>|$.*";
                }
                type uint32 {
                  range "0 .. 512";
                }
              }
              description
                "Entries sourced from ISIS Level 1";
            }
            leaf isis-level-2 {
              type union {
                type string {
                  pattern "<.*>|$.*";
                }
                type uint32 {
                  range "0 .. 512";
                }
              }
              description
                "Entries sourced from ISIS Level 2";
            }
            leaf bgp {
              type union {
                type string {
                  pattern "<.*>|$.*";
                }
                type uint32 {
                  range "0 .. 512";
                }
              }
              description
                "Entries sourced from BGP";
            }
          }
          leaf l3-unicast-topology {
            type empty;
            description
              "Download RIB entries into L3-Unicast topology";
          }
        }
      }
    }
    list admin-groups {
      key "name";
      ordered-by user;
      description
        "Administrative groups";
      leaf name {
        type string;
        description
          "Group name";
      }
      uses apply-advanced;
      leaf group-value {
        type union {
          type string {
            pattern "<.*>|$.*";
          }
          type uint32 {
            range "0 .. 31";
          }
        }
        description
          "Group bit position";
      }
    }
    leaf advertisement-hold-time {
      type union {
        type string {
          pattern "<.*>|$.*";
        }
        type uint32 {
          range "0 .. 65535";
        }
      }
      units "seconds";
      default "5";
      description
        "Time that an 'LSP down' advertisement will be delayed";
    }
    leaf rsvp-error-hold-time {
      type union {
        type string {
          pattern "<.*>|$.*";
        }
        type uint32 {
          range "0 .. 240";
        }
      }
      units "seconds";
      default "25";
      description
        "Time that RSVP PathErr events will be remembered";
    }
    leaf optimize-aggressive {
      type empty;
      description
        "Run aggressive optimization algorithm based on IGP metric only";
    }
    leaf smart-optimize-timer {
      type union {
        type string {
          pattern "<.*>|$.*";
        }
        type int32 {
          range "0 .. 65535";
        }
      }
      units "seconds";
      description
        "Path optimization interval after a link traversed by the path goes down";
    }
    leaf optimize-switchover-delay {
      type union {
        type string {
          pattern "<.*>|$.*";
        }
        type int32 {
          range "1 .. 900";
        }
      }
      units "seconds";
      description
        "Delay before switching LSP to newly optimized path";
    }
    leaf no-propagate-ttl {
      type empty;
      description
        "Disable TTL propagation from IP to MPLS (on push) and MPLS to IP (on pop)";
    }
    leaf explicit-null {
      type empty;
      description
        "Advertise the EXPLICIT_NULL label when the router is the egress";
    }
    leaf icmp-tunneling {
      type empty;
      description
        "Allow MPLS LSPs to be used for tunneling ICMP error packets";
    }
    leaf non-aggressive-make-before-break-cleanup {
      type empty;
      description
        "Defer path-degraded notifys until old instance is deleted";
    }
    leaf revert-timer {
      type union {
        type string {
          pattern "<.*>|$.*";
        }
        type int32 {
          range "0 .. 65535";
        }
      }
      units "seconds";
      description
        "Hold-down window before reverting back to primary path, 0 means disable";
    }
    leaf optimize-hold-dead-delay {
      type union {
        type string {
          pattern "<.*>|$.*";
        }
        type int32 {
          range "0 .. 65535";
        }
      }
      units "seconds";
      description
        "Delay before tearing down the old optimized path";
    }
    leaf cspf-backoff-time {
      type union {
        type string {
          pattern "<.*>|$.*";
        }
        type int32 {
          range "0 .. 65535";
        }
      }
      units "seconds";
      description
        "Delay before CSPF, when there is PathErr on backup path";
    }
    container adaptive-wait-timer {
      presence "enable adaptive-wait-timer";
      description
        "Enable adaptive wait timer for path messages.";
      uses apply-advanced;
      leaf initial-time {
        type union {
          type string {
            pattern "<.*>|$.*";
          }
          type int32 {
            range "180 .. 1800";
          }
        }
        units "seconds";
        default "180";
        description
          "Initial time for adaptive wait timer";
      }
      leaf max-time {
        type union {
          type string {
            pattern "<.*>|$.*";
          }
          type int32 {
            range "180 .. 3600";
          }
        }
        units "seconds";
        default "1800";
        description
          "Maximum time for adaptive wait timer";
      }
      leaf backoff-multiplier {
        type union {
          type string {
            pattern "<.*>|$.*";
          }
          type int32 {
            range "1 .. 5";
          }
        }
        default "2";
        description
          "Multiplier to exponentially backoff the adaptive-wait-timer";
      }
    }
    leaf expand-loose-hop {
      type empty;
      description
        "Perform CSPF path computation to expand loose hops";
    }
    leaf mib-mpls-show-p2mp {
      type empty;
      description
        "Show p2mp tunnels entries in mpls mib walk";
    }
    container bandwidth {
      description
        "Bandwidth to reserve (bps)";
      uses bandwidth-type;
    }
    container admin-group {
      description
        "Administrative group policy";
      uses admin_group_include_exclude;
    }
    container admin-group-extended {
      description
        "Extended administrative group policy";
      uses admin_group_include_exclude;
    }
    container priority {
      presence "enable priority";
      description
        "Preemption priorities";
    }
    leaf setup-priority {
      type union {
        type string {
          pattern "<.*>|$.*";
        }
        type uint32 {
          range "0 .. 7";
        }
      }
      description
        "Set-up priority";
    }
    leaf reservation-priority {
      type union {
        type string {
          pattern "<.*>|$.*";
        }
        type uint32 {
          range "0 .. 7";
        }
      }
      description
        "Reservation priority";
    }
    container oam {
      description
        "Periodic OAM";
      uses periodic_oam;
    }
    leaf class-of-service {
      type union {
        type string {
          pattern "<.*>|$.*";
        }
        type int32 {
          range "0 .. 7";
        }
      }
      description
        "Class-of-service value";
    }
    leaf no-decrement-ttl {
      type empty;
      description
        "Do not decrement the TTL within an LSP";
    }
    leaf hop-limit {
      type union {
        type string {
          pattern "<.*>|$.*";
        }
        type int32 {
          range "2 .. 255";
        }
      }
      description
        "Maximum allowed router hops";
    }
    leaf no-cspf {
      type empty;
      description
        "Disable automatic path computation";
    }
    leaf admin-down {
      type empty;
      description
        "Set GMPLS LSP to administrative down state";
    }
    leaf optimize-timer {
      type union {
        type string {
          pattern "<.*>|$.*";
        }
        type int32 {
          range "0 .. 65535";
        }
      }
      units "seconds";
      description
        "Periodical path reoptimizations";
    }
    leaf preference {
      type union {
        type uint32;
        type string {
          pattern "<.*>|$.*";
        }
      }
      description
        "Preference value";
    }
    choice record-choice {
      leaf record {
        type empty;
        description
          "Record transit routers";
      }
      leaf no-record {
        type empty;
        description
          "Don't record transit routers";
      }
    }
    leaf standby {
      type empty;
      description
        "Keep backup paths in continuous standby";
    }
    leaf exclude-srlg {
      type empty;
      description
        "Exclude SRLG links for secondary path";
    }
    leaf ultimate-hop-popping {
      type empty;
      description
        "Request ultimate hop popping from egress";
    }
    leaf sync-active-path-bandwidth {
      type empty;
      description
        "Signal standby path with bandwidth obtained from active path";
    }
    leaf cross-credibility-cspf {
      type empty;
      description
        "Compute paths across multi-protocol links and nodes";
    }
    leaf top-credibility-only-cspf {
      type empty;
      description
        "Compute paths only using highest credibility links and nodes";
    }
    list label-switched-path {
      key "name";
      ordered-by user;
      description
        "Label-switched path";
      leaf name {
        type string {
          length "1 .. 64";
        }
        description
          "Name of path";
      }
      uses apply-advanced;
      choice enable-disable {
        case case_1 {
          leaf disable {
            type empty;
            description
              "Disable MPLS label-switched path";
          }
        }
      }
      container traceoptions {
        description
          "Trace options for MPLS label-switched path";
        uses apply-advanced;
        container file {
          description
            "Trace file options";
          leaf filename {
            type string {
              length "1 .. 1024";
            }
            description
              "Name of file in which to write trace information";
          }
          leaf replace {
            type empty;
            status deprecated;
            description
              "Replace trace file rather than appending to it";
          }
          leaf size {
            type string;
            description
              "Maximum trace file size";
          }
          leaf files {
            type union {
              type string {
                pattern "<.*>|$.*";
              }
              type uint32 {
                range "2 .. 1000";
              }
            }
            default "10";
            description
              "Maximum number of trace files";
          }
          leaf no-stamp {
            type empty;
            status deprecated;
            description
              "Do not timestamp trace file";
          }
          choice world-readable-choice {
            leaf world-readable {
              type empty;
              description
                "Allow any user to read the log file";
            }
            leaf no-world-readable {
              type empty;
              description
                "Don't allow any user to read the log file";
            }
          }
        }
        list flag {
          key "name";
          ordered-by user;
          description
            "Tracing parameters";
          leaf name {
            type enumeration {
              enum "cspf" {
                description
                  "Trace CSPF computation";
              }
              enum "cspf-node" {
                description
                  "Trace nodes visited during CSPF";
              }
              enum "cspf-link" {
                description
                  "Trace links visited during CSPF";
              }
              enum "cspf-abstract" {
                description
                  "Trace abstract hop based CSPF details";
              }
              enum "state" {
                description
                  "Trace state transitions";
              }
              enum "all" {
                description
                  "Trace everything";
              }
            }
          }
        }
      }
      leaf no-install-to-address {
        type empty;
        description
          "Don't install host route 'to' address into routing tables";
      }
      leaf backup {
        type empty;
        description
          "Use LSP for IGP backup";
      }
      leaf from {
        type jt:ipv4addr;
        description
          "Address of ingress router";
      }
      container pop-and-forward {
        presence "enable pop-and-forward";
        description
          "Enable LSP as pop-and-forward with auto-delegation";
      }
      choice label-switched-path-or-template {
        case case_1 {
          leaf to {
            type jt:ipv4addr;
            description
              "Address of egress router";
          }
        }
        case case_2 {
          leaf template {
            type empty;
            description
              "Template for dynamic lsp paramaters";
          }
        }
      }
      leaf corouted-bidirectional {
        type empty;
        description
          "Setup the LSP as a corouted bidirectional LSP";
      }
      leaf corouted-bidirectional-passive {
        type empty;
        description
          "Associate LSP with incoming corouted bidirectional LSP";
      }
      leaf metric {
        type union {
          type string {
            pattern "<.*>|$.*";
          }
          type uint32 {
            range "1 .. 16777215";
          }
        }
        description
          "Metric value";
      }
      container conditional-metric {
        description
          "Set a conditional metric value for the LSP";
        uses apply-advanced;
        list igp-metric-threshold {
          key "name";
          max-elements 4;
          description
            "Set conditional LSP metric based on IGP metric, up to 4 conditions";
          leaf name {
            type union {
              type string {
                pattern "<.*>|$.*";
              }
              type uint32 {
                range "1 .. 16777215";
              }
            }
            description
              "Conditional IGP metric threshold";
          }
          leaf conditional-metric-value {
            type union {
              type string {
                pattern "<.*>|$.*";
              }
              type uint32 {
                range "1 .. 16777215";
              }
            }
            description
              "Conditional LSP metric value";
          }
        }
      }
      container metric-type {
        description
          "Metric type used for computaion";
        uses apply-advanced;
        choice metric-type-choice {
          case case_1 {
            leaf te {
              type empty;
              description
                "TE metric";
            }
          }
          case case_2 {
            leaf igp {
              type empty;
              description
                "IGP metric";
            }
          }
          case case_3 {
            container delay {
              presence "enable delay";
              description
                "Delay metric";
              uses apply-advanced;
              choice metric-choice {
                case case_1 {
                  leaf minimum {
                    type empty;
                    description
                      "Minimum delay metric type";
                  }
                }
                case case_2 {
                  leaf maximum {
                    type empty;
                    description
                      "Maximum delay metric type";
                  }
                }
                case case_3 {
                  leaf average {
                    type empty;
                    description
                      "Average delay metric type";
                  }
                }
              }
              leaf delay-variation-threshold {
                type union {
                  type string {
                    pattern "<.*>|$.*";
                  }
                  type uint32 {
                    range "1 .. 16777215";
                  }
                }
                description
                  "Link delay variation threshold";
              }
            }
          }
        }
      }
      leaf ldp-tunneling {
        type empty;
        description
          "Allow LDP to use this LSP for tunneling";
      }
      container soft-preemption {
        presence "enable soft-preemption";
        description
          "Attempt make-before-break service while preempting this LSP";
        uses apply-advanced;
      }
      list install {
        key "name";
        ordered-by user;
        description
          "Install prefix";
        leaf name {
          type jt:ipprefix;
          description
            "Destination prefix";
        }
        leaf active {
          type empty;
          description
            "Install prefix into forwarding table";
        }
      }
      leaf retry-timer {
        type union {
          type string {
            pattern "<.*>|$.*";
          }
          type uint32 {
            range "1 .. 600";
          }
        }
        units "seconds";
        description
          "Time before retrying the primary path";
      }
      leaf retry-limit {
        type union {
          type string {
            pattern "<.*>|$.*";
          }
          type uint32 {
            range "0 .. 10000";
          }
        }
        description
          "Maximum number of times to retry primary path";
      }
      leaf revert-timer {
        type union {
          type string {
            pattern "<.*>|$.*";
          }
          type int32 {
            range "0 .. 65535";
          }
        }
        units "seconds";
        description
          "Hold-down window before reverting back to primary path, 0 means disable";
      }
      leaf optimize-hold-dead-delay {
        type union {
          type string {
            pattern "<.*>|$.*";
          }
          type int32 {
            range "0 .. 65535";
          }
        }
        units "seconds";
        description
          "Delay before tearing down the old optimized path";
      }
      leaf cspf-backoff-time {
        type union {
          type string {
            pattern "<.*>|$.*";
          }
          type int32 {
            range "0 .. 65535";
          }
        }
        units "seconds";
        description
          "Delay before CSPF, when there is PathErr on backup path";
      }
      container bandwidth {
        description
          "Bandwidth to reserve (bps)";
        uses bandwidth-type;
      }
      container admin-group {
        description
          "Administrative group policy";
        uses admin_group_include_exclude;
      }
      container admin-group-extended {
        description
          "Extended administrative group policy";
        uses admin_group_include_exclude;
      }
      container priority {
        presence "enable priority";
        description
          "Preemption priorities";
      }
      leaf setup-priority {
        type union {
          type string {
            pattern "<.*>|$.*";
          }
          type uint32 {
            range "0 .. 7";
          }
        }
        description
          "Set-up priority";
      }
      leaf reservation-priority {
        type union {
          type string {
            pattern "<.*>|$.*";
          }
          type uint32 {
            range "0 .. 7";
          }
        }
        description
          "Reservation priority";
      }
      container oam {
        description
          "Periodic OAM";
        uses periodic_oam;
      }
      leaf class-of-service {
        type union {
          type string {
            pattern "<.*>|$.*";
          }
          type int32 {
            range "0 .. 7";
          }
        }
        description
          "Class-of-service value";
      }
      leaf no-decrement-ttl {
        type empty;
        description
          "Do not decrement the TTL within an LSP";
      }
      leaf hop-limit {
        type union {
          type string {
            pattern "<.*>|$.*";
          }
          type int32 {
            range "2 .. 255";
          }
        }
        description
          "Maximum allowed router hops";
      }
      leaf no-cspf {
        type empty;
        description
          "Disable automatic path computation";
      }
      leaf admin-down {
        type empty;
        description
          "Set GMPLS LSP to administrative down state";
      }
      leaf optimize-timer {
        type union {
          type string {
            pattern "<.*>|$.*";
          }
          type int32 {
            range "0 .. 65535";
          }
        }
        units "seconds";
        description
          "Periodical path reoptimizations";
      }
      leaf preference {
        type union {
          type uint32;
          type string {
            pattern "<.*>|$.*";
          }
        }
        description
          "Preference value";
      }
      choice record-choice {
        leaf record {
          type empty;
          description
            "Record transit routers";
        }
        leaf no-record {
          type empty;
          description
            "Don't record transit routers";
        }
      }
      leaf standby {
        type empty;
        description
          "Keep backup paths in continuous standby";
      }
      leaf exclude-srlg {
        type empty;
        description
          "Exclude SRLG links for secondary path";
      }
      leaf ultimate-hop-popping {
        type empty;
        description
          "Request ultimate hop popping from egress";
      }
      leaf sync-active-path-bandwidth {
        type empty;
        description
          "Signal standby path with bandwidth obtained from active path";
      }
      leaf cross-credibility-cspf {
        type empty;
        description
          "Compute paths across multi-protocol links and nodes";
      }
      leaf top-credibility-only-cspf {
        type empty;
        description
          "Compute paths only using highest credibility links and nodes";
      }
      leaf entropy-label {
        type empty;
        description
          "Enable entropy label";
      }
      leaf self-ping-duration {
        type union {
          type string {
            pattern "<.*>|$.*";
          }
          type int32 {
            range "1 .. 65535";
          }
        }
        units "seconds";
        description
          "Duration over which to run self-ping (65535 = until success). Default = 1800s";
      }
      leaf no-self-ping {
        type empty;
        description
          "Do not run self-ping for this LSP";
      }
      choice cspf-attribute {
        case case_1 {
          leaf random {
            type empty;
            description
              "Randomly select among equal-cost paths";
          }
        }
        case case_2 {
          leaf least-fill {
            type empty;
            description
              "Select the least filled among equal-cost paths";
          }
        }
        case case_3 {
          leaf most-fill {
            type empty;
            description
              "Select the most filled among equal-cost paths";
          }
        }
      }
      leaf description {
        type string {
          length "1 .. 80";
        }
        description
          "Text description of label-switched path";
      }
      container adaptive-wait-timer {
        presence "enable adaptive-wait-timer";
        description
          "Enable adaptive wait timer for path messages.";
        uses apply-advanced;
        leaf initial-time {
          type union {
            type string {
              pattern "<.*>|$.*";
            }
            type int32 {
              range "180 .. 1800";
            }
          }
          units "seconds";
          default "180";
          description
            "Initial time for adaptive wait timer";
        }
        leaf max-time {
          type union {
            type string {
              pattern "<.*>|$.*";
            }
            type int32 {
              range "180 .. 3600";
            }
          }
          units "seconds";
          default "1800";
          description
            "Maximum time for adaptive wait timer";
        }
        leaf backoff-multiplier {
          type union {
            type string {
              pattern "<.*>|$.*";
            }
            type int32 {
              range "1 .. 5";
            }
          }
          default "2";
          description
            "Multiplier to exponentially backoff the adaptive-wait-timer";
        }
      }
      choice lp-type {
        case case_1 {
          container link-protection {
            presence "enable link-protection";
            description
              "Protect LSP from link faults only";
            uses apply-advanced;
            choice constraint-choice {
              case case_1 {
                container inherit-lsp {
                  description
                    "Inherit bypass properties from Primary LSPs";
                  leaf constraints {
                    type empty;
                    description
                      "Inherit bypass constraints from primary LSP";
                  }
                }
              }
              case case_2 {
                container bypass-constraints {
                  description
                    "Explicitly defined constraints for bypass LSPs";
                  uses apply-advanced;
                  leaf hop-limit {
                    type union {
                      type string {
                        pattern "<.*>|$.*";
                      }
                      type int32 {
                        range "0 .. 255";
                      }
                    }
                    description
                      "Maximum allowed router hops";
                  }
                  choice include_any_or_no_include_any {
                    case case_1 {
                      leaf no-include-any {
                        type empty;
                        description
                          "Disable include-any checking";
                      }
                    }
                    case case_2 {
                      leaf-list include-any {
                        type string;
                        ordered-by user;
                        description
                          "Groups, one or more of which must be present";
                      }
                    }
                  }
                  choice include_all_or_no_include_all {
                    case case_1 {
                      leaf no-include-all {
                        type empty;
                        description
                          "Disable include-all checking";
                      }
                    }
                    case case_2 {
                      leaf-list include-all {
                        type string;
                        ordered-by user;
                        description
                          "Groups, all of which must be present";
                      }
                    }
                  }
                  choice exclude_or_no_exclude {
                    case case_1 {
                      leaf no-exclude {
                        type empty;
                        description
                          "Disable exclude checking";
                      }
                    }
                    case case_2 {
                      leaf-list exclude {
                        type string;
                        ordered-by user;
                        description
                          "Groups, all of which must be absent";
                      }
                    }
                  }
                }
              }
            }
          }
        }
        case case_2 {
          container node-link-protection {
            presence "enable node-link-protection";
            description
              "Protect LSP from both link and node faults";
            uses apply-advanced;
            choice constraint-choice {
              case case_1 {
                container inherit-lsp {
                  description
                    "Inherit bypass properties from Primary LSPs";
                  leaf constraints {
                    type empty;
                    description
                      "Inherit bypass constraints from primary LSP";
                  }
                }
              }
              case case_2 {
                container bypass-constraints {
                  description
                    "Explicitly defined constraints for bypass LSPs";
                  uses apply-advanced;
                  leaf hop-limit {
                    type union {
                      type string {
                        pattern "<.*>|$.*";
                      }
                      type int32 {
                        range "0 .. 255";
                      }
                    }
                    description
                      "Maximum allowed router hops";
                  }
                  choice include_any_or_no_include_any {
                    case case_1 {
                      leaf no-include-any {
                        type empty;
                        description
                          "Disable include-any checking";
                      }
                    }
                    case case_2 {
                      leaf-list include-any {
                        type string;
                        ordered-by user;
                        description
                          "Groups, one or more of which must be present";
                      }
                    }
                  }
                  choice include_all_or_no_include_all {
                    case case_1 {
                      leaf no-include-all {
                        type empty;
                        description
                          "Disable include-all checking";
                      }
                    }
                    case case_2 {
                      leaf-list include-all {
                        type string;
                        ordered-by user;
                        description
                          "Groups, all of which must be present";
                      }
                    }
                  }
                  choice exclude_or_no_exclude {
                    case case_1 {
                      leaf no-exclude {
                        type empty;
                        description
                          "Disable exclude checking";
                      }
                    }
                    case case_2 {
                      leaf-list exclude {
                        type string;
                        ordered-by user;
                        description
                          "Groups, all of which must be absent";
                      }
                    }
                  }
                }
              }
            }
          }
        }
      }
      leaf inter-domain {
        type empty;
        description
          "Inter-domain LSP";
      }
      leaf adaptive {
        type empty;
        description
          "Have the LSP smoothly cut over to new routes";
      }
      container in-place-lsp-bandwidth-update {
        presence "enable in-place-lsp-bandwidth-update";
        description
          "Update LSP in-place re-using the same LSP identifier";
      }
      container fast-reroute {
        presence "enable fast-reroute";
        description
          "Fast reroute";
        uses apply-advanced;
        leaf hop-limit {
          type union {
            type string {
              pattern "<.*>|$.*";
            }
            type int32 {
              range "0 .. 255";
            }
          }
          description
            "Maximum allowed router hops";
        }
        choice bw-attribute {
          case case_1 {
            leaf bandwidth {
              type string;
              description
                "Bandwidth to reserve (bps)";
            }
          }
          case case_2 {
            leaf bandwidth-percent {
              type union {
                type string {
                  pattern "<.*>|$.*";
                }
                type int32 {
                  range "1 .. 100";
                }
              }
              description
                "Percentage of main path bandwidth to reserve";
            }
          }
        }
        choice include_any_or_no_include_any {
          case case_1 {
            leaf no-include-any {
              type empty;
              description
                "Disable include-any checking";
            }
          }
          case case_2 {
            leaf-list include-any {
              type string;
              ordered-by user;
              description
                "Groups, one or more of which must be present";
            }
          }
        }
        choice include_all_or_no_include_all {
          case case_1 {
            leaf no-include-all {
              type empty;
              description
                "Disable include-all checking";
            }
          }
          case case_2 {
            leaf-list include-all {
              type string;
              ordered-by user;
              description
                "Groups, all of which must be present";
            }
          }
        }
        choice exclude_or_no_exclude {
          case case_1 {
            leaf no-exclude {
              type empty;
              description
                "Disable exclude checking";
            }
          }
          case case_2 {
            leaf-list exclude {
              type string;
              ordered-by user;
              description
                "Groups, all of which must be absent";
            }
          }
        }
      }
      container p2mp {
        presence "enable p2mp";
        description
          "Point-to-multipoint label-switched path";
        leaf path_name {
          type string;
          description
            "Name of point-to-multipoint LSP";
        }
      }
      container auto-bandwidth {
        presence "enable auto-bandwidth";
        description
          "Do auto bandwidth allocation for this LSP";
        uses apply-advanced;
        leaf adjust-interval {
          type union {
            type string {
              pattern "<.*>|$.*";
            }
            type uint32 {
              range "300 .. 315360000";
            }
          }
          units "seconds";
          default "86400";
          description
            "Time to adjust LSP bandwidth";
        }
        leaf adjust-threshold {
          type union {
            type string {
              pattern "<.*>|$.*";
            }
            type uint32 {
              range "0 .. 50";
            }
          }
          units "percent";
          default "0";
          description
            "Percentage change in average LSP utilization to trigger auto-adjustment";
        }
        leaf adjust-threshold-absolute {
          type string;
          units "bps";
          default "0";
          description
            "Change in average LSP utilization to trigger auto-adjustment";
        }
        leaf adjust-threshold-activate-bandwidth {
          type string;
          units "bps";
          description
            "Adjusts signaled bw if greater than this value";
        }
        leaf minimum-bandwidth {
          type string;
          units "bps";
          description
            "Minimum LSP bandwidth";
        }
        leaf maximum-bandwidth {
          type string;
          units "bps";
          description
            "Maximum LSP bandwidth";
        }
        leaf minimum-bandwidth-adjust-interval {
          type union {
            type string {
              pattern "<.*>|$.*";
            }
            type uint32 {
              range "300 .. 31536000";
            }
          }
          units "seconds";
          description
            "Duration for which minimum bandwidth will be frozen";
        }
        leaf minimum-bandwidth-adjust-threshold-change {
          type union {
            type string {
              pattern "<.*>|$.*";
            }
            type uint32 {
              range "0 .. 100";
            }
          }
          units "percent";
          description
            "Change in max average bandwidth to freeze min bandwidth";
        }
        leaf minimum-bandwidth-adjust-threshold-value {
          type string;
          units "bps";
          status deprecated;
          description
            "Freeze min bandwidth if max average bandwidth falls below this bw";
        }
        leaf monitor-bandwidth {
          type empty;
          description
            "Monitor LSP bandwidth without adjustments";
        }
        leaf adjust-threshold-overflow-limit {
          type union {
            type string {
              pattern "<.*>|$.*";
            }
            type uint32 {
              range "1 .. 65535";
            }
          }
          description
            "Number of consecutive overflow samples to trigger auto-adjustment";
        }
        leaf adjust-threshold-underflow-limit {
          type union {
            type string {
              pattern "<.*>|$.*";
            }
            type uint32 {
              range "1 .. 65535";
            }
          }
          description
            "Number of consecutive underflow samples to trigger auto-adjustment";
        }
        leaf resignal-minimum-bandwidth {
          type empty;
          description
            "Resignal the LSP using minimum-bandwidth";
        }
        leaf sync-active-path-bandwidth {
          type empty;
          description
            "Signal standby path with bandwidth obtained from active path";
        }
      }
      container optimize-on-change {
        description
          "Specify additional re-optimization triggers for this LSP";
        uses apply-advanced;
        leaf link-congestion {
          type empty;
          description
            "Optimize when a link becomes congested";
        }
      }
      container deselect-on-bandwidth-failure {
        presence "enable deselect-on-bandwidth-failure";
        description
          "Deselect active path if it cannot meet the bandwidth constraint";
        uses apply-advanced;
        leaf tear-lsp {
          type empty;
          description
            "Bring down active path when all paths fail to reserve required bandwidth";
        }
      }
      container track-igp-metric {
        description
          "Track IGP metric for LSP install prefixes";
        uses apply-advanced;
        leaf install-v4-prefixes {
          type empty;
          description
            "Track IGP metric for IPV4 prefixes";
        }
        leaf install-v6-prefixes {
          type empty;
          description
            "Track IGP metric for IPV6 prefixes";
        }
      }
      container associate-lsp {
        description
          "Associate the LSP for OAM";
        uses apply-advanced;
        leaf lsp-name {
          type string;
          mandatory true;
          description
            "Name of assocation LSP";
        }
        leaf from {
          type jt:ipv4addr;
          description
            "Address of ingress router of associated LSP";
        }
      }
      list primary {
        key "name";
        ordered-by user;
        description
          "Preferred path";
        leaf name {
          type string {
            length "1 .. 64";
          }
          description
            "Name of path";
        }
        uses apply-advanced;
        container bandwidth {
          description
            "Bandwidth to reserve (bps)";
          uses bandwidth-type;
        }
        container admin-group {
          description
            "Administrative group policy";
          uses admin_group_include_exclude;
        }
        container admin-group-extended {
          description
            "Extended administrative group policy";
          uses admin_group_include_exclude;
        }
        container priority {
          presence "enable priority";
          description
            "Preemption priorities";
        }
        leaf setup-priority {
          type union {
            type string {
              pattern "<.*>|$.*";
            }
            type uint32 {
              range "0 .. 7";
            }
          }
          description
            "Set-up priority";
        }
        leaf reservation-priority {
          type union {
            type string {
              pattern "<.*>|$.*";
            }
            type uint32 {
              range "0 .. 7";
            }
          }
          description
            "Reservation priority";
        }
        container oam {
          description
            "Periodic OAM";
          uses periodic_oam;
        }
        leaf class-of-service {
          type union {
            type string {
              pattern "<.*>|$.*";
            }
            type int32 {
              range "0 .. 7";
            }
          }
          description
            "Class-of-service value";
        }
        leaf no-decrement-ttl {
          type empty;
          description
            "Do not decrement the TTL within an LSP";
        }
        leaf hop-limit {
          type union {
            type string {
              pattern "<.*>|$.*";
            }
            type int32 {
              range "2 .. 255";
            }
          }
          description
            "Maximum allowed router hops";
        }
        leaf no-cspf {
          type empty;
          description
            "Disable automatic path computation";
        }
        leaf admin-down {
          type empty;
          description
            "Set GMPLS LSP to administrative down state";
        }
        leaf optimize-timer {
          type union {
            type string {
              pattern "<.*>|$.*";
            }
            type int32 {
              range "0 .. 65535";
            }
          }
          units "seconds";
          description
            "Periodical path reoptimizations";
        }
        leaf preference {
          type union {
            type uint32;
            type string {
              pattern "<.*>|$.*";
            }
          }
          description
            "Preference value";
        }
        choice record-choice {
          leaf record {
            type empty;
            description
              "Record transit routers";
          }
          leaf no-record {
            type empty;
            description
              "Don't record transit routers";
          }
        }
        leaf standby {
          type empty;
          description
            "Keep backup paths in continuous standby";
        }
        leaf exclude-srlg {
          type empty;
          description
            "Exclude SRLG links for secondary path";
        }
        leaf ultimate-hop-popping {
          type empty;
          description
            "Request ultimate hop popping from egress";
        }
        leaf sync-active-path-bandwidth {
          type empty;
          description
            "Signal standby path with bandwidth obtained from active path";
        }
        leaf cross-credibility-cspf {
          type empty;
          description
            "Compute paths across multi-protocol links and nodes";
        }
        leaf top-credibility-only-cspf {
          type empty;
          description
            "Compute paths only using highest credibility links and nodes";
        }
        leaf adaptive {
          type empty;
          description
            "Have the LSP smoothly cut over to new routes";
        }
        leaf select {
          type enumeration {
            enum "manual" {
              description
                "Manual override as preferred active path, if up and stable";
            }
            enum "unconditional" {
              description
                "Unconditional override as preferred active path, regardless of up/down status";
            }
          }
        }
        container upstream-label {
          description
            "Upstream Label for the bidirectional label-switched path";
          uses apply-advanced;
          leaf vlan-id {
            type union {
              type string {
                pattern "<.*>|$.*";
              }
              type uint32 {
                range "1 .. 4094";
              }
            }
            description
              "VLAN ID label for the label-switched path";
          }
        }
        container optimize-on-change {
          description
            "Specify additional re-optimization triggers for this path";
          uses apply-advanced;
          leaf link-congestion {
            type empty;
            description
              "Optimize when a link becomes congested";
          }
        }
      }
      list secondary {
        key "name";
        ordered-by user;
        description
          "Backup path";
        leaf name {
          type string {
            length "1 .. 64";
          }
          description
            "Name of path";
        }
        uses apply-advanced;
        container bandwidth {
          description
            "Bandwidth to reserve (bps)";
          uses bandwidth-type;
        }
        container admin-group {
          description
            "Administrative group policy";
          uses admin_group_include_exclude;
        }
        container admin-group-extended {
          description
            "Extended administrative group policy";
          uses admin_group_include_exclude;
        }
        container priority {
          presence "enable priority";
          description
            "Preemption priorities";
        }
        leaf setup-priority {
          type union {
            type string {
              pattern "<.*>|$.*";
            }
            type uint32 {
              range "0 .. 7";
            }
          }
          description
            "Set-up priority";
        }
        leaf reservation-priority {
          type union {
            type string {
              pattern "<.*>|$.*";
            }
            type uint32 {
              range "0 .. 7";
            }
          }
          description
            "Reservation priority";
        }
        container oam {
          description
            "Periodic OAM";
          uses periodic_oam;
        }
        leaf class-of-service {
          type union {
            type string {
              pattern "<.*>|$.*";
            }
            type int32 {
              range "0 .. 7";
            }
          }
          description
            "Class-of-service value";
        }
        leaf no-decrement-ttl {
          type empty;
          description
            "Do not decrement the TTL within an LSP";
        }
        leaf hop-limit {
          type union {
            type string {
              pattern "<.*>|$.*";
            }
            type int32 {
              range "2 .. 255";
            }
          }
          description
            "Maximum allowed router hops";
        }
        leaf no-cspf {
          type empty;
          description
            "Disable automatic path computation";
        }
        leaf admin-down {
          type empty;
          description
            "Set GMPLS LSP to administrative down state";
        }
        leaf optimize-timer {
          type union {
            type string {
              pattern "<.*>|$.*";
            }
            type int32 {
              range "0 .. 65535";
            }
          }
          units "seconds";
          description
            "Periodical path reoptimizations";
        }
        leaf preference {
          type union {
            type uint32;
            type string {
              pattern "<.*>|$.*";
            }
          }
          description
            "Preference value";
        }
        choice record-choice {
          leaf record {
            type empty;
            description
              "Record transit routers";
          }
          leaf no-record {
            type empty;
            description
              "Don't record transit routers";
          }
        }
        leaf standby {
          type empty;
          description
            "Keep backup paths in continuous standby";
        }
        leaf exclude-srlg {
          type empty;
          description
            "Exclude SRLG links for secondary path";
        }
        leaf ultimate-hop-popping {
          type empty;
          description
            "Request ultimate hop popping from egress";
        }
        leaf sync-active-path-bandwidth {
          type empty;
          description
            "Signal standby path with bandwidth obtained from active path";
        }
        leaf cross-credibility-cspf {
          type empty;
          description
            "Compute paths across multi-protocol links and nodes";
        }
        leaf top-credibility-only-cspf {
          type empty;
          description
            "Compute paths only using highest credibility links and nodes";
        }
        leaf adaptive {
          type empty;
          description
            "Have the LSP smoothly cut over to new routes";
        }
        leaf select {
          type enumeration {
            enum "manual" {
              description
                "Manual override as preferred active path, if up and stable";
            }
            enum "unconditional" {
              description
                "Unconditional override as preferred active path, regardless of up/down status";
            }
          }
        }
        container upstream-label {
          description
            "Upstream Label for the bidirectional label-switched path";
          uses apply-advanced;
          leaf vlan-id {
            type union {
              type string {
                pattern "<.*>|$.*";
              }
              type uint32 {
                range "1 .. 4094";
              }
            }
            description
              "VLAN ID label for the label-switched path";
          }
        }
        container optimize-on-change {
          description
            "Specify additional re-optimization triggers for this path";
          uses apply-advanced;
          leaf link-congestion {
            type empty;
            description
              "Optimize when a link becomes congested";
          }
        }
        container non-active-hold-priority {
          description
            "Non-active hold priority";
          leaf non-active-hold-prio-value {
            type union {
              type string {
                pattern "<.*>|$.*";
              }
              type uint32 {
                range "0 .. 7";
              }
            }
            description
              "Non-active hold priority value";
          }
        }
      }
      container policing {
        description
          "Traffic policing for this LSP";
        leaf no-auto-policing {
          type empty;
          description
            "Turn off automatic policing for this LSP";
        }
      }
      container lsp-external-controller {
        description
          "External path computing entity";
        uses apply-advanced;
        leaf ctrler_name {
          type string;
          mandatory true;
          description
            "Name of the external path computing entity";
        }
        leaf te-metric-bound {
          type union {
            type string {
              pattern "<.*>|$.*";
            }
            type uint32 {
              range "1 .. 4294967295";
            }
          }
          description
            "Maximum metric value, a path can have, for the metric-type TE";
        }
        leaf igp-metric-bound {
          type union {
            type string {
              pattern "<.*>|$.*";
            }
            type uint32 {
              range "1 .. 4294967295";
            }
          }
          description
            "Maximum metric value, a path can have, for the metric-type IGP";
        }
        leaf delay-metric-bound {
          type union {
            type string {
              pattern "<.*>|$.*";
            }
            type uint32 {
              range "1 .. 4294967295";
            }
          }
          description
            "Maximum metric value, a path can have, for the metric-type delay variation";
        }
        container diversity-association {
          description
            "Configure diversity association for LSP";
          uses apply-advanced;
          leaf-list group {
            type string;
            max-elements 8;
            ordered-by user;
            description
              "Configure diversity association group";
          }
          leaf shortest-path-first {
            type empty;
            description
              "Enable priority computation";
          }
        }
        container te-policy-association {
          description
            "Configure te policy association for LSP";
          uses apply-advanced;
          leaf-list group {
            type string;
            max-elements 8;
            ordered-by user;
            description
              "Configure te policy association group";
          }
        }
      }
      leaf associate-backup-pe-groups {
        type empty;
        description
          "Associate this LSP with backup-pe groups";
      }
      leaf egress-protection {
        type empty;
        description
          "Use this LSP for egress protection data transport";
      }
      leaf transport-class {
        type string;
        description
          "Transport class this LSP belongs to";
      }
    }
    container deselect-on-bandwidth-failure {
      presence "enable deselect-on-bandwidth-failure";
      description
        "Deselect active path if it cannot meet the bandwidth constraint";
      uses apply-advanced;
      leaf tear-lsp {
        type empty;
        description
          "Bring down active path when all paths fail to reserve required bandwidth";
      }
    }
    container track-igp-metric {
      description
        "Track IGP metric for LSP install prefixes";
      uses apply-advanced;
      leaf install-v4-prefixes {
        type empty;
        description
          "Track IGP metric for IPV4 prefixes";
      }
      leaf install-v6-prefixes {
        type empty;
        description
          "Track IGP metric for IPV6 prefixes";
      }
    }
    list container-label-switched-path {
      key "name";
      ordered-by user;
      leaf name {
        type string;
        description
          "Name of container-lsp";
      }
      uses apply-advanced;
      choice enable-disable {
        case case_1 {
          leaf disable {
            type empty;
            description
              "Disable MPLS container-label-switched path";
          }
        }
      }
      leaf description {
        type string {
          length "1 .. 80";
        }
        description
          "Text description of label-switched path";
      }
      container label-switched-path-template {
        description
          "Template for dynamic point-to-point LSP parameters";
        uses apply-advanced;
        choice dynamic-template {
          case case_1 {
            leaf template-name {
              type string {
                length "1 .. 64";
              }
              description
                "Name of point-to-point LSP template";
            }
          }
          case case_2 {
            leaf default-template {
              type empty;
              description
                "Use default parameters";
            }
          }
        }
      }
      leaf to {
        type jt:ipv4addr;
        mandatory true;
        description
          "Address of egress router";
      }
      leaf suffix {
        type string {
          length "1 .. 64";
        }
        description
          "Suffix to generate names of members of container LSP";
      }
      container splitting-merging {
        description
          "Do splitting and merging";
        uses apply-advanced;
        leaf maximum-member-lsps {
          type union {
            type string {
              pattern "<.*>|$.*";
            }
            type int32 {
              range "1 .. 64";
            }
          }
          description
            "Maximum number of LSPs";
        }
        leaf minimum-member-lsps {
          type union {
            type string {
              pattern "<.*>|$.*";
            }
            type int32 {
              range "1 .. 64";
            }
          }
          description
            "Minimum number of LSPs";
        }
        leaf splitting-bandwidth {
          type string;
          units "bps";
          description
            "Maximum bandwidth threshold for splitting";
        }
        leaf merging-bandwidth {
          type string;
          units "bps";
          description
            "Minimum bandwidth threshold for merging";
        }
        leaf maximum-signaling-bandwidth {
          type string;
          units "bps";
          description
            "Maximum bandwidth for signaling during normalization";
        }
        leaf minimum-signaling-bandwidth {
          type string;
          units "bps";
          description
            "Minimum bandwidth for signaling during normalization";
        }
        leaf splitting-merging-threshold {
          type union {
            type string {
              pattern "<.*>|$.*";
            }
            type uint32 {
              range "0 .. 100";
            }
          }
          units "percent";
          default "10";
          description
            "Change in aggregate LSP utilization to trigger splitting or merging";
        }
        container normalization {
          description
            "Do normalization";
          uses apply-advanced;
          leaf normalize-interval {
            type union {
              type string {
                pattern "<.*>|$.*";
              }
              type uint32 {
                range "300 .. 315360000";
              }
            }
            units "seconds";
            default "86400";
            description
              "Time to normalize container LSP";
          }
          leaf failover-normalization {
            type empty;
            description
              "Do pre-mature normalization in case some LSPs go down before next normalization";
          }
          leaf no-incremental-normalize {
            type empty;
            description
              "Do not normalize unless all LSPs are successfully signaled";
          }
          leaf normalization-retry-duration {
            type union {
              type string {
                pattern "<.*>|$.*";
              }
              type uint32 {
                range "1 .. 86400";
              }
            }
            units "seconds";
            description
              "Time before retrying the container LSP normalization";
          }
          leaf normalization-retry-limits {
            type union {
              type string {
                pattern "<.*>|$.*";
              }
              type uint32 {
                range "1 .. 1000";
              }
            }
            description
              "Maximum number of times to retry container LSP normalization";
          }
          leaf no-normalize-same-members {
            type empty;
            description
              "Do not normalize when we are not splitting or merging member LSPs";
          }
        }
        container sampling {
          description
            "Sampling information";
          uses apply-advanced;
          leaf cut-off-threshold {
            type union {
              type string {
                pattern "<.*>|$.*";
              }
              type uint32 {
                range "0 .. 100";
              }
            }
            default "0";
            description
              "Cut-off percentile to remove outliers from aggregate samples";
          }
          choice sampling-mode {
            case case_1 {
              leaf use-average-aggregate {
                type empty;
                description
                  "Use average of the samples";
              }
            }
            case case_2 {
              leaf use-percentile {
                type union {
                  type string {
                    pattern "<.*>|$.*";
                  }
                  type uint32 {
                    range "0 .. 100";
                  }
                }
                default "100";
                description
                  "Use a percentile of the samples";
              }
            }
          }
        }
      }
      container lsp-external-controller {
        description
          "External path computing entity";
        uses apply-advanced;
        leaf ctrler_name {
          type string;
          mandatory true;
          description
            "Name of the external path computing entity";
        }
        leaf te-metric-bound {
          type union {
            type string {
              pattern "<.*>|$.*";
            }
            type uint32 {
              range "1 .. 4294967295";
            }
          }
          description
            "Maximum metric value, a path can have, for the metric-type TE";
        }
        leaf igp-metric-bound {
          type union {
            type string {
              pattern "<.*>|$.*";
            }
            type uint32 {
              range "1 .. 4294967295";
            }
          }
          description
            "Maximum metric value, a path can have, for the metric-type IGP";
        }
        leaf delay-metric-bound {
          type union {
            type string {
              pattern "<.*>|$.*";
            }
            type uint32 {
              range "1 .. 4294967295";
            }
          }
          description
            "Maximum metric value, a path can have, for the metric-type delay variation";
        }
        container diversity-association {
          description
            "Configure diversity association for LSP";
          uses apply-advanced;
          leaf-list group {
            type string;
            max-elements 8;
            ordered-by user;
            description
              "Configure diversity association group";
          }
          leaf shortest-path-first {
            type empty;
            description
              "Enable priority computation";
          }
        }
        container te-policy-association {
          description
            "Configure te policy association for LSP";
          uses apply-advanced;
          leaf-list group {
            type string;
            max-elements 8;
            ordered-by user;
            description
              "Configure te policy association group";
          }
        }
      }
    }
    list transit-lsp-association {
      key "name";
      ordered-by user;
      description
        "Transit label switch path assoication";
      leaf name {
        type string;
        description
          "Name of transit assocation LSP group";
      }
      uses apply-advanced;
      leaf lsp-name-1 {
        type string;
        description
          "Name of assocation LSP 1";
      }
      leaf from-1 {
        type jt:ipv4addr;
        description
          "Address of associated LSP 1";
      }
      leaf lsp-name-2 {
        type string;
        description
          "Name of assocation LSP 2";
      }
      leaf from-2 {
        type jt:ipv4addr;
        description
          "Address of associated LSP 2";
      }
    }
    list exclude-hops {
      key "name";
      ordered-by user;
      description
        "List of routers to exclude in a label-switched path";
      leaf name {
        type string;
        description
          "Name of exclude-hops";
      }
      uses apply-advanced;
      list exclude-hop-list {
        key "name";
        description
          "List of routers in the label-switched path";
        leaf name {
          type jt:ipv4addr;
          description
            "Address of routers to exclude";
        }
      }
    }
    list path {
      key "name";
      ordered-by user;
      description
        "Route of a label-switched path";
      leaf name {
        type string;
        description
          "Name of label-switched path";
      }
      uses apply-advanced;
      container exclude {
        presence "enable exclude";
        description
          "Name of the list of routers to exclude in the label-switched path";
        uses apply-advanced;
        leaf exclude-name {
          type string;
          mandatory true;
          description
            "Name of exclude-hops";
        }
      }
      list path-list {
        key "name";
        ordered-by user;
        description
          "List of routers in the label-switched path";
        leaf name {
          type string;
          description
            "Address of next system in path";
        }
        leaf abstract {
          type empty;
          description
            "Next system in path is abstract";
        }
        choice loose_strict_none {
          case case_1 {
            leaf loose {
              type empty;
              description
                "Next hop might not be adjacent";
            }
          }
          case case_2 {
            leaf loose-link {
              type empty;
              description
                "Next hop link might not be adjacent";
            }
          }
          case case_3 {
            leaf strict {
              type empty;
              description
                "Next hop must be adjacent";
            }
          }
        }
      }
    }
    list constituent-list {
      key "name";
      ordered-by user;
      description
        "MPLS constituent list for abstract hops";
      leaf name {
        type string;
        description
          "Constituent list name";
      }
      uses apply-advanced;
      leaf-list srlg {
        type string;
        max-elements 16;
        ordered-by user;
        description
          "SRLG Name";
      }
      leaf-list admin-group {
        type string;
        max-elements 16;
        ordered-by user;
        description
          "Administrative groups";
      }
      leaf-list admin-group-extended {
        type string;
        max-elements 16;
        ordered-by user;
        description
          "Extended administrative groups";
      }
    }
    list abstract-hop {
      key "name";
      ordered-by user;
      description
        "MPLS abstract hop";
      leaf name {
        type string;
        description
          "Abstract hop name";
      }
      uses apply-advanced;
      leaf operator {
        type enumeration {
          enum "AND" {
            description
              "AND";
          }
          enum "OR" {
            description
              "OR";
          }
        }
        mandatory true;
        description
          "Operation among constituent lists";
      }
      list constituent-list {
        key "name";
        ordered-by user;
        description
          "Building abstract hop using constituent lists";
        leaf name {
          type string {
            length "1 .. 64";
          }
          description
            "Constituent list name";
        }
        uses apply-advanced;
        choice list-type {
          case case_1 {
            leaf include-any-list {
              type empty;
              description
                "Include any";
            }
          }
          case case_2 {
            leaf include-all-list {
              type empty;
              description
                "Include all";
            }
          }
          case case_3 {
            leaf exclude-any-list {
              type empty;
              description
                "Exclude any";
            }
          }
          case case_4 {
            leaf exclude-all-list {
              type empty;
              description
                "Exclude all";
            }
          }
        }
      }
    }
    container egress-protection {
      description
        "Egress router protection";
      uses apply-advanced;
      list context-identifier {
        key "name";
        description
          "Context identifier";
        leaf name {
          type jt:ipv4addr;
          description
            "IP address";
        }
        uses apply-advanced;
        choice context-type {
          case case_1 {
            leaf primary {
              type empty;
              description
                "Primary";
            }
          }
          case case_2 {
            leaf protector {
              type empty;
              description
                "Protector";
            }
          }
        }
        leaf metric {
          type union {
            type string {
              pattern "<.*>|$.*";
            }
            type uint32 {
              range "2 .. 16777215";
            }
          }
          description
            "IGP metric";
        }
        leaf advertise-mode {
          type enumeration {
            enum "stub-proxy" {
              description
                "Proxy";
            }
            enum "stub-alias" {
              description
                "Alias";
            }
          }
          description
            "Advertise mode";
        }
        leaf-list admin-group {
          type string;
          ordered-by user;
          description
            "Administrative groups";
        }
      }
      container traceoptions {
        description
          "Trace options for egress-protection";
        uses apply-advanced;
        container file {
          description
            "Trace file options";
          leaf filename {
            type string {
              length "1 .. 1024";
            }
            description
              "Name of file in which to write trace information";
          }
          leaf replace {
            type empty;
            status deprecated;
            description
              "Replace trace file rather than appending to it";
          }
          leaf size {
            type string;
            description
              "Maximum trace file size";
          }
          leaf files {
            type union {
              type string {
                pattern "<.*>|$.*";
              }
              type uint32 {
                range "2 .. 1000";
              }
            }
            default "10";
            description
              "Maximum number of trace files";
          }
          leaf no-stamp {
            type empty;
            status deprecated;
            description
              "Do not timestamp trace file";
          }
          choice world-readable-choice {
            leaf world-readable {
              type empty;
              description
                "Allow any user to read the log file";
            }
            leaf no-world-readable {
              type empty;
              description
                "Don't allow any user to read the log file";
            }
          }
        }
        list flag {
          key "name";
          ordered-by user;
          description
            "Tracing parameters";
          leaf name {
            type enumeration {
              enum "state" {
                description
                  "Trace state transitions";
              }
              enum "route" {
                description
                  "Trace route transitions";
              }
              enum "error" {
                description
                  "Trace error conditions";
              }
              enum "all" {
                description
                  "Trace everything";
              }
            }
          }
        }
      }
    }
    container label-range {
      description
        "MPLS labels ranges";
      uses apply-advanced;
      list lsi-label-range {
        key "name";
        ordered-by user;
        description
          "LSI-label-range";
        leaf name {
          type union {
            type string {
              pattern "<.*>|$.*";
            }
            type uint32 {
              range "16 .. 1048575";
            }
          }
          description
            "Label_range_start";
        }
        leaf range-end {
          type union {
            type string {
              pattern "<.*>|$.*";
            }
            type uint32 {
              range "16 .. 1048575";
            }
          }
          description
            "Label_range_end";
        }
      }
      list dynamic-label-range {
        key "name";
        ordered-by user;
        description
          "Dynamic-label-range";
        leaf name {
          type union {
            type string {
              pattern "<.*>|$.*";
            }
            type uint32 {
              range "16 .. 1048575";
            }
          }
          description
            "Label_range_start";
        }
        leaf range-end {
          type union {
            type string {
              pattern "<.*>|$.*";
            }
            type uint32 {
              range "16 .. 1048575";
            }
          }
          description
            "Label_range_end";
        }
      }
      list block-label-range {
        key "name";
        ordered-by user;
        description
          "Block-label-range";
        leaf name {
          type union {
            type string {
              pattern "<.*>|$.*";
            }
            type uint32 {
              range "16 .. 1048575";
            }
          }
          description
            "Label_range_start";
        }
        leaf range-end {
          type union {
            type string {
              pattern "<.*>|$.*";
            }
            type uint32 {
              range "16 .. 1048575";
            }
          }
          description
            "Label_range_end";
        }
      }
      list srgb-label-range {
        key "name";
        max-elements 1;
        ordered-by user;
        description
          "SRGB-label-range";
        leaf name {
          type union {
            type string {
              pattern "<.*>|$.*";
            }
            type uint32 {
              range "16 .. 1048575";
            }
          }
          description
            "Label_range_start";
        }
        leaf range-end {
          type union {
            type string {
              pattern "<.*>|$.*";
            }
            type uint32 {
              range "16 .. 1048575";
            }
          }
          description
            "Label_range_end";
        }
      }
      leaf label-limit {
        type union {
          type string {
            pattern "<.*>|$.*";
          }
          type uint32 {
            range "0 .. 1048575";
          }
        }
        description
          "Limit for the number of concurrent active labels";
      }
      list static-label-range {
        key "name";
        ordered-by user;
        description
          "Static-label-range";
        leaf name {
          type union {
            type string {
              pattern "<.*>|$.*";
            }
            type uint32 {
              range "16 .. 1048575";
            }
          }
          description
            "Label_range_start";
        }
        leaf range-end {
          type union {
            type string {
              pattern "<.*>|$.*";
            }
            type uint32 {
              range "16 .. 1048575";
            }
          }
          description
            "Label_range_end";
        }
      }
    }
    choice enable-disable {
      case case_1 {
        leaf disable {
          type empty;
          description
            "Disable MPLS";
        }
      }
    }
    container label-history {
      presence "enable label-history";
      description
        "MPLS label history recording";
      uses apply-advanced;
      leaf max-entries {
        type union {
          type string {
            pattern "<.*>|$.*";
          }
          type uint32 {
            range "1 .. 4294967295";
          }
        }
        description
          "Limit for the number of history entry per label";
      }
    }
    container traceoptions {
      description
        "Trace options for MPLS";
      uses apply-advanced;
      container file {
        description
          "Trace file options";
        leaf filename {
          type string {
            length "1 .. 1024";
          }
          description
            "Name of file in which to write trace information";
        }
        leaf replace {
          type empty;
          status deprecated;
          description
            "Replace trace file rather than appending to it";
        }
        leaf size {
          type string;
          description
            "Maximum trace file size";
        }
        leaf files {
          type union {
            type string {
              pattern "<.*>|$.*";
            }
            type uint32 {
              range "2 .. 1000";
            }
          }
          default "10";
          description
            "Maximum number of trace files";
        }
        leaf no-stamp {
          type empty;
          status deprecated;
          description
            "Do not timestamp trace file";
        }
        choice world-readable-choice {
          leaf world-readable {
            type empty;
            description
              "Allow any user to read the log file";
          }
          leaf no-world-readable {
            type empty;
            description
              "Don't allow any user to read the log file";
          }
        }
      }
      list flag {
        key "name";
        ordered-by user;
        description
          "Tracing parameters";
        leaf name {
          type enumeration {
            enum "connection" {
              description
                "Trace CCC activity";
            }
            enum "connection-detail" {
              description
                "Trace CCC activity in detail";
            }
            enum "cspf" {
              description
                "Trace CSPF computation";
            }
            enum "cspf-node" {
              description
                "Trace nodes visited during CSPF";
            }
            enum "cspf-link" {
              description
                "Trace links visited during CSPF";
            }
            enum "cspf-abstract" {
              description
                "Trace abstract hop based CSPF details";
            }
            enum "state" {
              description
                "Trace state transitions";
            }
            enum "error" {
              description
                "Trace error conditions";
            }
            enum "lsping" {
              description
                "Trace LSP ping packets received";
            }
            enum "graceful-restart" {
              description
                "Trace graceful-restart-related events";
            }
            enum "nsr-synchronization" {
              description
                "Trace NSR synchronization events";
            }
            enum "nsr-synchronization-detail" {
              description
                "Trace NSR synchronization events in detail";
            }
            enum "static" {
              description
                "Trace static label-switched path";
            }
            enum "egress-protection" {
              description
                "Trace egress protection events";
            }
            enum "all" {
              description
                "Trace everything";
            }
            enum "autobw-state" {
              description
                "Trace autobandwidth events in mpls trace";
            }
            enum "externally-controlled-lsp" {
              description
                "Trace externally controlled LSP events in mpls trace";
            }
            enum "ted-import" {
              description
                "Trace leaking TED entries into lsdist.0 table";
            }
            enum "ted-export" {
              description
                "Trace leaking of entries from lsdist.0 table into TED";
            }
            enum "lsp-history" {
              description
                "Trace LSP history events";
            }
            enum "abstract-hop" {
              description
                "Trace abstract hop related events";
            }
            enum "remote-pce" {
              description
                "Trace cPCE events in mpls trace";
            }
          }
        }
      }
    }
    leaf ipv6-tunneling {
      type empty;
      description
        "Allow MPLS LSPs to be used for tunneling IPv6 traffic";
    }
    list interface {
      key "name";
      ordered-by user;
      description
        "MPLS interface options";
      uses juniper-protocols-mpls-interface;
    }
    list static-label-switched-path {
      key "name";
      ordered-by user;
      description
        "Static label-switched path";
      leaf name {
        type string {
          length "1 .. 64";
        }
        description
          "Name of path";
      }
      uses apply-advanced;
      choice lsp-type {
        case case_1 {
          container bypass {
            description
              "Bypass ingress label-switched path";
            uses apply-advanced;
            leaf bandwidth {
              type string;
              units "bps";
              description
                "Bandwidth to reserve";
            }
            leaf description {
              type string {
                length "1 .. 80";
              }
              description
                "Text description of label-switched path";
            }
            leaf next-hop {
              type union {
                type jt:ipaddr-or-interface;
                type string {
                  pattern "<.*>|$.*";
                }
              }
              description
                "IPv4 or IPv6 address or interface of next-hop router";
            }
            leaf next-table {
              type string;
              description
                "Next-table for lookup";
            }
            leaf push {
              type union {
                type string {
                  pattern "<.*>|$.*";
                }
                type uint32 {
                  range "0 .. 1048575";
                }
              }
              description
                "Label to push";
            }
            leaf to {
              type jt:ipaddr;
              mandatory true;
              description
                "Address of egress router";
            }
          }
        }
        case case_2 {
          list transit {
            key "name";
            ordered-by user;
            description
              "Transit label-switched path";
            leaf name {
              type union {
                type string {
                  pattern "<.*>|$.*";
                }
                type uint32 {
                  range "16 .. 1048575";
                }
              }
              description
                "Incoming label value";
            }
            uses apply-advanced;
            leaf bandwidth {
              type string;
              units "bps";
              description
                "Bandwidth to reserve";
            }
            leaf description {
              type string {
                length "1 .. 80";
              }
              description
                "Text description of label-switched path";
            }
            container link-protection {
              description
                "Bypass link protection";
              leaf bypass-name {
                type string {
                  length "1 .. 64";
                }
                mandatory true;
                description
                  "Bypass label-switched path name";
              }
            }
            leaf next-hop {
              type union {
                type jt:ipaddr-or-interface;
                type string {
                  pattern "<.*>|$.*";
                }
              }
              mandatory true;
              description
                "IPv4 or IPv6 address or interface of next-hop router";
            }
            leaf member-interface {
              type union {
                type jt:interface-unit;
                type string {
                  pattern "<.*>|$.*";
                }
              }
              description
                "AE member interface name";
            }
            container node-protection {
              description
                "Bypass node protection";
              leaf bypass-name {
                type string {
                  length "1 .. 64";
                }
                mandatory true;
                description
                  "Bypass label-switched path name";
              }
              leaf next-next-label {
                type union {
                  type string {
                    pattern "<.*>|$.*";
                  }
                  type uint32 {
                    range "0 .. 1048575";
                  }
                }
                description
                  "Label expected by next-next-hop";
              }
            }
            choice label-action {
              case case_1 {
                leaf swap {
                  type union {
                    type string {
                      pattern "<.*>|$.*";
                    }
                    type uint32 {
                      range "0 .. 1048575";
                    }
                  }
                  description
                    "Swap top label with this label";
                }
              }
              case case_2 {
                leaf pop {
                  type empty;
                  description
                    "Pop the top label";
                }
              }
              case case_3 {
                leaf stitch {
                  type empty;
                  description
                    "Swap top label with the resolved LSP";
                }
              }
            }
          }
        }
        case case_3 {
          container ingress {
            description
              "Ingress LSR configuration for a static LSP";
            uses apply-advanced;
            leaf bandwidth {
              type string;
              units "bps";
              description
                "Bandwidth to reserve";
            }
            leaf class-of-service {
              type union {
                type string {
                  pattern "<.*>|$.*";
                }
                type int32 {
                  range "0 .. 7";
                }
              }
              description
                "Class-of-service value";
            }
            leaf description {
              type string {
                length "1 .. 80";
              }
              description
                "Text description of label-switched path";
            }
            list install {
              key "name";
              ordered-by user;
              description
                "Install prefix";
              leaf name {
                type jt:ipv4prefix;
                description
                  "Destination prefix";
              }
              leaf active {
                type empty;
                description
                  "Install prefix into forwarding table";
              }
            }
            leaf metric {
              type union {
                type string {
                  pattern "<.*>|$.*";
                }
                type uint32 {
                  range "1 .. 16777215";
                }
              }
              description
                "Metric value";
            }
            leaf next-hop {
              type union {
                type jt:ipv4addr-or-interface;
                type string {
                  pattern "<.*>|$.*";
                }
              }
              mandatory true;
              description
                "IPv4 address or interface of next-hop router";
            }
            container link-protection {
              description
                "Bypass link protection";
              leaf bypass-name {
                type string {
                  length "1 .. 64";
                }
                mandatory true;
                description
                  "Bypass label-switched path name";
              }
            }
            container node-protection {
              description
                "Bypass node protection";
              leaf bypass-name {
                type string {
                  length "1 .. 64";
                }
                mandatory true;
                description
                  "Bypass label-switched path name";
              }
              leaf next-next-label {
                type union {
                  type string {
                    pattern "<.*>|$.*";
                  }
                  type uint32 {
                    range "0 .. 1048575";
                  }
                }
                description
                  "Label expected by next-next-hop";
              }
            }
            leaf no-install-to-address {
              type empty;
              description
                "Don't install host route 'to' address into routing tables";
            }
            container policing {
              description
                "Traffic policing for this LSP";
              leaf filter {
                type string;
                description
                  "Name of filter to use for policing LSP traffic";
              }
              leaf no-auto-policing {
                type empty;
                description
                  "Turn off automatic policing for this LSP";
              }
            }
            leaf preference {
              type union {
                type uint32;
                type string {
                  pattern "<.*>|$.*";
                }
              }
              description
                "Preference value";
            }
            leaf to {
              type jt:ipv4addr;
              mandatory true;
              description
                "Address of egress router";
            }
            leaf push {
              type union {
                type string {
                  pattern "<.*>|$.*";
                }
                type uint32 {
                  range "0 .. 1048575";
                }
              }
              description
                "Label to push";
            }
            leaf entropy-label {
              type empty;
              description
                "Enable entropy label";
            }
          }
        }
        case case_4;
      }
    }
  }

  grouping bandwidth-type {
    uses apply-advanced;
    leaf per-traffic-class-bandwidth {
      type string;
      units "bps";
      description
        "Bandwidth to reserve";
    }
    leaf ct0 {
      type string;
      units "bps";
      description
        "Bandwidth from traffic class 0";
    }
    leaf ct1 {
      type string;
      units "bps";
      description
        "Bandwidth from traffic class 1";
    }
    leaf ct2 {
      type string;
      units "bps";
      description
        "Bandwidth from traffic class 2";
    }
    leaf ct3 {
      type string;
      units "bps";
      description
        "Bandwidth from traffic class 3";
    }
  }

  grouping juniper-protocols-mpls-interface {
    leaf name {
      type union {
        type jt:interface-name;
        type string {
          pattern "<.*>|$.*";
        }
      }
      description
        "Interface name";
    }
    uses apply-advanced;
    choice enable-disable {
      case case_1 {
        leaf disable {
          type empty;
          description
            "Disable MPLS on this interface";
        }
      }
    }
    leaf-list srlg {
      type string;
      max-elements 64;
      ordered-by user;
      description
        "SRLG Name";
    }
    leaf always-mark-connection-protection-tlv {
      type empty;
      description
        "Mark connection protection tlv on this interface";
    }
    leaf switch-away-lsps {
      type empty;
      description
        "Switch away protected LSPs to their bypass LSPs";
    }
    leaf-list admin-group {
      type string;
      ordered-by user;
      description
        "Administrative groups";
    }
    leaf-list admin-group-extended {
      type string;
      ordered-by user;
      description
        "Extended administrative groups";
    }
    container static {
      description
        "Static label-switch path related configurations";
      uses apply-advanced;
      leaf protection-revert-time {
        type union {
          type string {
            pattern "<.*>|$.*";
          }
          type uint32 {
            range "0 .. 65535";
          }
        }
        units "seconds";
        description
          "FRR revert wait time, 0 means disable";
      }
    }
  }

  grouping juniper-protocols-mvrp {
    description
      "MVRP Configuration";
    uses apply-advanced;
    container traceoptions {
      description
        "Tracing options for MVRP";
      uses mrp-trace-options;
    }
    leaf join-timer {
      type union {
        type string {
          pattern "<.*>|$.*";
        }
        type uint16 {
          range "100 .. 500";
        }
      }
      units "milliseconds";
      default "200";
      description
        "Join timer interval";
    }
    leaf leave-timer {
      type union {
        type string {
          pattern "<.*>|$.*";
        }
        type uint16 {
          range "300 .. 1000";
        }
      }
      units "milliseconds";
      default "800";
      description
        "Leave timer interval";
    }
    leaf leaveall-timer {
      type union {
        type string {
          pattern "<.*>|$.*";
        }
        type uint16 {
          range "10 .. 60";
        }
      }
      units "seconds";
      default "10";
      description
        "Leaveall timer interval";
    }
    leaf no-dynamic-vlan {
      type empty;
      description
        "Disable dynamic VLAN creation";
    }
    leaf no-attribute-length-in-pdu {
      type empty;
      description
        "No attribute length while sending pdu ";
    }
    leaf bpdu-destination-mac-address {
      type enumeration {
        enum "provider-bridge-group" {
          description
            "802.1ad provider bridge group address";
        }
      }
      description
        "Destination MAC address in the MVRP BPDUs";
    }
    list interface {
      key "name";
      ordered-by user;
      description
        "Configure interface options";
      leaf name {
        type union {
          type jt:interface-device;
          type string {
            pattern "<.*>|$.*";
          }
        }
        description
          "Interface name";
      }
      uses apply-advanced;
      leaf join-timer {
        type union {
          type string {
            pattern "<.*>|$.*";
          }
          type uint16 {
            range "100 .. 500";
          }
        }
        units "milliseconds";
        description
          "Join timer interval";
      }
      leaf leave-timer {
        type union {
          type string {
            pattern "<.*>|$.*";
          }
          type uint16 {
            range "300 .. 1000";
          }
        }
        units "milliseconds";
        description
          "Leave timer interval";
      }
      leaf leaveall-timer {
        type union {
          type string {
            pattern "<.*>|$.*";
          }
          type uint16 {
            range "10 .. 60";
          }
        }
        units "seconds";
        description
          "Leaveall timer interval";
      }
      leaf point-to-point {
        type empty;
        description
          "Port is point to point";
      }
      leaf registration {
        type enumeration {
          enum "normal" {
            description
              "Normal registration mode";
          }
          enum "restricted" {
            description
              "Restricted registration mode";
          }
          enum "forbidden" {
            description
              "Forbidden registration mode";
          }
        }
        default "normal";
        description
          "Registration mode";
      }
    }
  }

  grouping juniper-protocols-ospf {
    uses apply-advanced;
    list topology {
      key "name";
      ordered-by user;
      description
        "Topology parameters";
      leaf name {
        type string;
        description
          "Topology name";
      }
      uses apply-advanced;
      leaf disable {
        type empty;
        description
          "Disable this topology";
      }
      leaf topology-id {
        type union {
          type string {
            pattern "<.*>|$.*";
          }
          type uint8 {
            range "32 .. 127";
          }
        }
        description
          "Topology identifier";
      }
      leaf overload {
        type empty;
        description
          "Set the overload mode (repel transit traffic)";
      }
      leaf rib-group {
        type string;
        description
          "Routing table group for importing routes";
      }
      container spf-options {
        description
          "Configure options for SPF";
        uses apply-advanced;
        container microloop-avoidance {
          description
            "Configure microloop avoidance mechanism";
          uses apply-advanced;
          container post-convergence-path {
            presence "enable post-convergence-path";
            description
              "Temporarily install post-convergence path for routes potentially affected by microloops";
            uses apply-advanced;
            leaf delay {
              type union {
                type string {
                  pattern "<.*>|$.*";
                }
                type uint32 {
                  range "500 .. 60000";
                }
              }
              units "milliseconds";
              description
                "Time after which temporary post-convergence paths are removed";
            }
            leaf maximum-labels {
              type union {
                type string {
                  pattern "<.*>|$.*";
                }
                type uint32 {
                  range "2 .. 8";
                }
              }
              description
                "Maximum number of labels installed for post-convergence paths";
            }
          }
        }
        leaf delay {
          type union {
            type string {
              pattern "<.*>|$.*";
            }
            type uint32 {
              range "50 .. 8000";
            }
          }
          units "milliseconds";
          description
            "Time to wait before running an SPF";
        }
        leaf holddown {
          type union {
            type string {
              pattern "<.*>|$.*";
            }
            type uint32 {
              range "2000 .. 20000";
            }
          }
          units "milliseconds";
          description
            "Time to hold down before running an SPF";
        }
        leaf rapid-runs {
          type union {
            type string {
              pattern "<.*>|$.*";
            }
            type uint32 {
              range "1 .. 10";
            }
          }
          description
            "Number of maximum rapid SPF runs before holddown";
        }
        leaf no-ignore-our-externals {
          type empty;
          description
            "Do not ignore self-generated external and NSSA LSAs";
        }
        container multipath {
          description
            "Configure multipath options";
          uses apply-advanced;
          container weighted {
            description
              "Weighted multipath options";
            uses apply-advanced;
            leaf one-hop {
              type empty;
              description
                "Enable load balancing on onehop multipath based on interface bandwidth";
            }
          }
        }
      }
      container backup-spf-options {
        description
          "Configure options for backup SPF";
        uses apply-advanced;
        container remote-backup-calculation {
          presence "enable remote-backup-calculation";
          description
            "Calculate Remote LFA backup nexthops";
          uses apply-advanced;
          container pq-nodes-nearest-to-source {
            description
              "PQ nodes selection based upon nearest to source";
            uses apply-advanced;
            leaf percent {
              type union {
                type string {
                  pattern "<.*>|$.*";
                }
                type uint32 {
                  range "10 .. 100";
                }
              }
              description
                "Selection percentage for nearest to source";
            }
          }
        }
        container use-post-convergence-lfa {
          presence "enable use-post-convergence-lfa";
          description
            "Calculate post-convergence backup paths";
          uses apply-advanced;
          leaf maximum-labels {
            type union {
              type string {
                pattern "<.*>|$.*";
              }
              type uint32 {
                range "2 .. 8";
              }
            }
            description
              "Maximum number of labels installed for post-convergence paths";
          }
          leaf maximum-backup-paths {
            type union {
              type string {
                pattern "<.*>|$.*";
              }
              type uint32 {
                range "1 .. 8";
              }
            }
            description
              "Maximum number of equal-cost post-convergence paths installed";
          }
        }
        leaf use-source-packet-routing {
          type empty;
          description
            "Use spring backup paths for inet.0 routes";
        }
        leaf disable {
          type empty;
          description
            "Do not run backup SPF";
        }
        leaf no-install {
          type empty;
          description
            "Do not install backup nexthops into the RIB";
        }
        leaf downstream-paths-only {
          type empty;
          description
            "Use only downstream backup paths";
        }
        container per-prefix-calculation {
          description
            "Calculate backup nexthops for non-best prefix originators";
          uses apply-advanced;
          leaf stubs {
            type empty;
            description
              "Per prefix calculation for stubs only";
          }
          leaf summary {
            type empty;
            description
              "Per prefix calculation for summary originators only";
          }
          leaf externals {
            type empty;
            description
              "Per prefix calculation for externals";
          }
          leaf all {
            type empty;
            description
              "Per prefix calculation for all";
          }
        }
        leaf node-link-degradation {
          type empty;
          description
            "Degrade to link protection when nodelink protection not available";
        }
      }
      leaf prefix-export-limit {
        type union {
          type string {
            pattern "<.*>|$.*";
          }
          type uint32 {
            range "0 .. 4294967295";
          }
        }
        description
          "Maximum number of prefixes that can be exported";
      }
    }
    container spf-options {
      description
        "Configure options for SPF";
      uses apply-advanced;
      container microloop-avoidance {
        description
          "Configure microloop avoidance mechanism";
        uses apply-advanced;
        container post-convergence-path {
          presence "enable post-convergence-path";
          description
            "Temporarily install post-convergence path for routes potentially affected by microloops";
          uses apply-advanced;
          leaf delay {
            type union {
              type string {
                pattern "<.*>|$.*";
              }
              type uint32 {
                range "500 .. 60000";
              }
            }
            units "milliseconds";
            description
              "Time after which temporary post-convergence paths are removed";
          }
          leaf maximum-labels {
            type union {
              type string {
                pattern "<.*>|$.*";
              }
              type uint32 {
                range "2 .. 8";
              }
            }
            description
              "Maximum number of labels installed for post-convergence paths";
          }
        }
      }
      leaf delay {
        type union {
          type string {
            pattern "<.*>|$.*";
          }
          type uint32 {
            range "50 .. 8000";
          }
        }
        units "milliseconds";
        description
          "Time to wait before running an SPF";
      }
      leaf holddown {
        type union {
          type string {
            pattern "<.*>|$.*";
          }
          type uint32 {
            range "2000 .. 20000";
          }
        }
        units "milliseconds";
        description
          "Time to hold down before running an SPF";
      }
      leaf rapid-runs {
        type union {
          type string {
            pattern "<.*>|$.*";
          }
          type uint32 {
            range "1 .. 10";
          }
        }
        description
          "Number of maximum rapid SPF runs before holddown";
      }
      leaf no-ignore-our-externals {
        type empty;
        description
          "Do not ignore self-generated external and NSSA LSAs";
      }
      container multipath {
        description
          "Configure multipath options";
        uses apply-advanced;
        container weighted {
          description
            "Weighted multipath options";
          uses apply-advanced;
          leaf one-hop {
            type empty;
            description
              "Enable load balancing on onehop multipath based on interface bandwidth";
          }
        }
      }
    }
    container backup-spf-options {
      description
        "Configure options for backup SPF";
      uses apply-advanced;
      container remote-backup-calculation {
        presence "enable remote-backup-calculation";
        description
          "Calculate Remote LFA backup nexthops";
        uses apply-advanced;
        container pq-nodes-nearest-to-source {
          description
            "PQ nodes selection based upon nearest to source";
          uses apply-advanced;
          leaf percent {
            type union {
              type string {
                pattern "<.*>|$.*";
              }
              type uint32 {
                range "10 .. 100";
              }
            }
            description
              "Selection percentage for nearest to source";
          }
        }
      }
      container use-post-convergence-lfa {
        presence "enable use-post-convergence-lfa";
        description
          "Calculate post-convergence backup paths";
        uses apply-advanced;
        leaf maximum-labels {
          type union {
            type string {
              pattern "<.*>|$.*";
            }
            type uint32 {
              range "2 .. 8";
            }
          }
          description
            "Maximum number of labels installed for post-convergence paths";
        }
      }
      leaf use-source-packet-routing {
        type empty;
        description
          "Use spring backup paths for inet.0 routes";
      }
      leaf disable {
        type empty;
        description
          "Do not run backup SPF";
      }
      leaf no-install {
        type empty;
        description
          "Do not install backup nexthops into the RIB";
      }
      leaf downstream-paths-only {
        type empty;
        description
          "Use only downstream backup paths";
      }
      container per-prefix-calculation {
        description
          "Calculate backup nexthops for non-best prefix originators";
        uses apply-advanced;
        leaf stubs {
          type empty;
          description
            "Per prefix calculation for stubs only";
        }
        leaf summary {
          type empty;
          description
            "Per prefix calculation for summary originators only";
        }
        leaf externals {
          type empty;
          description
            "Per prefix calculation for externals";
        }
        leaf all {
          type empty;
          description
            "Per prefix calculation for all";
        }
      }
      leaf node-link-degradation {
        type empty;
        description
          "Degrade to link protection when nodelink protection not available";
      }
    }
    container source-packet-routing {
      presence "enable source-packet-routing";
      description
        "Enable source packet routing (SPRING)";
      uses apply-advanced;
      container adjacency-segment {
        description
          "Attributes for adjacency segments in spring";
        uses apply-advanced;
        leaf hold-time {
          type union {
            type string {
              pattern "<.*>|$.*";
            }
            type uint32 {
              range "180000 .. 900000";
            }
          }
          description
            "Retain time of Adjacency segment after isolating from an interface";
        }
      }
      leaf-list prefix-segment {
        type jt:policy-algebra;
        ordered-by user;
        description
          "Prefix Segment policy";
      }
      leaf explicit-null {
        type empty;
        description
          "Set E and P bits in all Prefix SID advertisements";
      }
      container node-segment {
        presence "enable node-segment";
        description
          "Enable support for Node segments in SPRING";
        uses apply-advanced;
        leaf ipv4-index {
          type union {
            type string {
              pattern "<.*>|$.*";
            }
            type uint32 {
              range "0 .. 199999";
            }
          }
          description
            "Set ipv4 node segment index";
        }
        leaf index-range {
          type union {
            type string {
              pattern "<.*>|$.*";
            }
            type uint32 {
              range "32 .. 16385";
            }
          }
          description
            "Set range of node segment indices allowed";
        }
      }
      container srgb {
        description
          "Set the SRGB global block in SPRING";
        leaf start-label {
          type union {
            type string {
              pattern "<.*>|$.*";
            }
            type uint32 {
              range "16 .. 1048575";
            }
          }
          description
            "Start range for SRGB label block";
        }
        leaf index-range {
          type union {
            type string {
              pattern "<.*>|$.*";
            }
            type uint32 {
              range "32 .. 1048559";
            }
          }
          mandatory true;
          description
            "Index to the SRGB start label block";
        }
      }
      leaf mapping-server {
        type string;
        description
          "Mapping server name";
      }
      leaf install-prefix-sid-for-best-route {
        type empty;
        description
          "For best route install a exact prefix sid route";
      }
      leaf ldp-stitching {
        type empty;
        description
          "Enable SR to LDP stitching";
      }
      leaf-list flex-algorithm {
        type union {
          type string {
            pattern "<.*>|$.*";
          }
          type uint32 {
            range "128 .. 255";
          }
        }
        max-elements 16;
        description
          "Flex-algorithms we would like to participate in";
      }
      leaf strict-asla-based-flex-algorithm {
        type empty;
        description
          "Flex-Algorithm to ignore links not having ASLA sub-TLVs";
      }
      container sensor-based-stats {
        description
          "Configure sensor based stats in SPRING";
        uses apply-advanced;
        container per-interface-per-member-link {
          description
            "Configure sensor based stats per nexthop";
          leaf ingress {
            type empty;
            description
              "Enable sensor based stats on ingress interface";
          }
          leaf egress {
            type empty;
            description
              "Enable sensor based stats on egress interface";
          }
        }
        container per-sid {
          description
            "Configure sensor based stats per spring route";
          leaf ingress {
            type empty;
            description
              "Enable sensor based stats for per-sid ingress accounting";
          }
          leaf egress {
            type empty;
            description
              "Enable sensor based stats for IP-MPLS egress accounting";
          }
        }
      }
    }
    list area {
      key "name";
      ordered-by user;
      description
        "Configure an OSPF area";
      leaf name {
        type jt:areaid;
        description
          "Area ID";
      }
      uses apply-advanced;
      choice stub-option {
        case case_1 {
          container stub {
            presence "enable stub";
            description
              "Configure a stub area";
            leaf default-metric {
              type union {
                type string {
                  pattern "<.*>|$.*";
                }
                type uint32 {
                  range "1 .. 16777215";
                }
              }
              description
                "Metric for the default route in this stub area";
            }
            choice summaries-choice {
              leaf summaries {
                type empty;
                description
                  "Flood summary LSAs into this stub area";
              }
              leaf no-summaries {
                type empty;
                description
                  "Don't flood summary LSAs into this stub area";
              }
            }
          }
        }
        case case_2 {
          container nssa {
            presence "enable nssa";
            description
              "Configure a not-so-stubby area";
            uses apply-advanced;
            container default-lsa {
              presence "enable default-lsa";
              description
                "Configure a default LSA";
              uses apply-advanced;
              leaf default-metric {
                type union {
                  type string {
                    pattern "<.*>|$.*";
                  }
                  type uint32 {
                    range "1 .. 16777215";
                  }
                }
                description
                  "Metric for the default route in this area";
              }
              leaf metric-type {
                type union {
                  type string {
                    pattern "<.*>|$.*";
                  }
                  type uint32 {
                    range "1 .. 2";
                  }
                }
                description
                  "External metric type for the default type 7 LSA";
              }
              leaf type-7 {
                type empty;
                description
                  "Flood type 7 default LSA if no-summaries is configured";
              }
            }
            leaf default-metric {
              type union {
                type string {
                  pattern "<.*>|$.*";
                }
                type uint32 {
                  range "1 .. 16777215";
                }
              }
              status deprecated;
              description
                "Metric for the default route in this area";
            }
            leaf metric-type {
              type union {
                type string {
                  pattern "<.*>|$.*";
                }
                type uint32 {
                  range "1 .. 2";
                }
              }
              status deprecated;
              description
                "External metric type for the default type 7 LSA";
            }
            choice summaries-choice {
              leaf summaries {
                type empty;
                description
                  "Flood summary LSAs into this NSSA area";
              }
              leaf no-summaries {
                type empty;
                description
                  "Don't flood summary LSAs into this NSSA area";
              }
            }
            list area-range {
              key "name";
              ordered-by user;
              description
                "Configure NSSA area ranges";
              leaf name {
                type jt:ipprefix;
                description
                  "Range to summarize NSSA routes in this area";
              }
              uses apply-advanced;
              leaf restrict {
                type empty;
                description
                  "Restrict advertisement of this area range";
              }
              leaf exact {
                type empty;
                description
                  "Enforce exact match for advertisement of this area range";
              }
              container override-metric {
                presence "enable override-metric";
                description
                  "Override the dynamic metric for this area-range";
                uses apply-advanced;
                leaf metric {
                  type union {
                    type string {
                      pattern "<.*>|$.*";
                    }
                    type uint32 {
                      range "1 .. 16777215";
                    }
                  }
                  mandatory true;
                  description
                    "Metric value";
                }
                leaf metric-type {
                  type union {
                    type string {
                      pattern "<.*>|$.*";
                    }
                    type uint32 {
                      range "1 .. 2";
                    }
                  }
                  default "1";
                  description
                    "Set the metric type for the override metric";
                }
              }
            }
          }
        }
      }
      list area-range {
        key "name";
        ordered-by user;
        description
          "Configure area ranges";
        leaf name {
          type jt:ipprefix;
          description
            "Range to summarize routes in this area";
        }
        uses apply-advanced;
        leaf restrict {
          type empty;
          description
            "Restrict advertisement of this area range";
        }
        leaf exact {
          type empty;
          description
            "Enforce exact match for advertisement of this area range";
        }
        leaf override-metric {
          type union {
            type string {
              pattern "<.*>|$.*";
            }
            type uint32 {
              range "1 .. 16777215";
            }
          }
          description
            "Override the dynamic metric for this area-range";
        }
      }
      leaf-list network-summary-export {
        type jt:policy-algebra;
        ordered-by user;
        description
          "Export policy for Type 3 Summary LSAs";
      }
      leaf-list network-summary-import {
        type jt:policy-algebra;
        ordered-by user;
        description
          "Import policy for Type 3 Summary LSAs";
      }
      leaf-list inter-area-prefix-export {
        type jt:policy-algebra;
        ordered-by user;
        description
          "Export policy for Inter Area Prefix LSAs";
      }
      leaf-list inter-area-prefix-import {
        type jt:policy-algebra;
        ordered-by user;
        description
          "Import policy for Inter Area Prefix LSAs";
      }
      leaf authentication-type {
        type enumeration {
          enum "none" {
            status deprecated;
            description
              "No authentication";
          }
          enum "simple" {
            status deprecated;
            description
              "Simple password authentication";
          }
          enum "md5" {
            status deprecated;
            description
              "MD5 authentication";
          }
        }
        status deprecated;
        description
          "Authentication type";
      }
      list virtual-link {
        key "neighbor-id transit-area";
        ordered-by user;
        description
          "Configure virtual links";
        leaf neighbor-id {
          type jt:ipv4addr;
          description
            "Router ID of a virtual neighbor";
        }
        leaf transit-area {
          type jt:areaid;
          description
            "Transit area in common with virtual neighbor";
        }
        uses apply-advanced;
        choice enable-disable {
          case case_1 {
            leaf disable {
              type empty;
              description
                "Disable this virtual link";
            }
          }
        }
        leaf retransmit-interval {
          type union {
            type string {
              pattern "<.*>|$.*";
            }
            type uint32 {
              range "1 .. 65535";
            }
          }
          description
            "Retransmission interval (seconds)";
        }
        leaf transit-delay {
          type union {
            type string {
              pattern "<.*>|$.*";
            }
            type uint32 {
              range "1 .. 65535";
            }
          }
          description
            "Transit delay (seconds)";
        }
        leaf hello-interval {
          type union {
            type string {
              pattern "<.*>|$.*";
            }
            type uint32 {
              range "1 .. 255";
            }
          }
          description
            "Hello interval (seconds)";
        }
        leaf dead-interval {
          type union {
            type string {
              pattern "<.*>|$.*";
            }
            type uint32 {
              range "1 .. 65535";
            }
          }
          description
            "Dead interval (seconds)";
        }
        leaf mtu {
          type union {
            type string {
              pattern "<.*>|$.*";
            }
            type uint32 {
              range "128 .. 65535";
            }
          }
          description
            "Maximum OSPF packet size";
        }
        choice auth {
          case case_1 {
            container authentication {
              uses juniper-ospf-authentication;
            }
          }
          case case_2 {
            container authentication-key {
              status deprecated;
              description
                "Authentication key";
              leaf keyname {
                type jt:unreadable;
                mandatory true;
                description
                  "Authentication key value";
              }
              leaf key-id {
                type union {
                  type string {
                    pattern "<.*>|$.*";
                  }
                  type uint32 {
                    range "0 .. 255";
                  }
                }
                description
                  "Key ID for MD5 authentication";
              }
            }
          }
        }
        leaf demand-circuit {
          type empty;
          description
            "Interface functions as a demand circuit";
        }
        leaf flood-reduction {
          type empty;
          description
            "Enable flood reduction";
        }
        leaf no-neighbor-down-notification {
          type empty;
          description
            "Don't inform other protocols about neighbor down events";
        }
        leaf ipsec-sa {
          type string {
            length "1 .. 32";
          }
          description
            "IPSec security association name";
        }
        list topology {
          key "name";
          ordered-by user;
          description
            "Topology specific attributes";
          leaf name {
            type string;
            description
              "Topology name";
          }
          uses apply-advanced;
          leaf disable {
            type empty;
            description
              "Disable this topology";
          }
          leaf metric {
            type union {
              type string {
                pattern "<.*>|$.*";
              }
              type uint16 {
                range "1 .. 65535";
              }
            }
            description
              "Topology metric";
          }
          container bandwidth-based-metrics {
            description
              "Configure bandwidth based metrics";
            uses apply-advanced;
            list bandwidth {
              key "name";
              description
                "Bandwidth threshold";
              leaf name {
                type string;
              }
              leaf metric {
                type union {
                  type string {
                    pattern "<.*>|$.*";
                  }
                  type uint16 {
                    range "1 .. 65535";
                  }
                }
                mandatory true;
                description
                  "Metric associated with specified bandwidth";
              }
            }
          }
        }
      }
      list sham-link-remote {
        key "name";
        ordered-by user;
        description
          "Configure parameters for remote sham link endpoint";
        leaf name {
          type jt:ipaddr;
          description
            "Remote sham link endpoint address";
        }
        uses apply-advanced;
        leaf metric {
          type union {
            type string {
              pattern "<.*>|$.*";
            }
            type uint16 {
              range "1 .. 65535";
            }
          }
          description
            "Sham link metric";
        }
        leaf ipsec-sa {
          type string {
            length "1 .. 32";
          }
          description
            "IPSec security association name";
        }
        leaf demand-circuit {
          type empty;
          description
            "Interface functions as a demand circuit";
        }
        leaf flood-reduction {
          type empty;
          description
            "Enable flood reduction";
        }
        list topology {
          key "name";
          ordered-by user;
          description
            "Topology specific attributes";
          leaf name {
            type string;
            description
              "Topology name";
          }
          uses apply-advanced;
          leaf disable {
            type empty;
            description
              "Disable this topology";
          }
          leaf metric {
            type union {
              type string {
                pattern "<.*>|$.*";
              }
              type uint16 {
                range "1 .. 65535";
              }
            }
            description
              "Topology metric";
          }
          container bandwidth-based-metrics {
            description
              "Configure bandwidth based metrics";
            uses apply-advanced;
            list bandwidth {
              key "name";
              description
                "Bandwidth threshold";
              leaf name {
                type string;
              }
              leaf metric {
                type union {
                  type string {
                    pattern "<.*>|$.*";
                  }
                  type uint16 {
                    range "1 .. 65535";
                  }
                }
                mandatory true;
                description
                  "Metric associated with specified bandwidth";
              }
            }
          }
        }
        leaf keychain {
          type string {
            length "1 .. 128";
          }
          description
            "Key chain name";
        }
      }
      list interface {
        key "name";
        ordered-by user;
        description
          "Include an interface in this area";
        leaf name {
          type union {
            type jt:ipv4addr-or-interface;
            type string {
              pattern "<.*>|$.*";
            }
          }
          description
            "Interface name";
        }
        uses apply-advanced;
        choice enable-disable {
          case case_1 {
            leaf disable {
              type empty;
              description
                "Disable OSPF on this interface";
            }
          }
        }
        leaf interface-type {
          type enumeration {
            enum "nbma" {
              description
                "Nonbroadcast multiaccess";
            }
            enum "p2mp" {
              description
                "Point-to-multipoint NBMA";
            }
            enum "p2p" {
              description
                "Point-to-point";
            }
            enum "p2mp-over-lan" {
              description
                "Point-to-multipoint over LAN mode";
            }
          }
          description
            "Type of interface";
        }
        container passive {
          presence "enable passive";
          description
            "Do not run OSPF, but advertise it";
          uses apply-advanced;
          container traffic-engineering {
            description
              "Advertise TE link information";
            uses apply-advanced;
            leaf remote-node-id {
              type jt:ipaddr;
              description
                "Remote address of the link";
            }
            leaf remote-node-router-id {
              type jt:ipv4addr;
              description
                "TE Router-ID of the remote node";
            }
          }
        }
        leaf secondary {
          type empty;
          description
            "Treat interface as secondary";
        }
        leaf own-router-lsa {
          type empty;
          description
            "Generate a separate router LSA for this interface";
        }
        container bandwidth-based-metrics {
          description
            "Configure bandwidth based metrics";
          uses apply-advanced;
          list bandwidth {
            key "name";
            description
              "Bandwidth threshold";
            leaf name {
              type string;
            }
            leaf metric {
              type union {
                type string {
                  pattern "<.*>|$.*";
                }
                type uint16 {
                  range "1 .. 65535";
                }
              }
              mandatory true;
              description
                "Metric associated with specified bandwidth";
            }
          }
        }
        leaf metric {
          type union {
            type string {
              pattern "<.*>|$.*";
            }
            type uint16 {
              range "1 .. 65535";
            }
          }
          description
            "Interface metric";
        }
        leaf priority {
          type union {
            type string {
              pattern "<.*>|$.*";
            }
            type uint32 {
              range "0 .. 255";
            }
          }
          description
            "Designated router priority";
        }
        leaf retransmit-interval {
          type union {
            type string {
              pattern "<.*>|$.*";
            }
            type uint32 {
              range "1 .. 65535";
            }
          }
          description
            "Retransmission interval (seconds)";
        }
        leaf transit-delay {
          type union {
            type string {
              pattern "<.*>|$.*";
            }
            type uint32 {
              range "1 .. 65535";
            }
          }
          description
            "Transit delay (seconds)";
        }
        leaf hello-interval {
          type union {
            type string {
              pattern "<.*>|$.*";
            }
            type uint32 {
              range "1 .. 255";
            }
          }
          description
            "Hello interval (seconds)";
        }
        leaf dead-interval {
          type union {
            type string {
              pattern "<.*>|$.*";
            }
            type uint32 {
              range "1 .. 65535";
            }
          }
          description
            "Dead interval (seconds)";
        }
        leaf mtu {
          type union {
            type string {
              pattern "<.*>|$.*";
            }
            type uint32 {
              range "128 .. 65535";
            }
          }
          description
            "Maximum OSPF packet size";
        }
        choice auth {
          case case_1 {
            container authentication {
              uses juniper-ospf-authentication;
            }
          }
          case case_2 {
            container authentication-key {
              status deprecated;
              description
                "Authentication key";
              leaf keyname {
                type jt:unreadable;
                mandatory true;
                description
                  "Authentication key value";
              }
              leaf key-id {
                type union {
                  type string {
                    pattern "<.*>|$.*";
                  }
                  type uint32 {
                    range "0 .. 255";
                  }
                }
                description
                  "Key ID for MD5 authentication";
              }
            }
          }
        }
        leaf demand-circuit {
          type empty;
          description
            "Interface functions as a demand circuit";
        }
        leaf flood-reduction {
          type empty;
          description
            "Enable flood reduction";
        }
        leaf no-neighbor-down-notification {
          type empty;
          description
            "Don't inform other protocols about neighbor down events";
        }
        list topology {
          key "name";
          ordered-by user;
          description
            "Topology specific attributes";
          leaf name {
            type string;
            description
              "Topology name";
          }
          uses apply-advanced;
          leaf disable {
            type empty;
            description
              "Disable this topology";
          }
          leaf metric {
            type union {
              type string {
                pattern "<.*>|$.*";
              }
              type uint16 {
                range "1 .. 65535";
              }
            }
            description
              "Topology metric";
          }
          container bandwidth-based-metrics {
            description
              "Configure bandwidth based metrics";
            uses apply-advanced;
            list bandwidth {
              key "name";
              description
                "Bandwidth threshold";
              leaf name {
                type string;
              }
              leaf metric {
                type union {
                  type string {
                    pattern "<.*>|$.*";
                  }
                  type uint16 {
                    range "1 .. 65535";
                  }
                }
                mandatory true;
                description
                  "Metric associated with specified bandwidth";
              }
            }
          }
        }
        leaf transmit-interval {
          type union {
            type string {
              pattern "<.*>|$.*";
            }
            type uint32 {
              range "1 .. 4294967295";
            }
          }
          status deprecated;
          description
            "OSPF packet transmit interval (milliseconds)";
        }
        container bfd-liveness-detection {
          description
            "Bidirectional Forwarding Detection options";
          uses apply-advanced;
          leaf version {
            type enumeration {
              enum "0" {
                description
                  "BFD version 0 (deprecated)";
              }
              enum "1" {
                description
                  "BFD version 1";
              }
              enum "automatic" {
                description
                  "Choose BFD version automatically";
              }
            }
            default "automatic";
            description
              "BFD protocol version number";
          }
          leaf minimum-interval {
            type union {
              type string {
                pattern "<.*>|$.*";
              }
              type uint32 {
                range "1 .. 255000";
              }
            }
            units "milliseconds";
            description
              "Minimum transmit and receive interval";
          }
          leaf minimum-transmit-interval {
            type union {
              type string {
                pattern "<.*>|$.*";
              }
              type uint32 {
                range "1 .. 255000";
              }
            }
            units "milliseconds";
            status deprecated;
            description
              "Minimum transmit interval";
          }
          leaf minimum-receive-interval {
            type union {
              type string {
                pattern "<.*>|$.*";
              }
              type uint32 {
                range "1 .. 255000";
              }
            }
            units "milliseconds";
            description
              "Minimum receive interval";
          }
          leaf multiplier {
            type union {
              type string {
                pattern "<.*>|$.*";
              }
              type uint32 {
                range "1 .. 255";
              }
            }
            default "3";
            description
              "Detection time multiplier";
          }
          leaf inline-disable {
            type empty;
            description
              "Disable inline mode for this BFD session";
          }
          leaf pdu-size {
            type union {
              type string {
                pattern "<.*>|$.*";
              }
              type uint32 {
                range "24 .. 16000";
              }
            }
            default "24";
            description
              "BFD transport protocol payload size";
          }
          choice adaptation-choice {
            case case_1 {
              leaf no-adaptation {
                type empty;
                description
                  "Disable adaptation";
              }
            }
          }
          container transmit-interval {
            description
              "Transmit-interval options";
            uses apply-advanced;
            leaf minimum-interval {
              type union {
                type string {
                  pattern "<.*>|$.*";
                }
                type uint32 {
                  range "1 .. 255000";
                }
              }
              units "milliseconds";
              description
                "Minimum transmit interval";
            }
            leaf threshold {
              type union {
                type uint32;
                type string {
                  pattern "<.*>|$.*";
                }
              }
              units "milliseconds";
              description
                "High transmit interval triggering a trap";
            }
          }
          container detection-time {
            description
              "Detection-time options";
            uses apply-advanced;
            leaf threshold {
              type union {
                type uint32;
                type string {
                  pattern "<.*>|$.*";
                }
              }
              units "milliseconds";
              description
                "High detection-time triggering a trap";
            }
          }
          container authentication {
            description
              "Authentication options";
            uses apply-advanced;
            leaf key-chain {
              type string;
              description
                "Key chain name";
            }
            leaf algorithm {
              type enumeration {
                enum "simple-password" {
                  description
                    "Simple password";
                }
                enum "keyed-md5" {
                  description
                    "Keyed message Digest 5";
                }
                enum "meticulous-keyed-md5" {
                  description
                    "Meticulous keyed message Digest 5";
                }
                enum "keyed-sha-1" {
                  description
                    "Keyed secure hash algorithm (SHA1) ";
                }
                enum "meticulous-keyed-sha-1" {
                  description
                    "Meticulous keyed secure hash algorithm (SHA1) ";
                }
              }
              description
                "Algorithm name";
            }
            leaf loose-check {
              type empty;
              description
                "Verify authentication only if authentication is negotiated";
            }
          }
          container echo {
            description
              "Echo mode parameters";
            uses apply-advanced;
            leaf minimum-interval {
              type union {
                type string {
                  pattern "<.*>|$.*";
                }
                type uint32 {
                  range "100 .. 255000";
                }
              }
              units "milliseconds";
              description
                "Minimum transmit and receive interval";
            }
          }
          container echo-lite {
            description
              "Echo-lite more parameters";
            uses apply-advanced;
            leaf minimum-interval {
              type union {
                type string {
                  pattern "<.*>|$.*";
                }
                type uint32 {
                  range "100 .. 255000";
                }
              }
              units "milliseconds";
              description
                "Minimum transmit and receive interval";
            }
          }
          leaf full-neighbors-only {
            type empty;
            description
              "Setup BFD sessions only to Full neighbors";
          }
          leaf holddown-interval {
            type union {
              type string {
                pattern "<.*>|$.*";
              }
              type uint32 {
                range "0 .. 255000";
              }
            }
            units "milliseconds";
            description
              "Time to hold the session-UP notification to the client";
          }
        }
        leaf dynamic-neighbors {
          type empty;
          description
            "Learn neighbors dynamically on a p2mp interface";
        }
        leaf no-advertise-adjacency-segment {
          type empty;
          description
            "Do not advertise an adjacency segment for this interface";
        }
        list neighbor {
          key "name";
          ordered-by user;
          description
            "NBMA neighbor";
          leaf name {
            type jt:ipaddr;
            description
              "Address of neighbor";
          }
          leaf eligible {
            type empty;
            description
              "Eligible to be DR on an NBMA network";
          }
        }
        leaf poll-interval {
          type union {
            type string {
              pattern "<.*>|$.*";
            }
            type uint32 {
              range "1 .. 65535";
            }
          }
          description
            "Poll interval for NBMA interfaces";
        }
        leaf no-interface-state-traps {
          type empty;
          description
            "Do not send interface state change traps";
        }
        leaf strict-bfd {
          type empty;
          description
            "Enable strict bfd over this interface";
        }
        container post-convergence-lfa {
          presence "enable post-convergence-lfa";
          description
            "Protect interface using post-convergence backup path";
          uses apply-advanced;
        }
        leaf te-metric {
          type union {
            type string {
              pattern "<.*>|$.*";
            }
            type uint32 {
              range "1 .. 4294967295";
            }
          }
          description
            "Traffic engineering metric";
        }
        container ldp-synchronization {
          presence "enable ldp-synchronization";
          description
            "Advertise maximum metric until LDP is operational";
          uses ldp-sync-obj;
        }
        container ipv4-adjacency-segment {
          description
            "Configure ipv4 adjacency segment";
          uses apply-advanced;
          container unprotected {
            description
              "Adjacency SID uneligible for protection";
            choice adjsid-type {
              case case_1 {
                container index {
                  description
                    "Adjacency SID indexed from SRGB";
                  leaf index-number {
                    type union {
                      type string {
                        pattern "<.*>|$.*";
                      }
                      type uint32 {
                        range "0 .. 199999";
                      }
                    }
                  }
                }
              }
              case case_2 {
                leaf label {
                  type union {
                    type string {
                      pattern "<.*>|$.*";
                    }
                    type uint32 {
                      range "16 .. 1048575";
                    }
                  }
                  description
                    "Adjacency SID from static label pool";
                }
              }
              case case_3 {
                leaf dynamic {
                  type empty;
                  description
                    "Dynamically allocate an adjacency segment";
                }
              }
            }
          }
        }
        list lan-neighbor {
          key "name";
          ordered-by user;
          description
            "Configuration specific to a LAN neighbor";
          leaf name {
            type jt:ipaddr;
            description
              "Address of neighbor";
          }
          uses apply-advanced;
          container ipv4-adjacency-segment {
            description
              "Configure ipv4 adjacency segment";
            uses apply-advanced;
            container protected {
              description
                "Adjacency SID is eligible for protection";
              choice adjsid-type {
                case case_1 {
                  container index {
                    description
                      "Adjacency SID indexed from SRGB";
                    leaf index-number {
                      type union {
                        type string {
                          pattern "<.*>|$.*";
                        }
                        type uint32 {
                          range "0 .. 199999";
                        }
                      }
                    }
                  }
                }
                case case_2 {
                  leaf label {
                    type union {
                      type string {
                        pattern "<.*>|$.*";
                      }
                      type uint32 {
                        range "16 .. 1048575";
                      }
                    }
                    description
                      "Adjacency SID from static label pool";
                  }
                }
                case case_3 {
                  leaf dynamic {
                    type empty;
                    description
                      "Dynamically allocate an adjacency segment";
                  }
                }
              }
            }
            container unprotected {
              description
                "Adjacency SID uneligible for protection";
              choice adjsid-type {
                case case_1 {
                  container index {
                    description
                      "Adjacency SID indexed from SRGB";
                    leaf index-number {
                      type union {
                        type string {
                          pattern "<.*>|$.*";
                        }
                        type uint32 {
                          range "0 .. 199999";
                        }
                      }
                    }
                  }
                }
                case case_2 {
                  leaf label {
                    type union {
                      type string {
                        pattern "<.*>|$.*";
                      }
                      type uint32 {
                        range "16 .. 1048575";
                      }
                    }
                    description
                      "Adjacency SID from static label pool";
                  }
                }
                case case_3 {
                  leaf dynamic {
                    type empty;
                    description
                      "Dynamically allocate an adjacency segment";
                  }
                }
              }
            }
          }
        }
        leaf delay-metric {
          type union {
            type string {
              pattern "<.*>|$.*";
            }
            type uint32 {
              range "0 .. 16777215";
            }
          }
          units "microseconds";
          description
            "Delay metric";
        }
        container delay-measurement {
          presence "enable delay-measurement";
          description
            "Enable delay measurement";
          uses apply-advanced;
          leaf probe-interval {
            type union {
              type string {
                pattern "<.*>|$.*";
              }
              type uint32 {
                range "1 .. 255";
              }
            }
            units "seconds";
            description
              "Probe interval";
          }
          leaf probe-count {
            type union {
              type string {
                pattern "<.*>|$.*";
              }
              type uint32 {
                range "1 .. 15";
              }
            }
            description
              "Probe count";
          }
          container advertisement {
            description
              "Delay advertisement";
            uses apply-advanced;
            container periodic {
              description
                "Periodic advertisement parameters";
              uses apply-advanced;
              leaf threshold {
                type union {
                  type string {
                    pattern "<.*>|$.*";
                  }
                  type uint32 {
                    range "0 .. 100";
                  }
                }
                units "percentage";
                description
                  "Threshold";
              }
              leaf interval {
                type union {
                  type string {
                    pattern "<.*>|$.*";
                  }
                  type uint32 {
                    range "30 .. 3600";
                  }
                }
                units "seconds";
                description
                  "Interval";
              }
            }
            container accelerated {
              presence "enable accelerated";
              description
                "Accelerated advertisement parameters";
              uses apply-advanced;
              leaf threshold {
                type union {
                  type string {
                    pattern "<.*>|$.*";
                  }
                  type uint32 {
                    range "0 .. 100";
                  }
                }
                units "percentage";
                description
                  "Threshold";
              }
            }
          }
        }
        container application-specific {
          description
            "Advertise application-specific TE attributes";
          uses apply-advanced;
          list attribute-group {
            key "name";
            max-elements 1;
            ordered-by user;
            description
              "Link attribute group name";
            leaf name {
              type string;
              description
                "Link attribute group name";
            }
            uses apply-advanced;
            leaf te-metric {
              type union {
                type string {
                  pattern "<.*>|$.*";
                }
                type uint32 {
                  range "1 .. 4294967295";
                }
              }
              description
                "Traffic engineering metric for this attribute group";
            }
            leaf-list admin-group {
              type string;
              max-elements 16;
              ordered-by user;
              description
                "Administrative groups for this attribute-group";
            }
            leaf delay-metric {
              type union {
                type string {
                  pattern "<.*>|$.*";
                }
                type uint32 {
                  range "0 .. 16777215";
                }
              }
              units "microseconds";
              description
                "Delay metric for this attribute-group";
            }
            leaf advertise-interface-delay {
              type empty;
              description
                "Use interface specific static/dynamic delay values as applicable in ASLA Sub-TLVs";
            }
            container application {
              description
                "Standard Applications part of this attribute-group";
              uses apply-advanced;
              leaf flex-algorithm {
                type empty;
                description
                  "Set X flag in standard application bit mask";
              }
            }
          }
        }
      }
      leaf no-source-packet-routing {
        type empty;
        description
          "Disable SPRING in this area";
      }
    }
    choice enable-disable {
      case case_1 {
        leaf disable {
          type empty;
          description
            "Disable OSPF";
        }
      }
    }
    container traceoptions {
      description
        "Trace options for OSPF";
      uses apply-advanced;
      container file {
        description
          "Trace file options";
        leaf filename {
          type string {
            length "1 .. 1024";
          }
          description
            "Name of file in which to write trace information";
        }
        leaf replace {
          type empty;
          status deprecated;
          description
            "Replace trace file rather than appending to it";
        }
        leaf size {
          type string;
          description
            "Maximum trace file size";
        }
        leaf files {
          type union {
            type string {
              pattern "<.*>|$.*";
            }
            type uint32 {
              range "2 .. 1000";
            }
          }
          default "10";
          description
            "Maximum number of trace files";
        }
        leaf no-stamp {
          type empty;
          status deprecated;
          description
            "Do not timestamp trace file";
        }
        choice world-readable-choice {
          leaf world-readable {
            type empty;
            description
              "Allow any user to read the log file";
          }
          leaf no-world-readable {
            type empty;
            description
              "Don't allow any user to read the log file";
          }
        }
      }
      list flag {
        key "name";
        ordered-by user;
        description
          "Tracing parameters";
        leaf name {
          type enumeration {
            enum "spf" {
              description
                "Trace SPF calculations";
            }
            enum "error" {
              description
                "Trace errored packets";
            }
            enum "event" {
              description
                "Trace OSPF state machine events";
            }
            enum "packet-dump" {
              description
                "Dump the contents of selected packet types";
            }
            enum "flooding" {
              description
                "Trace LSA flooding";
            }
            enum "lsa-analysis" {
              description
                "Trace LSA analysis";
            }
            enum "packets" {
              description
                "Trace all OSPF packets";
            }
            enum "hello" {
              description
                "Trace hello packets";
            }
            enum "database-description" {
              description
                "Trace database description packets";
            }
            enum "lsa-request" {
              description
                "Trace LSA request packets";
            }
            enum "lsa-update" {
              description
                "Trace LSA update packets";
            }
            enum "lsa-ack" {
              description
                "Trace LSA acknowledgment packets";
            }
            enum "ldp-synchronization" {
              description
                "Trace synchronization between OSPF and LDP";
            }
            enum "on-demand" {
              description
                "Trace demand circuit extensions";
            }
            enum "nsr-synchronization" {
              description
                "Trace NSR synchronization events";
            }
            enum "graceful-restart" {
              description
                "Trace graceful restart";
            }
            enum "restart-signaling" {
              description
                "Trace restart signaling";
            }
            enum "traffic-statistics" {
              description
                "Trace Segment Routing Traffic Statistics";
            }
            enum "backup-spf" {
              description
                "Trace backup SPF (LFA) specific events";
            }
            enum "source-packet-routing" {
              description
                "Trace source packet routing (SPRING) events";
            }
            enum "post-convergence-lfa" {
              description
                "Trace post-convergence-lfa related events";
            }
            enum "flex-algorithm" {
              description
                "Trace flex-algorithm related events";
            }
            enum "rmopd" {
              description
                "Trace rmopd interactions";
            }
            enum "route" {
              description
                "Trace routing information";
            }
            enum "normal" {
              description
                "Trace normal events";
            }
            enum "general" {
              description
                "Trace general events";
            }
            enum "state" {
              description
                "Trace state transitions";
            }
            enum "policy" {
              description
                "Trace policy processing";
            }
            enum "task" {
              description
                "Trace routing protocol task processing";
            }
            enum "timer" {
              description
                "Trace routing protocol timer processing";
            }
            enum "all" {
              description
                "Trace everything";
            }
          }
        }
        leaf send {
          type empty;
          description
            "Trace transmitted packets";
        }
        leaf receive {
          type empty;
          description
            "Trace received packets";
        }
        leaf detail {
          type empty;
          description
            "Trace detailed information";
        }
        leaf disable {
          type empty;
          description
            "Disable this trace flag";
        }
      }
    }
    leaf prefix-export-limit {
      type union {
        type string {
          pattern "<.*>|$.*";
        }
        type uint32 {
          range "0 .. 4294967295";
        }
      }
      description
        "Maximum number of prefixes that can be exported";
    }
    container rib-groups {
      description
        "Routing table groups for importing OSPF routes";
      uses apply-advanced;
      leaf inet {
        type string;
        description
          "Name of the IPv4/v6 routing table group";
      }
      leaf inet3 {
        type string;
        description
          "Name of the IPv4/v6 inet.3 routing table group";
      }
    }
    leaf job-stats {
      type empty;
      description
        "Collect job statistics";
    }
    container overload {
      presence "enable overload";
      description
        "Set the overload mode (repel transit traffic)";
      uses apply-advanced;
      leaf timeout {
        type union {
          type string {
            pattern "<.*>|$.*";
          }
          type uint32 {
            range "60 .. 3600";
          }
        }
        units "seconds";
        description
          "Time after which overload mode is reset";
      }
      leaf allow-route-leaking {
        type empty;
        description
          "Allow routes to be leaked when overload is configured";
      }
      leaf stub-network {
        type empty;
        description
          "Advertise Stub Network with maximum metric";
      }
      leaf intra-area-prefix {
        type empty;
        description
          "Advertise Intra Area Prefix with maximum metric";
      }
      leaf as-external {
        type empty;
        description
          "Advertise As External with maximum usable metric";
      }
    }
    container database-protection {
      presence "enable database-protection";
      description
        "Configure database protection attributes";
      uses apply-advanced;
      leaf maximum-lsa {
        type union {
          type string {
            pattern "<.*>|$.*";
          }
          type uint32 {
            range "1 .. 1000000";
          }
        }
        mandatory true;
        description
          "Maximum allowed non self-generated LSAs";
      }
      leaf warning-only {
        type empty;
        description
          "Emit only a warning when LSA maximum limit is exceeded";
      }
      leaf warning-threshold {
        type union {
          type string {
            pattern "<.*>|$.*";
          }
          type uint8 {
            range "30 .. 100";
          }
        }
        units "percent";
        description
          "Percentage of LSA maximum above which to trigger warning";
      }
      leaf ignore-count {
        type union {
          type string {
            pattern "<.*>|$.*";
          }
          type uint8 {
            range "1 .. 32";
          }
        }
        description
          "Maximum number of times to go into ignore state";
      }
      leaf ignore-time {
        type union {
          type string {
            pattern "<.*>|$.*";
          }
          type uint16 {
            range "30 .. 3600";
          }
        }
        units "seconds";
        description
          "Time to stay in ignore state and ignore all neighbors";
      }
      leaf reset-time {
        type union {
          type string {
            pattern "<.*>|$.*";
          }
          type uint32 {
            range "60 .. 86400";
          }
        }
        units "seconds";
        description
          "Time after which the ignore count gets reset to zero";
      }
    }
    container graceful-restart {
      description
        "Configure graceful restart attributes";
      uses apply-advanced;
      choice enable-disable {
        case case_1 {
          leaf disable {
            type empty;
            description
              "Disable OSPF graceful restart capability";
          }
        }
      }
      leaf restart-duration {
        type union {
          type string {
            pattern "<.*>|$.*";
          }
          type uint32 {
            range "1 .. 3600";
          }
        }
        units "seconds";
        description
          "Time for all neighbors to become full";
      }
      leaf notify-duration {
        type union {
          type string {
            pattern "<.*>|$.*";
          }
          type uint32 {
            range "1 .. 3600";
          }
        }
        units "seconds";
        description
          "Time to send all max-aged grace LSAs";
      }
      container helper-disable {
        presence "enable helper-disable";
        description
          "Disable graceful restart helper capability";
        uses apply-advanced;
        choice disable-choices {
          case case_1 {
            leaf standard {
              type empty;
              description
                "Disable helper-mode for rfc3623 based GR";
            }
          }
          case case_2 {
            leaf restart-signaling {
              type empty;
              description
                "Disable helper mode for restart-signaling ";
            }
          }
          case case_3 {
            leaf both {
              type empty;
              description
                "Disable helper mode for both the types of GR";
            }
          }
        }
      }
      leaf no-strict-lsa-checking {
        type empty;
        description
          "Do not abort graceful helper mode upon LSA changes";
      }
    }
    leaf route-type-community {
      type enumeration {
        enum "iana" {
          description
            "BGP extended community value used is 0x0306";
        }
        enum "vendor" {
          description
            "Vendor BGP extended community value used is 0x8000";
        }
      }
      description
        "Specify BGP extended community value to encode OSPF route type";
    }
    container domain-id {
      description
        "Configure domain ID";
      choice domain_id_or_disable {
        case case_1 {
          leaf domain-id {
            type string;
            description
              "Domain ID";
          }
        }
        case case_2 {
          leaf disable {
            type empty;
            description
              "Disable domain ID";
          }
        }
      }
    }
    choice domain_vpn_tag_or_disable {
      case case_1 {
        leaf domain-vpn-tag {
          type union {
            type string {
              pattern "<.*>|$.*";
            }
            type uint32 {
              range "0 .. 4294967295";
            }
          }
          description
            "Domain VPN tag for external LSA";
        }
      }
      case case_2 {
        leaf no-domain-vpn-tag {
          type empty;
          description
            "Disable domain VPN tag";
        }
      }
    }
    leaf preference {
      type union {
        type uint32;
        type string {
          pattern "<.*>|$.*";
        }
      }
      description
        "Preference of internal routes";
    }
    leaf external-preference {
      type union {
        type uint32;
        type string {
          pattern "<.*>|$.*";
        }
      }
      description
        "Preference of external routes";
    }
    leaf labeled-preference {
      type union {
        type uint32;
        type string {
          pattern "<.*>|$.*";
        }
      }
      description
        "Preference of labeled routes";
    }
    leaf-list export {
      type jt:policy-algebra;
      ordered-by user;
      description
        "Export policy";
    }
    leaf-list import {
      type jt:policy-algebra;
      ordered-by user;
      description
        "Import policy (for external routes or setting priority)";
    }
    leaf reference-bandwidth {
      type string;
      description
        "Bandwidth for calculating metric defaults";
    }
    leaf lsa-refresh-interval {
      type union {
        type string {
          pattern "<.*>|$.*";
        }
        type uint32 {
          range "25 .. 50";
        }
      }
      default "50";
      description
        "LSA refresh interval (minutes)";
    }
    leaf spf-delay {
      type union {
        type string {
          pattern "<.*>|$.*";
        }
        type uint32 {
          range "50 .. 8000";
        }
      }
      units "milliseconds";
      status deprecated;
      description
        "Time to wait before running an SPF";
    }
    leaf no-rfc-1583 {
      type empty;
      description
        "Disable RFC1583 compatibility";
    }
    leaf forwarding-address-to-broadcast {
      type empty;
      description
        "Set forwarding address in Type 5 LSA in broadcast network";
    }
    choice nssa-abr-option {
      case case_1 {
        leaf no-nssa-abr {
          type empty;
          description
            "Disable full NSSA functionality at ABR";
        }
      }
    }
    container sham-link {
      presence "enable sham-link";
      description
        "Configure parameters for sham links";
      uses apply-advanced;
      leaf local {
        type jt:ipaddr;
        description
          "Local sham link endpoint address";
      }
      leaf no-advertise-local {
        type empty;
        status deprecated;
        description
          "Don't advertise local sham link endpoint as stub in router LSA";
      }
    }
  }

  grouping juniper-protocols-ospf3 {
    list realm {
      key "name";
      ordered-by user;
      description
        "OSPFv3 realm configuration";
      leaf name {
        type enumeration {
          enum "ipv6-unicast" {
            description
              "IPv6 unicast realm";
          }
          enum "ipv6-multicast" {
            description
              "IPv6 multicast realm";
          }
          enum "ipv4-unicast" {
            description
              "IPv4 unicast realm";
          }
          enum "ipv4-multicast" {
            description
              "IPv4 multicast realm";
          }
        }
        description
          "OSPFv3 realm name";
      }
      uses apply-advanced;
      list topology {
        key "name";
        ordered-by user;
        description
          "Topology parameters";
        leaf name {
          type string;
          description
            "Topology name";
        }
        uses apply-advanced;
        leaf disable {
          type empty;
          description
            "Disable this topology";
        }
        leaf topology-id {
          type union {
            type string {
              pattern "<.*>|$.*";
            }
            type uint8 {
              range "32 .. 127";
            }
          }
          description
            "Topology identifier";
        }
        leaf overload {
          type empty;
          description
            "Set the overload mode (repel transit traffic)";
        }
        leaf rib-group {
          type string;
          description
            "Routing table group for importing routes";
        }
        container spf-options {
          description
            "Configure options for SPF";
          uses apply-advanced;
          container microloop-avoidance {
            description
              "Configure microloop avoidance mechanism";
            uses apply-advanced;
            container post-convergence-path {
              presence "enable post-convergence-path";
              description
                "Temporarily install post-convergence path for routes potentially affected by microloops";
              uses apply-advanced;
              leaf delay {
                type union {
                  type string {
                    pattern "<.*>|$.*";
                  }
                  type uint32 {
                    range "500 .. 60000";
                  }
                }
                units "milliseconds";
                description
                  "Time after which temporary post-convergence paths are removed";
              }
              leaf maximum-labels {
                type union {
                  type string {
                    pattern "<.*>|$.*";
                  }
                  type uint32 {
                    range "2 .. 8";
                  }
                }
                description
                  "Maximum number of labels installed for post-convergence paths";
              }
            }
          }
          leaf delay {
            type union {
              type string {
                pattern "<.*>|$.*";
              }
              type uint32 {
                range "50 .. 8000";
              }
            }
            units "milliseconds";
            description
              "Time to wait before running an SPF";
          }
          leaf holddown {
            type union {
              type string {
                pattern "<.*>|$.*";
              }
              type uint32 {
                range "2000 .. 20000";
              }
            }
            units "milliseconds";
            description
              "Time to hold down before running an SPF";
          }
          leaf rapid-runs {
            type union {
              type string {
                pattern "<.*>|$.*";
              }
              type uint32 {
                range "1 .. 10";
              }
            }
            description
              "Number of maximum rapid SPF runs before holddown";
          }
          leaf no-ignore-our-externals {
            type empty;
            description
              "Do not ignore self-generated external and NSSA LSAs";
          }
          container multipath {
            description
              "Configure multipath options";
            uses apply-advanced;
            container weighted {
              description
                "Weighted multipath options";
              uses apply-advanced;
              leaf one-hop {
                type empty;
                description
                  "Enable load balancing on onehop multipath based on interface bandwidth";
              }
            }
          }
        }
        container backup-spf-options {
          description
            "Configure options for backup SPF";
          uses apply-advanced;
          container remote-backup-calculation {
            presence "enable remote-backup-calculation";
            description
              "Calculate Remote LFA backup nexthops";
            uses apply-advanced;
            container pq-nodes-nearest-to-source {
              description
                "PQ nodes selection based upon nearest to source";
              uses apply-advanced;
              leaf percent {
                type union {
                  type string {
                    pattern "<.*>|$.*";
                  }
                  type uint32 {
                    range "10 .. 100";
                  }
                }
                description
                  "Selection percentage for nearest to source";
              }
            }
          }
          container use-post-convergence-lfa {
            presence "enable use-post-convergence-lfa";
            description
              "Calculate post-convergence backup paths";
            uses apply-advanced;
            leaf maximum-labels {
              type union {
                type string {
                  pattern "<.*>|$.*";
                }
                type uint32 {
                  range "2 .. 8";
                }
              }
              description
                "Maximum number of labels installed for post-convergence paths";
            }
            leaf maximum-backup-paths {
              type union {
                type string {
                  pattern "<.*>|$.*";
                }
                type uint32 {
                  range "1 .. 8";
                }
              }
              description
                "Maximum number of equal-cost post-convergence paths installed";
            }
          }
          leaf use-source-packet-routing {
            type empty;
            description
              "Use spring backup paths for inet.0 routes";
          }
          leaf disable {
            type empty;
            description
              "Do not run backup SPF";
          }
          leaf no-install {
            type empty;
            description
              "Do not install backup nexthops into the RIB";
          }
          leaf downstream-paths-only {
            type empty;
            description
              "Use only downstream backup paths";
          }
          container per-prefix-calculation {
            description
              "Calculate backup nexthops for non-best prefix originators";
            uses apply-advanced;
            leaf stubs {
              type empty;
              description
                "Per prefix calculation for stubs only";
            }
            leaf summary {
              type empty;
              description
                "Per prefix calculation for summary originators only";
            }
            leaf externals {
              type empty;
              description
                "Per prefix calculation for externals";
            }
            leaf all {
              type empty;
              description
                "Per prefix calculation for all";
            }
          }
          leaf node-link-degradation {
            type empty;
            description
              "Degrade to link protection when nodelink protection not available";
          }
        }
        leaf prefix-export-limit {
          type union {
            type string {
              pattern "<.*>|$.*";
            }
            type uint32 {
              range "0 .. 4294967295";
            }
          }
          description
            "Maximum number of prefixes that can be exported";
        }
      }
      container spf-options {
        description
          "Configure options for SPF";
        uses apply-advanced;
        container microloop-avoidance {
          description
            "Configure microloop avoidance mechanism";
          uses apply-advanced;
          container post-convergence-path {
            presence "enable post-convergence-path";
            description
              "Temporarily install post-convergence path for routes potentially affected by microloops";
            uses apply-advanced;
            leaf delay {
              type union {
                type string {
                  pattern "<.*>|$.*";
                }
                type uint32 {
                  range "500 .. 60000";
                }
              }
              units "milliseconds";
              description
                "Time after which temporary post-convergence paths are removed";
            }
            leaf maximum-labels {
              type union {
                type string {
                  pattern "<.*>|$.*";
                }
                type uint32 {
                  range "2 .. 8";
                }
              }
              description
                "Maximum number of labels installed for post-convergence paths";
            }
          }
        }
        leaf delay {
          type union {
            type string {
              pattern "<.*>|$.*";
            }
            type uint32 {
              range "50 .. 8000";
            }
          }
          units "milliseconds";
          description
            "Time to wait before running an SPF";
        }
        leaf holddown {
          type union {
            type string {
              pattern "<.*>|$.*";
            }
            type uint32 {
              range "2000 .. 20000";
            }
          }
          units "milliseconds";
          description
            "Time to hold down before running an SPF";
        }
        leaf rapid-runs {
          type union {
            type string {
              pattern "<.*>|$.*";
            }
            type uint32 {
              range "1 .. 10";
            }
          }
          description
            "Number of maximum rapid SPF runs before holddown";
        }
        leaf no-ignore-our-externals {
          type empty;
          description
            "Do not ignore self-generated external and NSSA LSAs";
        }
        container multipath {
          description
            "Configure multipath options";
          uses apply-advanced;
          container weighted {
            description
              "Weighted multipath options";
            uses apply-advanced;
            leaf one-hop {
              type empty;
              description
                "Enable load balancing on onehop multipath based on interface bandwidth";
            }
          }
        }
      }
      container backup-spf-options {
        description
          "Configure options for backup SPF";
        uses apply-advanced;
        container remote-backup-calculation {
          presence "enable remote-backup-calculation";
          description
            "Calculate Remote LFA backup nexthops";
          uses apply-advanced;
          container pq-nodes-nearest-to-source {
            description
              "PQ nodes selection based upon nearest to source";
            uses apply-advanced;
            leaf percent {
              type union {
                type string {
                  pattern "<.*>|$.*";
                }
                type uint32 {
                  range "10 .. 100";
                }
              }
              description
                "Selection percentage for nearest to source";
            }
          }
        }
        container use-post-convergence-lfa {
          presence "enable use-post-convergence-lfa";
          description
            "Calculate post-convergence backup paths";
          uses apply-advanced;
          leaf maximum-labels {
            type union {
              type string {
                pattern "<.*>|$.*";
              }
              type uint32 {
                range "2 .. 8";
              }
            }
            description
              "Maximum number of labels installed for post-convergence paths";
          }
        }
        leaf use-source-packet-routing {
          type empty;
          description
            "Use spring backup paths for inet.0 routes";
        }
        leaf disable {
          type empty;
          description
            "Do not run backup SPF";
        }
        leaf no-install {
          type empty;
          description
            "Do not install backup nexthops into the RIB";
        }
        leaf downstream-paths-only {
          type empty;
          description
            "Use only downstream backup paths";
        }
        container per-prefix-calculation {
          description
            "Calculate backup nexthops for non-best prefix originators";
          uses apply-advanced;
          leaf stubs {
            type empty;
            description
              "Per prefix calculation for stubs only";
          }
          leaf summary {
            type empty;
            description
              "Per prefix calculation for summary originators only";
          }
          leaf externals {
            type empty;
            description
              "Per prefix calculation for externals";
          }
          leaf all {
            type empty;
            description
              "Per prefix calculation for all";
          }
        }
        leaf node-link-degradation {
          type empty;
          description
            "Degrade to link protection when nodelink protection not available";
        }
      }
      container traffic-engineering {
        presence "enable traffic-engineering";
        description
          "Configure traffic engineering attributes";
        uses apply-advanced;
        leaf no-topology {
          type empty;
          description
            "Disable dissemination of TE link-state topology information";
        }
        leaf multicast-rpf-routes {
          type empty;
          description
            "Install routes for multicast RPF checks into inet.2";
        }
        leaf l3-unicast-topology {
          type empty;
          description
            "Download IGP topology into TED";
        }
        container ignore-lsp-metrics {
          presence "enable ignore-lsp-metrics";
          description
            "Ignore label-switched path metrics when doing shortcuts";
          uses apply-advanced;
          leaf unconfigured-only {
            type empty;
            description
              "Ignore lsp metrics for unconfigured only";
          }
        }
        container shortcuts {
          presence "enable shortcuts";
          description
            "Use label-switched paths as next hops, if possible";
          uses apply-advanced;
          leaf ignore-lsp-metrics {
            type empty;
            status deprecated;
            description
              "Ignore label-switched path metrics when doing shortcuts";
          }
          leaf lsp-metric-into-summary {
            type empty;
            description
              "Advertise LSP metric into summary LSAs";
          }
          list family {
            key "name";
            ordered-by user;
            description
              "Address family specific traffic-engineering attributes";
            leaf name {
              type enumeration {
                enum "inet" {
                  description
                    "IPv4 family";
                }
                enum "inet-mpls" {
                  description
                    "IPv4-MPLS family";
                }
              }
            }
            uses apply-advanced;
          }
        }
        leaf advertise-unnumbered-interfaces {
          type empty;
          description
            "Advertise unnumbered interfaces";
        }
        leaf credibility-protocol-preference {
          type empty;
          description
            "TED protocol credibility follows protocol preference";
        }
        container advertisement {
          description
            "Advertise TE parameters even if RSVP is not turned on";
          uses apply-advanced;
          leaf always {
            type empty;
            description
              "Advertise TE parameters in TE LSAs";
          }
        }
        container tunnel-source-protocol {
          description
            "Protocols from which to pick label-switched paths";
          uses apply-advanced;
          container rsvp {
            presence "enable rsvp";
            description
              "Pick label-switched paths from rsvp";
            uses apply-advanced;
            leaf preference {
              type union {
                type string {
                  pattern "<.*>|$.*";
                }
                type uint32 {
                  range "1 .. 255";
                }
              }
              description
                "Preference for label-switched paths from this protocol";
            }
          }
          container spring-te {
            presence "enable spring-te";
            description
              "Pick label-switched paths from spring-te";
            uses apply-advanced;
            leaf preference {
              type union {
                type string {
                  pattern "<.*>|$.*";
                }
                type uint32 {
                  range "1 .. 255";
                }
              }
              description
                "Preference for label-switched paths from this protocol";
            }
          }
        }
      }
      container source-packet-routing {
        presence "enable source-packet-routing";
        description
          "Enable source packet routing (SPRING)";
        uses apply-advanced;
        container adjacency-segment {
          description
            "Attributes for adjacency segments in spring";
          uses apply-advanced;
          leaf hold-time {
            type union {
              type string {
                pattern "<.*>|$.*";
              }
              type uint32 {
                range "180000 .. 900000";
              }
            }
            description
              "Retain time of Adjacency segment after isolating from an interface";
          }
        }
        leaf-list prefix-segment {
          type jt:policy-algebra;
          ordered-by user;
          description
            "Prefix Segment policy";
        }
        leaf explicit-null {
          type empty;
          description
            "Set E and P bits in all Prefix SID advertisements";
        }
        container node-segment {
          presence "enable node-segment";
          description
            "Enable support for Node segments in SPRING";
          uses apply-advanced;
          leaf ipv4-index {
            type union {
              type string {
                pattern "<.*>|$.*";
              }
              type uint32 {
                range "0 .. 199999";
              }
            }
            description
              "Set ipv4 node segment index";
          }
          leaf index-range {
            type union {
              type string {
                pattern "<.*>|$.*";
              }
              type uint32 {
                range "32 .. 16385";
              }
            }
            description
              "Set range of node segment indices allowed";
          }
        }
        container srgb {
          description
            "Set the SRGB global block in SPRING";
          leaf start-label {
            type union {
              type string {
                pattern "<.*>|$.*";
              }
              type uint32 {
                range "16 .. 1048575";
              }
            }
            description
              "Start range for SRGB label block";
          }
          leaf index-range {
            type union {
              type string {
                pattern "<.*>|$.*";
              }
              type uint32 {
                range "32 .. 1048559";
              }
            }
            mandatory true;
            description
              "Index to the SRGB start label block";
          }
        }
        leaf mapping-server {
          type string;
          description
            "Mapping server name";
        }
        leaf install-prefix-sid-for-best-route {
          type empty;
          description
            "For best route install a exact prefix sid route";
        }
        leaf ldp-stitching {
          type empty;
          description
            "Enable SR to LDP stitching";
        }
        leaf-list flex-algorithm {
          type union {
            type string {
              pattern "<.*>|$.*";
            }
            type uint32 {
              range "128 .. 255";
            }
          }
          max-elements 16;
          description
            "Flex-algorithms we would like to participate in";
        }
        leaf strict-asla-based-flex-algorithm {
          type empty;
          description
            "Flex-Algorithm to ignore links not having ASLA sub-TLVs";
        }
        container sensor-based-stats {
          description
            "Configure sensor based stats in SPRING";
          uses apply-advanced;
          container per-interface-per-member-link {
            description
              "Configure sensor based stats per nexthop";
            leaf ingress {
              type empty;
              description
                "Enable sensor based stats on ingress interface";
            }
            leaf egress {
              type empty;
              description
                "Enable sensor based stats on egress interface";
            }
          }
          container per-sid {
            description
              "Configure sensor based stats per spring route";
            leaf ingress {
              type empty;
              description
                "Enable sensor based stats for per-sid ingress accounting";
            }
            leaf egress {
              type empty;
              description
                "Enable sensor based stats for IP-MPLS egress accounting";
            }
          }
        }
      }
      list area {
        key "name";
        ordered-by user;
        description
          "Configure an OSPF area";
        leaf name {
          type jt:areaid;
          description
            "Area ID";
        }
        uses apply-advanced;
        choice stub-option {
          case case_1 {
            container stub {
              presence "enable stub";
              description
                "Configure a stub area";
              leaf default-metric {
                type union {
                  type string {
                    pattern "<.*>|$.*";
                  }
                  type uint32 {
                    range "1 .. 16777215";
                  }
                }
                description
                  "Metric for the default route in this stub area";
              }
              choice summaries-choice {
                leaf summaries {
                  type empty;
                  description
                    "Flood summary LSAs into this stub area";
                }
                leaf no-summaries {
                  type empty;
                  description
                    "Don't flood summary LSAs into this stub area";
                }
              }
            }
          }
          case case_2 {
            container nssa {
              presence "enable nssa";
              description
                "Configure a not-so-stubby area";
              uses apply-advanced;
              container default-lsa {
                presence "enable default-lsa";
                description
                  "Configure a default LSA";
                uses apply-advanced;
                leaf default-metric {
                  type union {
                    type string {
                      pattern "<.*>|$.*";
                    }
                    type uint32 {
                      range "1 .. 16777215";
                    }
                  }
                  description
                    "Metric for the default route in this area";
                }
                leaf metric-type {
                  type union {
                    type string {
                      pattern "<.*>|$.*";
                    }
                    type uint32 {
                      range "1 .. 2";
                    }
                  }
                  description
                    "External metric type for the default type 7 LSA";
                }
                leaf type-7 {
                  type empty;
                  description
                    "Flood type 7 default LSA if no-summaries is configured";
                }
              }
              leaf default-metric {
                type union {
                  type string {
                    pattern "<.*>|$.*";
                  }
                  type uint32 {
                    range "1 .. 16777215";
                  }
                }
                status deprecated;
                description
                  "Metric for the default route in this area";
              }
              leaf metric-type {
                type union {
                  type string {
                    pattern "<.*>|$.*";
                  }
                  type uint32 {
                    range "1 .. 2";
                  }
                }
                status deprecated;
                description
                  "External metric type for the default type 7 LSA";
              }
              choice summaries-choice {
                leaf summaries {
                  type empty;
                  description
                    "Flood summary LSAs into this NSSA area";
                }
                leaf no-summaries {
                  type empty;
                  description
                    "Don't flood summary LSAs into this NSSA area";
                }
              }
              list area-range {
                key "name";
                ordered-by user;
                description
                  "Configure NSSA area ranges";
                leaf name {
                  type jt:ipprefix;
                  description
                    "Range to summarize NSSA routes in this area";
                }
                uses apply-advanced;
                leaf restrict {
                  type empty;
                  description
                    "Restrict advertisement of this area range";
                }
                leaf exact {
                  type empty;
                  description
                    "Enforce exact match for advertisement of this area range";
                }
                container override-metric {
                  presence "enable override-metric";
                  description
                    "Override the dynamic metric for this area-range";
                  uses apply-advanced;
                  leaf metric {
                    type union {
                      type string {
                        pattern "<.*>|$.*";
                      }
                      type uint32 {
                        range "1 .. 16777215";
                      }
                    }
                    mandatory true;
                    description
                      "Metric value";
                  }
                  leaf metric-type {
                    type union {
                      type string {
                        pattern "<.*>|$.*";
                      }
                      type uint32 {
                        range "1 .. 2";
                      }
                    }
                    default "1";
                    description
                      "Set the metric type for the override metric";
                  }
                }
              }
            }
          }
        }
        list area-range {
          key "name";
          ordered-by user;
          description
            "Configure area ranges";
          leaf name {
            type jt:ipprefix;
            description
              "Range to summarize routes in this area";
          }
          uses apply-advanced;
          leaf restrict {
            type empty;
            description
              "Restrict advertisement of this area range";
          }
          leaf exact {
            type empty;
            description
              "Enforce exact match for advertisement of this area range";
          }
          leaf override-metric {
            type union {
              type string {
                pattern "<.*>|$.*";
              }
              type uint32 {
                range "1 .. 16777215";
              }
            }
            description
              "Override the dynamic metric for this area-range";
          }
        }
        leaf-list network-summary-export {
          type jt:policy-algebra;
          ordered-by user;
          description
            "Export policy for Type 3 Summary LSAs";
        }
        leaf-list network-summary-import {
          type jt:policy-algebra;
          ordered-by user;
          description
            "Import policy for Type 3 Summary LSAs";
        }
        leaf-list inter-area-prefix-export {
          type jt:policy-algebra;
          ordered-by user;
          description
            "Export policy for Inter Area Prefix LSAs";
        }
        leaf-list inter-area-prefix-import {
          type jt:policy-algebra;
          ordered-by user;
          description
            "Import policy for Inter Area Prefix LSAs";
        }
        leaf authentication-type {
          type enumeration {
            enum "none" {
              status deprecated;
              description
                "No authentication";
            }
            enum "simple" {
              status deprecated;
              description
                "Simple password authentication";
            }
            enum "md5" {
              status deprecated;
              description
                "MD5 authentication";
            }
          }
          status deprecated;
          description
            "Authentication type";
        }
        list virtual-link {
          key "neighbor-id transit-area";
          ordered-by user;
          description
            "Configure virtual links";
          leaf neighbor-id {
            type jt:ipv4addr;
            description
              "Router ID of a virtual neighbor";
          }
          leaf transit-area {
            type jt:areaid;
            description
              "Transit area in common with virtual neighbor";
          }
          uses apply-advanced;
          choice enable-disable {
            case case_1 {
              leaf disable {
                type empty;
                description
                  "Disable this virtual link";
              }
            }
          }
          leaf retransmit-interval {
            type union {
              type string {
                pattern "<.*>|$.*";
              }
              type uint32 {
                range "1 .. 65535";
              }
            }
            description
              "Retransmission interval (seconds)";
          }
          leaf transit-delay {
            type union {
              type string {
                pattern "<.*>|$.*";
              }
              type uint32 {
                range "1 .. 65535";
              }
            }
            description
              "Transit delay (seconds)";
          }
          leaf hello-interval {
            type union {
              type string {
                pattern "<.*>|$.*";
              }
              type uint32 {
                range "1 .. 255";
              }
            }
            description
              "Hello interval (seconds)";
          }
          leaf dead-interval {
            type union {
              type string {
                pattern "<.*>|$.*";
              }
              type uint32 {
                range "1 .. 65535";
              }
            }
            description
              "Dead interval (seconds)";
          }
          leaf mtu {
            type union {
              type string {
                pattern "<.*>|$.*";
              }
              type uint32 {
                range "128 .. 65535";
              }
            }
            description
              "Maximum OSPF packet size";
          }
          choice auth {
            case case_1 {
              container authentication {
                uses juniper-ospf-authentication;
              }
            }
            case case_2 {
              container authentication-key {
                status deprecated;
                description
                  "Authentication key";
                leaf keyname {
                  type jt:unreadable;
                  mandatory true;
                  description
                    "Authentication key value";
                }
                leaf key-id {
                  type union {
                    type string {
                      pattern "<.*>|$.*";
                    }
                    type uint32 {
                      range "0 .. 255";
                    }
                  }
                  description
                    "Key ID for MD5 authentication";
                }
              }
            }
          }
          leaf demand-circuit {
            type empty;
            description
              "Interface functions as a demand circuit";
          }
          leaf flood-reduction {
            type empty;
            description
              "Enable flood reduction";
          }
          leaf no-neighbor-down-notification {
            type empty;
            description
              "Don't inform other protocols about neighbor down events";
          }
          leaf ipsec-sa {
            type string {
              length "1 .. 32";
            }
            description
              "IPSec security association name";
          }
          list topology {
            key "name";
            ordered-by user;
            description
              "Topology specific attributes";
            leaf name {
              type string;
              description
                "Topology name";
            }
            uses apply-advanced;
            leaf disable {
              type empty;
              description
                "Disable this topology";
            }
            leaf metric {
              type union {
                type string {
                  pattern "<.*>|$.*";
                }
                type uint16 {
                  range "1 .. 65535";
                }
              }
              description
                "Topology metric";
            }
            container bandwidth-based-metrics {
              description
                "Configure bandwidth based metrics";
              uses apply-advanced;
              list bandwidth {
                key "name";
                description
                  "Bandwidth threshold";
                leaf name {
                  type string;
                }
                leaf metric {
                  type union {
                    type string {
                      pattern "<.*>|$.*";
                    }
                    type uint16 {
                      range "1 .. 65535";
                    }
                  }
                  mandatory true;
                  description
                    "Metric associated with specified bandwidth";
                }
              }
            }
          }
        }
        list sham-link-remote {
          key "name";
          ordered-by user;
          description
            "Configure parameters for remote sham link endpoint";
          leaf name {
            type jt:ipaddr;
            description
              "Remote sham link endpoint address";
          }
          uses apply-advanced;
          leaf metric {
            type union {
              type string {
                pattern "<.*>|$.*";
              }
              type uint16 {
                range "1 .. 65535";
              }
            }
            description
              "Sham link metric";
          }
          leaf ipsec-sa {
            type string {
              length "1 .. 32";
            }
            description
              "IPSec security association name";
          }
          leaf demand-circuit {
            type empty;
            description
              "Interface functions as a demand circuit";
          }
          leaf flood-reduction {
            type empty;
            description
              "Enable flood reduction";
          }
          list topology {
            key "name";
            ordered-by user;
            description
              "Topology specific attributes";
            leaf name {
              type string;
              description
                "Topology name";
            }
            uses apply-advanced;
            leaf disable {
              type empty;
              description
                "Disable this topology";
            }
            leaf metric {
              type union {
                type string {
                  pattern "<.*>|$.*";
                }
                type uint16 {
                  range "1 .. 65535";
                }
              }
              description
                "Topology metric";
            }
            container bandwidth-based-metrics {
              description
                "Configure bandwidth based metrics";
              uses apply-advanced;
              list bandwidth {
                key "name";
                description
                  "Bandwidth threshold";
                leaf name {
                  type string;
                }
                leaf metric {
                  type union {
                    type string {
                      pattern "<.*>|$.*";
                    }
                    type uint16 {
                      range "1 .. 65535";
                    }
                  }
                  mandatory true;
                  description
                    "Metric associated with specified bandwidth";
                }
              }
            }
          }
          leaf keychain {
            type string {
              length "1 .. 128";
            }
            description
              "Key chain name";
          }
        }
        list interface {
          key "name";
          ordered-by user;
          description
            "Include an interface in this area";
          leaf name {
            type union {
              type jt:ipv4addr-or-interface;
              type string {
                pattern "<.*>|$.*";
              }
            }
            description
              "Interface name";
          }
          uses apply-advanced;
          choice enable-disable {
            case case_1 {
              leaf disable {
                type empty;
                description
                  "Disable OSPF on this interface";
              }
            }
          }
          leaf interface-type {
            type enumeration {
              enum "nbma" {
                description
                  "Nonbroadcast multiaccess";
              }
              enum "p2mp" {
                description
                  "Point-to-multipoint NBMA";
              }
              enum "p2p" {
                description
                  "Point-to-point";
              }
              enum "p2mp-over-lan" {
                description
                  "Point-to-multipoint over LAN mode";
              }
            }
            description
              "Type of interface";
          }
          container passive {
            presence "enable passive";
            description
              "Do not run OSPF, but advertise it";
            uses apply-advanced;
            container traffic-engineering {
              description
                "Advertise TE link information";
              uses apply-advanced;
              leaf remote-node-id {
                type jt:ipaddr;
                description
                  "Remote address of the link";
              }
              leaf remote-node-router-id {
                type jt:ipv4addr;
                description
                  "TE Router-ID of the remote node";
              }
            }
          }
          leaf secondary {
            type empty;
            description
              "Treat interface as secondary";
          }
          leaf own-router-lsa {
            type empty;
            description
              "Generate a separate router LSA for this interface";
          }
          container bandwidth-based-metrics {
            description
              "Configure bandwidth based metrics";
            uses apply-advanced;
            list bandwidth {
              key "name";
              description
                "Bandwidth threshold";
              leaf name {
                type string;
              }
              leaf metric {
                type union {
                  type string {
                    pattern "<.*>|$.*";
                  }
                  type uint16 {
                    range "1 .. 65535";
                  }
                }
                mandatory true;
                description
                  "Metric associated with specified bandwidth";
              }
            }
          }
          leaf metric {
            type union {
              type string {
                pattern "<.*>|$.*";
              }
              type uint16 {
                range "1 .. 65535";
              }
            }
            description
              "Interface metric";
          }
          leaf priority {
            type union {
              type string {
                pattern "<.*>|$.*";
              }
              type uint32 {
                range "0 .. 255";
              }
            }
            description
              "Designated router priority";
          }
          leaf retransmit-interval {
            type union {
              type string {
                pattern "<.*>|$.*";
              }
              type uint32 {
                range "1 .. 65535";
              }
            }
            description
              "Retransmission interval (seconds)";
          }
          leaf transit-delay {
            type union {
              type string {
                pattern "<.*>|$.*";
              }
              type uint32 {
                range "1 .. 65535";
              }
            }
            description
              "Transit delay (seconds)";
          }
          leaf hello-interval {
            type union {
              type string {
                pattern "<.*>|$.*";
              }
              type uint32 {
                range "1 .. 255";
              }
            }
            description
              "Hello interval (seconds)";
          }
          leaf dead-interval {
            type union {
              type string {
                pattern "<.*>|$.*";
              }
              type uint32 {
                range "1 .. 65535";
              }
            }
            description
              "Dead interval (seconds)";
          }
          leaf mtu {
            type union {
              type string {
                pattern "<.*>|$.*";
              }
              type uint32 {
                range "128 .. 65535";
              }
            }
            description
              "Maximum OSPF packet size";
          }
          choice auth {
            case case_1 {
              container authentication {
                uses juniper-ospf-authentication;
              }
            }
            case case_2 {
              container authentication-key {
                status deprecated;
                description
                  "Authentication key";
                leaf keyname {
                  type jt:unreadable;
                  mandatory true;
                  description
                    "Authentication key value";
                }
                leaf key-id {
                  type union {
                    type string {
                      pattern "<.*>|$.*";
                    }
                    type uint32 {
                      range "0 .. 255";
                    }
                  }
                  description
                    "Key ID for MD5 authentication";
                }
              }
            }
          }
          leaf demand-circuit {
            type empty;
            description
              "Interface functions as a demand circuit";
          }
          leaf flood-reduction {
            type empty;
            description
              "Enable flood reduction";
          }
          leaf no-neighbor-down-notification {
            type empty;
            description
              "Don't inform other protocols about neighbor down events";
          }
          list topology {
            key "name";
            ordered-by user;
            description
              "Topology specific attributes";
            leaf name {
              type string;
              description
                "Topology name";
            }
            uses apply-advanced;
            leaf disable {
              type empty;
              description
                "Disable this topology";
            }
            leaf metric {
              type union {
                type string {
                  pattern "<.*>|$.*";
                }
                type uint16 {
                  range "1 .. 65535";
                }
              }
              description
                "Topology metric";
            }
            container bandwidth-based-metrics {
              description
                "Configure bandwidth based metrics";
              uses apply-advanced;
              list bandwidth {
                key "name";
                description
                  "Bandwidth threshold";
                leaf name {
                  type string;
                }
                leaf metric {
                  type union {
                    type string {
                      pattern "<.*>|$.*";
                    }
                    type uint16 {
                      range "1 .. 65535";
                    }
                  }
                  mandatory true;
                  description
                    "Metric associated with specified bandwidth";
                }
              }
            }
          }
          leaf transmit-interval {
            type union {
              type string {
                pattern "<.*>|$.*";
              }
              type uint32 {
                range "1 .. 4294967295";
              }
            }
            status deprecated;
            description
              "OSPF packet transmit interval (milliseconds)";
          }
          container bfd-liveness-detection {
            description
              "Bidirectional Forwarding Detection options";
            uses apply-advanced;
            leaf version {
              type enumeration {
                enum "0" {
                  description
                    "BFD version 0 (deprecated)";
                }
                enum "1" {
                  description
                    "BFD version 1";
                }
                enum "automatic" {
                  description
                    "Choose BFD version automatically";
                }
              }
              default "automatic";
              description
                "BFD protocol version number";
            }
            leaf minimum-interval {
              type union {
                type string {
                  pattern "<.*>|$.*";
                }
                type uint32 {
                  range "1 .. 255000";
                }
              }
              units "milliseconds";
              description
                "Minimum transmit and receive interval";
            }
            leaf minimum-transmit-interval {
              type union {
                type string {
                  pattern "<.*>|$.*";
                }
                type uint32 {
                  range "1 .. 255000";
                }
              }
              units "milliseconds";
              status deprecated;
              description
                "Minimum transmit interval";
            }
            leaf minimum-receive-interval {
              type union {
                type string {
                  pattern "<.*>|$.*";
                }
                type uint32 {
                  range "1 .. 255000";
                }
              }
              units "milliseconds";
              description
                "Minimum receive interval";
            }
            leaf multiplier {
              type union {
                type string {
                  pattern "<.*>|$.*";
                }
                type uint32 {
                  range "1 .. 255";
                }
              }
              default "3";
              description
                "Detection time multiplier";
            }
            leaf inline-disable {
              type empty;
              description
                "Disable inline mode for this BFD session";
            }
            leaf pdu-size {
              type union {
                type string {
                  pattern "<.*>|$.*";
                }
                type uint32 {
                  range "24 .. 16000";
                }
              }
              default "24";
              description
                "BFD transport protocol payload size";
            }
            choice adaptation-choice {
              case case_1 {
                leaf no-adaptation {
                  type empty;
                  description
                    "Disable adaptation";
                }
              }
            }
            container transmit-interval {
              description
                "Transmit-interval options";
              uses apply-advanced;
              leaf minimum-interval {
                type union {
                  type string {
                    pattern "<.*>|$.*";
                  }
                  type uint32 {
                    range "1 .. 255000";
                  }
                }
                units "milliseconds";
                description
                  "Minimum transmit interval";
              }
              leaf threshold {
                type union {
                  type uint32;
                  type string {
                    pattern "<.*>|$.*";
                  }
                }
                units "milliseconds";
                description
                  "High transmit interval triggering a trap";
              }
            }
            container detection-time {
              description
                "Detection-time options";
              uses apply-advanced;
              leaf threshold {
                type union {
                  type uint32;
                  type string {
                    pattern "<.*>|$.*";
                  }
                }
                units "milliseconds";
                description
                  "High detection-time triggering a trap";
              }
            }
            container authentication {
              description
                "Authentication options";
              uses apply-advanced;
              leaf key-chain {
                type string;
                description
                  "Key chain name";
              }
              leaf algorithm {
                type enumeration {
                  enum "simple-password" {
                    description
                      "Simple password";
                  }
                  enum "keyed-md5" {
                    description
                      "Keyed message Digest 5";
                  }
                  enum "meticulous-keyed-md5" {
                    description
                      "Meticulous keyed message Digest 5";
                  }
                  enum "keyed-sha-1" {
                    description
                      "Keyed secure hash algorithm (SHA1) ";
                  }
                  enum "meticulous-keyed-sha-1" {
                    description
                      "Meticulous keyed secure hash algorithm (SHA1) ";
                  }
                }
                description
                  "Algorithm name";
              }
              leaf loose-check {
                type empty;
                description
                  "Verify authentication only if authentication is negotiated";
              }
            }
            container echo {
              description
                "Echo mode parameters";
              uses apply-advanced;
              leaf minimum-interval {
                type union {
                  type string {
                    pattern "<.*>|$.*";
                  }
                  type uint32 {
                    range "100 .. 255000";
                  }
                }
                units "milliseconds";
                description
                  "Minimum transmit and receive interval";
              }
            }
            container echo-lite {
              description
                "Echo-lite more parameters";
              uses apply-advanced;
              leaf minimum-interval {
                type union {
                  type string {
                    pattern "<.*>|$.*";
                  }
                  type uint32 {
                    range "100 .. 255000";
                  }
                }
                units "milliseconds";
                description
                  "Minimum transmit and receive interval";
              }
            }
            leaf full-neighbors-only {
              type empty;
              description
                "Setup BFD sessions only to Full neighbors";
            }
            leaf holddown-interval {
              type union {
                type string {
                  pattern "<.*>|$.*";
                }
                type uint32 {
                  range "0 .. 255000";
                }
              }
              units "milliseconds";
              description
                "Time to hold the session-UP notification to the client";
            }
          }
          leaf dynamic-neighbors {
            type empty;
            description
              "Learn neighbors dynamically on a p2mp interface";
          }
          leaf no-advertise-adjacency-segment {
            type empty;
            description
              "Do not advertise an adjacency segment for this interface";
          }
          list neighbor {
            key "name";
            ordered-by user;
            description
              "NBMA neighbor";
            leaf name {
              type jt:ipaddr;
              description
                "Address of neighbor";
            }
            leaf eligible {
              type empty;
              description
                "Eligible to be DR on an NBMA network";
            }
          }
          leaf poll-interval {
            type union {
              type string {
                pattern "<.*>|$.*";
              }
              type uint32 {
                range "1 .. 65535";
              }
            }
            description
              "Poll interval for NBMA interfaces";
          }
          leaf no-interface-state-traps {
            type empty;
            description
              "Do not send interface state change traps";
          }
          leaf strict-bfd {
            type empty;
            description
              "Enable strict bfd over this interface";
          }
          container post-convergence-lfa {
            presence "enable post-convergence-lfa";
            description
              "Protect interface using post-convergence backup path";
            uses apply-advanced;
          }
          leaf te-metric {
            type union {
              type string {
                pattern "<.*>|$.*";
              }
              type uint32 {
                range "1 .. 4294967295";
              }
            }
            description
              "Traffic engineering metric";
          }
          container ldp-synchronization {
            presence "enable ldp-synchronization";
            description
              "Advertise maximum metric until LDP is operational";
            uses ldp-sync-obj;
          }
          container ipv4-adjacency-segment {
            description
              "Configure ipv4 adjacency segment";
            uses apply-advanced;
            container unprotected {
              description
                "Adjacency SID uneligible for protection";
              choice adjsid-type {
                case case_1 {
                  container index {
                    description
                      "Adjacency SID indexed from SRGB";
                    leaf index-number {
                      type union {
                        type string {
                          pattern "<.*>|$.*";
                        }
                        type uint32 {
                          range "0 .. 199999";
                        }
                      }
                    }
                  }
                }
                case case_2 {
                  leaf label {
                    type union {
                      type string {
                        pattern "<.*>|$.*";
                      }
                      type uint32 {
                        range "16 .. 1048575";
                      }
                    }
                    description
                      "Adjacency SID from static label pool";
                  }
                }
                case case_3 {
                  leaf dynamic {
                    type empty;
                    description
                      "Dynamically allocate an adjacency segment";
                  }
                }
              }
            }
          }
          list lan-neighbor {
            key "name";
            ordered-by user;
            description
              "Configuration specific to a LAN neighbor";
            leaf name {
              type jt:ipaddr;
              description
                "Address of neighbor";
            }
            uses apply-advanced;
            container ipv4-adjacency-segment {
              description
                "Configure ipv4 adjacency segment";
              uses apply-advanced;
              container protected {
                description
                  "Adjacency SID is eligible for protection";
                choice adjsid-type {
                  case case_1 {
                    container index {
                      description
                        "Adjacency SID indexed from SRGB";
                      leaf index-number {
                        type union {
                          type string {
                            pattern "<.*>|$.*";
                          }
                          type uint32 {
                            range "0 .. 199999";
                          }
                        }
                      }
                    }
                  }
                  case case_2 {
                    leaf label {
                      type union {
                        type string {
                          pattern "<.*>|$.*";
                        }
                        type uint32 {
                          range "16 .. 1048575";
                        }
                      }
                      description
                        "Adjacency SID from static label pool";
                    }
                  }
                  case case_3 {
                    leaf dynamic {
                      type empty;
                      description
                        "Dynamically allocate an adjacency segment";
                    }
                  }
                }
              }
              container unprotected {
                description
                  "Adjacency SID uneligible for protection";
                choice adjsid-type {
                  case case_1 {
                    container index {
                      description
                        "Adjacency SID indexed from SRGB";
                      leaf index-number {
                        type union {
                          type string {
                            pattern "<.*>|$.*";
                          }
                          type uint32 {
                            range "0 .. 199999";
                          }
                        }
                      }
                    }
                  }
                  case case_2 {
                    leaf label {
                      type union {
                        type string {
                          pattern "<.*>|$.*";
                        }
                        type uint32 {
                          range "16 .. 1048575";
                        }
                      }
                      description
                        "Adjacency SID from static label pool";
                    }
                  }
                  case case_3 {
                    leaf dynamic {
                      type empty;
                      description
                        "Dynamically allocate an adjacency segment";
                    }
                  }
                }
              }
            }
          }
          leaf delay-metric {
            type union {
              type string {
                pattern "<.*>|$.*";
              }
              type uint32 {
                range "0 .. 16777215";
              }
            }
            units "microseconds";
            description
              "Delay metric";
          }
          container delay-measurement {
            presence "enable delay-measurement";
            description
              "Enable delay measurement";
            uses apply-advanced;
            leaf probe-interval {
              type union {
                type string {
                  pattern "<.*>|$.*";
                }
                type uint32 {
                  range "1 .. 255";
                }
              }
              units "seconds";
              description
                "Probe interval";
            }
            leaf probe-count {
              type union {
                type string {
                  pattern "<.*>|$.*";
                }
                type uint32 {
                  range "1 .. 15";
                }
              }
              description
                "Probe count";
            }
            container advertisement {
              description
                "Delay advertisement";
              uses apply-advanced;
              container periodic {
                description
                  "Periodic advertisement parameters";
                uses apply-advanced;
                leaf threshold {
                  type union {
                    type string {
                      pattern "<.*>|$.*";
                    }
                    type uint32 {
                      range "0 .. 100";
                    }
                  }
                  units "percentage";
                  description
                    "Threshold";
                }
                leaf interval {
                  type union {
                    type string {
                      pattern "<.*>|$.*";
                    }
                    type uint32 {
                      range "30 .. 3600";
                    }
                  }
                  units "seconds";
                  description
                    "Interval";
                }
              }
              container accelerated {
                presence "enable accelerated";
                description
                  "Accelerated advertisement parameters";
                uses apply-advanced;
                leaf threshold {
                  type union {
                    type string {
                      pattern "<.*>|$.*";
                    }
                    type uint32 {
                      range "0 .. 100";
                    }
                  }
                  units "percentage";
                  description
                    "Threshold";
                }
              }
            }
          }
          container application-specific {
            description
              "Advertise application-specific TE attributes";
            uses apply-advanced;
            list attribute-group {
              key "name";
              max-elements 1;
              ordered-by user;
              description
                "Link attribute group name";
              leaf name {
                type string;
                description
                  "Link attribute group name";
              }
              uses apply-advanced;
              leaf te-metric {
                type union {
                  type string {
                    pattern "<.*>|$.*";
                  }
                  type uint32 {
                    range "1 .. 4294967295";
                  }
                }
                description
                  "Traffic engineering metric for this attribute group";
              }
              leaf-list admin-group {
                type string;
                max-elements 16;
                ordered-by user;
                description
                  "Administrative groups for this attribute-group";
              }
              leaf delay-metric {
                type union {
                  type string {
                    pattern "<.*>|$.*";
                  }
                  type uint32 {
                    range "0 .. 16777215";
                  }
                }
                units "microseconds";
                description
                  "Delay metric for this attribute-group";
              }
              leaf advertise-interface-delay {
                type empty;
                description
                  "Use interface specific static/dynamic delay values as applicable in ASLA Sub-TLVs";
              }
              container application {
                description
                  "Standard Applications part of this attribute-group";
                uses apply-advanced;
                leaf flex-algorithm {
                  type empty;
                  description
                    "Set X flag in standard application bit mask";
                }
              }
            }
          }
        }
        leaf no-source-packet-routing {
          type empty;
          description
            "Disable SPRING in this area";
        }
      }
      choice enable-disable {
        case case_1 {
          leaf disable {
            type empty;
            description
              "Disable OSPF";
          }
        }
      }
      container traceoptions {
        description
          "Trace options for OSPF";
        uses apply-advanced;
        container file {
          description
            "Trace file options";
          leaf filename {
            type string {
              length "1 .. 1024";
            }
            description
              "Name of file in which to write trace information";
          }
          leaf replace {
            type empty;
            status deprecated;
            description
              "Replace trace file rather than appending to it";
          }
          leaf size {
            type string;
            description
              "Maximum trace file size";
          }
          leaf files {
            type union {
              type string {
                pattern "<.*>|$.*";
              }
              type uint32 {
                range "2 .. 1000";
              }
            }
            default "10";
            description
              "Maximum number of trace files";
          }
          leaf no-stamp {
            type empty;
            status deprecated;
            description
              "Do not timestamp trace file";
          }
          choice world-readable-choice {
            leaf world-readable {
              type empty;
              description
                "Allow any user to read the log file";
            }
            leaf no-world-readable {
              type empty;
              description
                "Don't allow any user to read the log file";
            }
          }
        }
        list flag {
          key "name";
          ordered-by user;
          description
            "Tracing parameters";
          leaf name {
            type enumeration {
              enum "spf" {
                description
                  "Trace SPF calculations";
              }
              enum "error" {
                description
                  "Trace errored packets";
              }
              enum "event" {
                description
                  "Trace OSPF state machine events";
              }
              enum "packet-dump" {
                description
                  "Dump the contents of selected packet types";
              }
              enum "flooding" {
                description
                  "Trace LSA flooding";
              }
              enum "lsa-analysis" {
                description
                  "Trace LSA analysis";
              }
              enum "packets" {
                description
                  "Trace all OSPF packets";
              }
              enum "hello" {
                description
                  "Trace hello packets";
              }
              enum "database-description" {
                description
                  "Trace database description packets";
              }
              enum "lsa-request" {
                description
                  "Trace LSA request packets";
              }
              enum "lsa-update" {
                description
                  "Trace LSA update packets";
              }
              enum "lsa-ack" {
                description
                  "Trace LSA acknowledgment packets";
              }
              enum "ldp-synchronization" {
                description
                  "Trace synchronization between OSPF and LDP";
              }
              enum "on-demand" {
                description
                  "Trace demand circuit extensions";
              }
              enum "nsr-synchronization" {
                description
                  "Trace NSR synchronization events";
              }
              enum "graceful-restart" {
                description
                  "Trace graceful restart";
              }
              enum "restart-signaling" {
                description
                  "Trace restart signaling";
              }
              enum "traffic-statistics" {
                description
                  "Trace Segment Routing Traffic Statistics";
              }
              enum "backup-spf" {
                description
                  "Trace backup SPF (LFA) specific events";
              }
              enum "source-packet-routing" {
                description
                  "Trace source packet routing (SPRING) events";
              }
              enum "post-convergence-lfa" {
                description
                  "Trace post-convergence-lfa related events";
              }
              enum "flex-algorithm" {
                description
                  "Trace flex-algorithm related events";
              }
              enum "rmopd" {
                description
                  "Trace rmopd interactions";
              }
              enum "route" {
                description
                  "Trace routing information";
              }
              enum "normal" {
                description
                  "Trace normal events";
              }
              enum "general" {
                description
                  "Trace general events";
              }
              enum "state" {
                description
                  "Trace state transitions";
              }
              enum "policy" {
                description
                  "Trace policy processing";
              }
              enum "task" {
                description
                  "Trace routing protocol task processing";
              }
              enum "timer" {
                description
                  "Trace routing protocol timer processing";
              }
              enum "all" {
                description
                  "Trace everything";
              }
            }
          }
          leaf send {
            type empty;
            description
              "Trace transmitted packets";
          }
          leaf receive {
            type empty;
            description
              "Trace received packets";
          }
          leaf detail {
            type empty;
            description
              "Trace detailed information";
          }
          leaf disable {
            type empty;
            description
              "Disable this trace flag";
          }
        }
      }
      leaf prefix-export-limit {
        type union {
          type string {
            pattern "<.*>|$.*";
          }
          type uint32 {
            range "0 .. 4294967295";
          }
        }
        description
          "Maximum number of prefixes that can be exported";
      }
      container rib-groups {
        description
          "Routing table groups for importing OSPF routes";
        uses apply-advanced;
        leaf inet {
          type string;
          description
            "Name of the IPv4/v6 routing table group";
        }
        leaf inet3 {
          type string;
          description
            "Name of the IPv4/v6 inet.3 routing table group";
        }
      }
      leaf job-stats {
        type empty;
        description
          "Collect job statistics";
      }
      container overload {
        presence "enable overload";
        description
          "Set the overload mode (repel transit traffic)";
        uses apply-advanced;
        leaf timeout {
          type union {
            type string {
              pattern "<.*>|$.*";
            }
            type uint32 {
              range "60 .. 3600";
            }
          }
          units "seconds";
          description
            "Time after which overload mode is reset";
        }
        leaf allow-route-leaking {
          type empty;
          description
            "Allow routes to be leaked when overload is configured";
        }
        leaf stub-network {
          type empty;
          description
            "Advertise Stub Network with maximum metric";
        }
        leaf intra-area-prefix {
          type empty;
          description
            "Advertise Intra Area Prefix with maximum metric";
        }
        leaf as-external {
          type empty;
          description
            "Advertise As External with maximum usable metric";
        }
      }
      container database-protection {
        presence "enable database-protection";
        description
          "Configure database protection attributes";
        uses apply-advanced;
        leaf maximum-lsa {
          type union {
            type string {
              pattern "<.*>|$.*";
            }
            type uint32 {
              range "1 .. 1000000";
            }
          }
          mandatory true;
          description
            "Maximum allowed non self-generated LSAs";
        }
        leaf warning-only {
          type empty;
          description
            "Emit only a warning when LSA maximum limit is exceeded";
        }
        leaf warning-threshold {
          type union {
            type string {
              pattern "<.*>|$.*";
            }
            type uint8 {
              range "30 .. 100";
            }
          }
          units "percent";
          description
            "Percentage of LSA maximum above which to trigger warning";
        }
        leaf ignore-count {
          type union {
            type string {
              pattern "<.*>|$.*";
            }
            type uint8 {
              range "1 .. 32";
            }
          }
          description
            "Maximum number of times to go into ignore state";
        }
        leaf ignore-time {
          type union {
            type string {
              pattern "<.*>|$.*";
            }
            type uint16 {
              range "30 .. 3600";
            }
          }
          units "seconds";
          description
            "Time to stay in ignore state and ignore all neighbors";
        }
        leaf reset-time {
          type union {
            type string {
              pattern "<.*>|$.*";
            }
            type uint32 {
              range "60 .. 86400";
            }
          }
          units "seconds";
          description
            "Time after which the ignore count gets reset to zero";
        }
      }
      container graceful-restart {
        description
          "Configure graceful restart attributes";
        uses apply-advanced;
        choice enable-disable {
          case case_1 {
            leaf disable {
              type empty;
              description
                "Disable OSPF graceful restart capability";
            }
          }
        }
        leaf restart-duration {
          type union {
            type string {
              pattern "<.*>|$.*";
            }
            type uint32 {
              range "1 .. 3600";
            }
          }
          units "seconds";
          description
            "Time for all neighbors to become full";
        }
        leaf notify-duration {
          type union {
            type string {
              pattern "<.*>|$.*";
            }
            type uint32 {
              range "1 .. 3600";
            }
          }
          units "seconds";
          description
            "Time to send all max-aged grace LSAs";
        }
        container helper-disable {
          presence "enable helper-disable";
          description
            "Disable graceful restart helper capability";
          uses apply-advanced;
          choice disable-choices {
            case case_1 {
              leaf standard {
                type empty;
                description
                  "Disable helper-mode for rfc3623 based GR";
              }
            }
            case case_2 {
              leaf restart-signaling {
                type empty;
                description
                  "Disable helper mode for restart-signaling ";
              }
            }
            case case_3 {
              leaf both {
                type empty;
                description
                  "Disable helper mode for both the types of GR";
              }
            }
          }
        }
        leaf no-strict-lsa-checking {
          type empty;
          description
            "Do not abort graceful helper mode upon LSA changes";
        }
      }
      leaf route-type-community {
        type enumeration {
          enum "iana" {
            description
              "BGP extended community value used is 0x0306";
          }
          enum "vendor" {
            description
              "Vendor BGP extended community value used is 0x8000";
          }
        }
        description
          "Specify BGP extended community value to encode OSPF route type";
      }
      container domain-id {
        description
          "Configure domain ID";
        choice domain_id_or_disable {
          case case_1 {
            leaf domain-id {
              type string;
              description
                "Domain ID";
            }
          }
          case case_2 {
            leaf disable {
              type empty;
              description
                "Disable domain ID";
            }
          }
        }
      }
      choice domain_vpn_tag_or_disable {
        case case_1 {
          leaf domain-vpn-tag {
            type union {
              type string {
                pattern "<.*>|$.*";
              }
              type uint32 {
                range "0 .. 4294967295";
              }
            }
            description
              "Domain VPN tag for external LSA";
          }
        }
        case case_2 {
          leaf no-domain-vpn-tag {
            type empty;
            description
              "Disable domain VPN tag";
          }
        }
      }
      leaf preference {
        type union {
          type uint32;
          type string {
            pattern "<.*>|$.*";
          }
        }
        description
          "Preference of internal routes";
      }
      leaf external-preference {
        type union {
          type uint32;
          type string {
            pattern "<.*>|$.*";
          }
        }
        description
          "Preference of external routes";
      }
      leaf labeled-preference {
        type union {
          type uint32;
          type string {
            pattern "<.*>|$.*";
          }
        }
        description
          "Preference of labeled routes";
      }
      leaf-list export {
        type jt:policy-algebra;
        ordered-by user;
        description
          "Export policy";
      }
      leaf-list import {
        type jt:policy-algebra;
        ordered-by user;
        description
          "Import policy (for external routes or setting priority)";
      }
      leaf reference-bandwidth {
        type string;
        description
          "Bandwidth for calculating metric defaults";
      }
      leaf lsa-refresh-interval {
        type union {
          type string {
            pattern "<.*>|$.*";
          }
          type uint32 {
            range "25 .. 50";
          }
        }
        default "50";
        description
          "LSA refresh interval (minutes)";
      }
      leaf spf-delay {
        type union {
          type string {
            pattern "<.*>|$.*";
          }
          type uint32 {
            range "50 .. 8000";
          }
        }
        units "milliseconds";
        status deprecated;
        description
          "Time to wait before running an SPF";
      }
      leaf no-rfc-1583 {
        type empty;
        description
          "Disable RFC1583 compatibility";
      }
      leaf forwarding-address-to-broadcast {
        type empty;
        description
          "Set forwarding address in Type 5 LSA in broadcast network";
      }
      choice nssa-abr-option {
        case case_1 {
          leaf no-nssa-abr {
            type empty;
            description
              "Disable full NSSA functionality at ABR";
          }
        }
      }
      container sham-link {
        presence "enable sham-link";
        description
          "Configure parameters for sham links";
        uses apply-advanced;
        leaf local {
          type jt:ipaddr;
          description
            "Local sham link endpoint address";
        }
        leaf no-advertise-local {
          type empty;
          status deprecated;
          description
            "Don't advertise local sham link endpoint as stub in router LSA";
        }
      }
    }
    uses apply-advanced;
    list topology {
      key "name";
      ordered-by user;
      description
        "Topology parameters";
      leaf name {
        type string;
        description
          "Topology name";
      }
      uses apply-advanced;
      leaf disable {
        type empty;
        description
          "Disable this topology";
      }
      leaf topology-id {
        type union {
          type string {
            pattern "<.*>|$.*";
          }
          type uint8 {
            range "32 .. 127";
          }
        }
        description
          "Topology identifier";
      }
      leaf overload {
        type empty;
        description
          "Set the overload mode (repel transit traffic)";
      }
      leaf rib-group {
        type string;
        description
          "Routing table group for importing routes";
      }
      container spf-options {
        description
          "Configure options for SPF";
        uses apply-advanced;
        container microloop-avoidance {
          description
            "Configure microloop avoidance mechanism";
          uses apply-advanced;
          container post-convergence-path {
            presence "enable post-convergence-path";
            description
              "Temporarily install post-convergence path for routes potentially affected by microloops";
            uses apply-advanced;
            leaf delay {
              type union {
                type string {
                  pattern "<.*>|$.*";
                }
                type uint32 {
                  range "500 .. 60000";
                }
              }
              units "milliseconds";
              description
                "Time after which temporary post-convergence paths are removed";
            }
            leaf maximum-labels {
              type union {
                type string {
                  pattern "<.*>|$.*";
                }
                type uint32 {
                  range "2 .. 8";
                }
              }
              description
                "Maximum number of labels installed for post-convergence paths";
            }
          }
        }
        leaf delay {
          type union {
            type string {
              pattern "<.*>|$.*";
            }
            type uint32 {
              range "50 .. 8000";
            }
          }
          units "milliseconds";
          description
            "Time to wait before running an SPF";
        }
        leaf holddown {
          type union {
            type string {
              pattern "<.*>|$.*";
            }
            type uint32 {
              range "2000 .. 20000";
            }
          }
          units "milliseconds";
          description
            "Time to hold down before running an SPF";
        }
        leaf rapid-runs {
          type union {
            type string {
              pattern "<.*>|$.*";
            }
            type uint32 {
              range "1 .. 10";
            }
          }
          description
            "Number of maximum rapid SPF runs before holddown";
        }
        leaf no-ignore-our-externals {
          type empty;
          description
            "Do not ignore self-generated external and NSSA LSAs";
        }
        container multipath {
          description
            "Configure multipath options";
          uses apply-advanced;
          container weighted {
            description
              "Weighted multipath options";
            uses apply-advanced;
            leaf one-hop {
              type empty;
              description
                "Enable load balancing on onehop multipath based on interface bandwidth";
            }
          }
        }
      }
      container backup-spf-options {
        description
          "Configure options for backup SPF";
        uses apply-advanced;
        container remote-backup-calculation {
          presence "enable remote-backup-calculation";
          description
            "Calculate Remote LFA backup nexthops";
          uses apply-advanced;
          container pq-nodes-nearest-to-source {
            description
              "PQ nodes selection based upon nearest to source";
            uses apply-advanced;
            leaf percent {
              type union {
                type string {
                  pattern "<.*>|$.*";
                }
                type uint32 {
                  range "10 .. 100";
                }
              }
              description
                "Selection percentage for nearest to source";
            }
          }
        }
        container use-post-convergence-lfa {
          presence "enable use-post-convergence-lfa";
          description
            "Calculate post-convergence backup paths";
          uses apply-advanced;
          leaf maximum-labels {
            type union {
              type string {
                pattern "<.*>|$.*";
              }
              type uint32 {
                range "2 .. 8";
              }
            }
            description
              "Maximum number of labels installed for post-convergence paths";
          }
          leaf maximum-backup-paths {
            type union {
              type string {
                pattern "<.*>|$.*";
              }
              type uint32 {
                range "1 .. 8";
              }
            }
            description
              "Maximum number of equal-cost post-convergence paths installed";
          }
        }
        leaf use-source-packet-routing {
          type empty;
          description
            "Use spring backup paths for inet.0 routes";
        }
        leaf disable {
          type empty;
          description
            "Do not run backup SPF";
        }
        leaf no-install {
          type empty;
          description
            "Do not install backup nexthops into the RIB";
        }
        leaf downstream-paths-only {
          type empty;
          description
            "Use only downstream backup paths";
        }
        container per-prefix-calculation {
          description
            "Calculate backup nexthops for non-best prefix originators";
          uses apply-advanced;
          leaf stubs {
            type empty;
            description
              "Per prefix calculation for stubs only";
          }
          leaf summary {
            type empty;
            description
              "Per prefix calculation for summary originators only";
          }
          leaf externals {
            type empty;
            description
              "Per prefix calculation for externals";
          }
          leaf all {
            type empty;
            description
              "Per prefix calculation for all";
          }
        }
        leaf node-link-degradation {
          type empty;
          description
            "Degrade to link protection when nodelink protection not available";
        }
      }
      leaf prefix-export-limit {
        type union {
          type string {
            pattern "<.*>|$.*";
          }
          type uint32 {
            range "0 .. 4294967295";
          }
        }
        description
          "Maximum number of prefixes that can be exported";
      }
    }
    container spf-options {
      description
        "Configure options for SPF";
      uses apply-advanced;
      container microloop-avoidance {
        description
          "Configure microloop avoidance mechanism";
        uses apply-advanced;
        container post-convergence-path {
          presence "enable post-convergence-path";
          description
            "Temporarily install post-convergence path for routes potentially affected by microloops";
          uses apply-advanced;
          leaf delay {
            type union {
              type string {
                pattern "<.*>|$.*";
              }
              type uint32 {
                range "500 .. 60000";
              }
            }
            units "milliseconds";
            description
              "Time after which temporary post-convergence paths are removed";
          }
          leaf maximum-labels {
            type union {
              type string {
                pattern "<.*>|$.*";
              }
              type uint32 {
                range "2 .. 8";
              }
            }
            description
              "Maximum number of labels installed for post-convergence paths";
          }
        }
      }
      leaf delay {
        type union {
          type string {
            pattern "<.*>|$.*";
          }
          type uint32 {
            range "50 .. 8000";
          }
        }
        units "milliseconds";
        description
          "Time to wait before running an SPF";
      }
      leaf holddown {
        type union {
          type string {
            pattern "<.*>|$.*";
          }
          type uint32 {
            range "2000 .. 20000";
          }
        }
        units "milliseconds";
        description
          "Time to hold down before running an SPF";
      }
      leaf rapid-runs {
        type union {
          type string {
            pattern "<.*>|$.*";
          }
          type uint32 {
            range "1 .. 10";
          }
        }
        description
          "Number of maximum rapid SPF runs before holddown";
      }
      leaf no-ignore-our-externals {
        type empty;
        description
          "Do not ignore self-generated external and NSSA LSAs";
      }
      container multipath {
        description
          "Configure multipath options";
        uses apply-advanced;
        container weighted {
          description
            "Weighted multipath options";
          uses apply-advanced;
          leaf one-hop {
            type empty;
            description
              "Enable load balancing on onehop multipath based on interface bandwidth";
          }
        }
      }
    }
    container source-packet-routing {
      presence "enable source-packet-routing";
      description
        "Enable source packet routing (SPRING)";
      uses apply-advanced;
      container adjacency-segment {
        description
          "Attributes for adjacency segments in spring";
        uses apply-advanced;
        leaf hold-time {
          type union {
            type string {
              pattern "<.*>|$.*";
            }
            type uint32 {
              range "180000 .. 900000";
            }
          }
          description
            "Retain time of Adjacency segment after isolating from an interface";
        }
      }
      leaf-list prefix-segment {
        type jt:policy-algebra;
        ordered-by user;
        description
          "Prefix Segment policy";
      }
      leaf explicit-null {
        type empty;
        description
          "Set E and P bits in all Prefix SID advertisements";
      }
      container node-segment {
        presence "enable node-segment";
        description
          "Enable support for Node segments in SPRING";
        uses apply-advanced;
        leaf ipv4-index {
          type union {
            type string {
              pattern "<.*>|$.*";
            }
            type uint32 {
              range "0 .. 199999";
            }
          }
          description
            "Set ipv4 node segment index";
        }
        leaf index-range {
          type union {
            type string {
              pattern "<.*>|$.*";
            }
            type uint32 {
              range "32 .. 16385";
            }
          }
          description
            "Set range of node segment indices allowed";
        }
      }
      container srgb {
        description
          "Set the SRGB global block in SPRING";
        leaf start-label {
          type union {
            type string {
              pattern "<.*>|$.*";
            }
            type uint32 {
              range "16 .. 1048575";
            }
          }
          description
            "Start range for SRGB label block";
        }
        leaf index-range {
          type union {
            type string {
              pattern "<.*>|$.*";
            }
            type uint32 {
              range "32 .. 1048559";
            }
          }
          mandatory true;
          description
            "Index to the SRGB start label block";
        }
      }
      leaf mapping-server {
        type string;
        description
          "Mapping server name";
      }
      leaf install-prefix-sid-for-best-route {
        type empty;
        description
          "For best route install a exact prefix sid route";
      }
      leaf ldp-stitching {
        type empty;
        description
          "Enable SR to LDP stitching";
      }
      leaf-list flex-algorithm {
        type union {
          type string {
            pattern "<.*>|$.*";
          }
          type uint32 {
            range "128 .. 255";
          }
        }
        max-elements 16;
        description
          "Flex-algorithms we would like to participate in";
      }
      leaf strict-asla-based-flex-algorithm {
        type empty;
        description
          "Flex-Algorithm to ignore links not having ASLA sub-TLVs";
      }
      container sensor-based-stats {
        description
          "Configure sensor based stats in SPRING";
        uses apply-advanced;
        container per-interface-per-member-link {
          description
            "Configure sensor based stats per nexthop";
          leaf ingress {
            type empty;
            description
              "Enable sensor based stats on ingress interface";
          }
          leaf egress {
            type empty;
            description
              "Enable sensor based stats on egress interface";
          }
        }
        container per-sid {
          description
            "Configure sensor based stats per spring route";
          leaf ingress {
            type empty;
            description
              "Enable sensor based stats for per-sid ingress accounting";
          }
          leaf egress {
            type empty;
            description
              "Enable sensor based stats for IP-MPLS egress accounting";
          }
        }
      }
    }
    list area {
      key "name";
      ordered-by user;
      description
        "Configure an OSPF area";
      leaf name {
        type jt:areaid;
        description
          "Area ID";
      }
      uses apply-advanced;
      choice stub-option {
        case case_1 {
          container stub {
            presence "enable stub";
            description
              "Configure a stub area";
            leaf default-metric {
              type union {
                type string {
                  pattern "<.*>|$.*";
                }
                type uint32 {
                  range "1 .. 16777215";
                }
              }
              description
                "Metric for the default route in this stub area";
            }
            choice summaries-choice {
              leaf summaries {
                type empty;
                description
                  "Flood summary LSAs into this stub area";
              }
              leaf no-summaries {
                type empty;
                description
                  "Don't flood summary LSAs into this stub area";
              }
            }
          }
        }
        case case_2 {
          container nssa {
            presence "enable nssa";
            description
              "Configure a not-so-stubby area";
            uses apply-advanced;
            container default-lsa {
              presence "enable default-lsa";
              description
                "Configure a default LSA";
              uses apply-advanced;
              leaf default-metric {
                type union {
                  type string {
                    pattern "<.*>|$.*";
                  }
                  type uint32 {
                    range "1 .. 16777215";
                  }
                }
                description
                  "Metric for the default route in this area";
              }
              leaf metric-type {
                type union {
                  type string {
                    pattern "<.*>|$.*";
                  }
                  type uint32 {
                    range "1 .. 2";
                  }
                }
                description
                  "External metric type for the default type 7 LSA";
              }
              leaf type-7 {
                type empty;
                description
                  "Flood type 7 default LSA if no-summaries is configured";
              }
            }
            leaf default-metric {
              type union {
                type string {
                  pattern "<.*>|$.*";
                }
                type uint32 {
                  range "1 .. 16777215";
                }
              }
              status deprecated;
              description
                "Metric for the default route in this area";
            }
            leaf metric-type {
              type union {
                type string {
                  pattern "<.*>|$.*";
                }
                type uint32 {
                  range "1 .. 2";
                }
              }
              status deprecated;
              description
                "External metric type for the default type 7 LSA";
            }
            choice summaries-choice {
              leaf summaries {
                type empty;
                description
                  "Flood summary LSAs into this NSSA area";
              }
              leaf no-summaries {
                type empty;
                description
                  "Don't flood summary LSAs into this NSSA area";
              }
            }
            list area-range {
              key "name";
              ordered-by user;
              description
                "Configure NSSA area ranges";
              leaf name {
                type jt:ipprefix;
                description
                  "Range to summarize NSSA routes in this area";
              }
              uses apply-advanced;
              leaf restrict {
                type empty;
                description
                  "Restrict advertisement of this area range";
              }
              leaf exact {
                type empty;
                description
                  "Enforce exact match for advertisement of this area range";
              }
              container override-metric {
                presence "enable override-metric";
                description
                  "Override the dynamic metric for this area-range";
                uses apply-advanced;
                leaf metric {
                  type union {
                    type string {
                      pattern "<.*>|$.*";
                    }
                    type uint32 {
                      range "1 .. 16777215";
                    }
                  }
                  mandatory true;
                  description
                    "Metric value";
                }
                leaf metric-type {
                  type union {
                    type string {
                      pattern "<.*>|$.*";
                    }
                    type uint32 {
                      range "1 .. 2";
                    }
                  }
                  default "1";
                  description
                    "Set the metric type for the override metric";
                }
              }
            }
          }
        }
      }
      list area-range {
        key "name";
        ordered-by user;
        description
          "Configure area ranges";
        leaf name {
          type jt:ipprefix;
          description
            "Range to summarize routes in this area";
        }
        uses apply-advanced;
        leaf restrict {
          type empty;
          description
            "Restrict advertisement of this area range";
        }
        leaf exact {
          type empty;
          description
            "Enforce exact match for advertisement of this area range";
        }
        leaf override-metric {
          type union {
            type string {
              pattern "<.*>|$.*";
            }
            type uint32 {
              range "1 .. 16777215";
            }
          }
          description
            "Override the dynamic metric for this area-range";
        }
      }
      leaf-list network-summary-export {
        type jt:policy-algebra;
        ordered-by user;
        description
          "Export policy for Type 3 Summary LSAs";
      }
      leaf-list network-summary-import {
        type jt:policy-algebra;
        ordered-by user;
        description
          "Import policy for Type 3 Summary LSAs";
      }
      leaf-list inter-area-prefix-export {
        type jt:policy-algebra;
        ordered-by user;
        description
          "Export policy for Inter Area Prefix LSAs";
      }
      leaf-list inter-area-prefix-import {
        type jt:policy-algebra;
        ordered-by user;
        description
          "Import policy for Inter Area Prefix LSAs";
      }
      leaf authentication-type {
        type enumeration {
          enum "none" {
            status deprecated;
            description
              "No authentication";
          }
          enum "simple" {
            status deprecated;
            description
              "Simple password authentication";
          }
          enum "md5" {
            status deprecated;
            description
              "MD5 authentication";
          }
        }
        status deprecated;
        description
          "Authentication type";
      }
      list virtual-link {
        key "neighbor-id transit-area";
        ordered-by user;
        description
          "Configure virtual links";
        leaf neighbor-id {
          type jt:ipv4addr;
          description
            "Router ID of a virtual neighbor";
        }
        leaf transit-area {
          type jt:areaid;
          description
            "Transit area in common with virtual neighbor";
        }
        uses apply-advanced;
        choice enable-disable {
          case case_1 {
            leaf disable {
              type empty;
              description
                "Disable this virtual link";
            }
          }
        }
        leaf retransmit-interval {
          type union {
            type string {
              pattern "<.*>|$.*";
            }
            type uint32 {
              range "1 .. 65535";
            }
          }
          description
            "Retransmission interval (seconds)";
        }
        leaf transit-delay {
          type union {
            type string {
              pattern "<.*>|$.*";
            }
            type uint32 {
              range "1 .. 65535";
            }
          }
          description
            "Transit delay (seconds)";
        }
        leaf hello-interval {
          type union {
            type string {
              pattern "<.*>|$.*";
            }
            type uint32 {
              range "1 .. 255";
            }
          }
          description
            "Hello interval (seconds)";
        }
        leaf dead-interval {
          type union {
            type string {
              pattern "<.*>|$.*";
            }
            type uint32 {
              range "1 .. 65535";
            }
          }
          description
            "Dead interval (seconds)";
        }
        leaf mtu {
          type union {
            type string {
              pattern "<.*>|$.*";
            }
            type uint32 {
              range "128 .. 65535";
            }
          }
          description
            "Maximum OSPF packet size";
        }
        choice auth {
          case case_1 {
            container authentication {
              uses juniper-ospf-authentication;
            }
          }
          case case_2 {
            container authentication-key {
              status deprecated;
              description
                "Authentication key";
              leaf keyname {
                type jt:unreadable;
                mandatory true;
                description
                  "Authentication key value";
              }
              leaf key-id {
                type union {
                  type string {
                    pattern "<.*>|$.*";
                  }
                  type uint32 {
                    range "0 .. 255";
                  }
                }
                description
                  "Key ID for MD5 authentication";
              }
            }
          }
        }
        leaf demand-circuit {
          type empty;
          description
            "Interface functions as a demand circuit";
        }
        leaf flood-reduction {
          type empty;
          description
            "Enable flood reduction";
        }
        leaf no-neighbor-down-notification {
          type empty;
          description
            "Don't inform other protocols about neighbor down events";
        }
        leaf ipsec-sa {
          type string {
            length "1 .. 32";
          }
          description
            "IPSec security association name";
        }
        list topology {
          key "name";
          ordered-by user;
          description
            "Topology specific attributes";
          leaf name {
            type string;
            description
              "Topology name";
          }
          uses apply-advanced;
          leaf disable {
            type empty;
            description
              "Disable this topology";
          }
          leaf metric {
            type union {
              type string {
                pattern "<.*>|$.*";
              }
              type uint16 {
                range "1 .. 65535";
              }
            }
            description
              "Topology metric";
          }
          container bandwidth-based-metrics {
            description
              "Configure bandwidth based metrics";
            uses apply-advanced;
            list bandwidth {
              key "name";
              description
                "Bandwidth threshold";
              leaf name {
                type string;
              }
              leaf metric {
                type union {
                  type string {
                    pattern "<.*>|$.*";
                  }
                  type uint16 {
                    range "1 .. 65535";
                  }
                }
                mandatory true;
                description
                  "Metric associated with specified bandwidth";
              }
            }
          }
        }
      }
      list sham-link-remote {
        key "name";
        ordered-by user;
        description
          "Configure parameters for remote sham link endpoint";
        leaf name {
          type jt:ipaddr;
          description
            "Remote sham link endpoint address";
        }
        uses apply-advanced;
        leaf metric {
          type union {
            type string {
              pattern "<.*>|$.*";
            }
            type uint16 {
              range "1 .. 65535";
            }
          }
          description
            "Sham link metric";
        }
        leaf ipsec-sa {
          type string {
            length "1 .. 32";
          }
          description
            "IPSec security association name";
        }
        leaf demand-circuit {
          type empty;
          description
            "Interface functions as a demand circuit";
        }
        leaf flood-reduction {
          type empty;
          description
            "Enable flood reduction";
        }
        list topology {
          key "name";
          ordered-by user;
          description
            "Topology specific attributes";
          leaf name {
            type string;
            description
              "Topology name";
          }
          uses apply-advanced;
          leaf disable {
            type empty;
            description
              "Disable this topology";
          }
          leaf metric {
            type union {
              type string {
                pattern "<.*>|$.*";
              }
              type uint16 {
                range "1 .. 65535";
              }
            }
            description
              "Topology metric";
          }
          container bandwidth-based-metrics {
            description
              "Configure bandwidth based metrics";
            uses apply-advanced;
            list bandwidth {
              key "name";
              description
                "Bandwidth threshold";
              leaf name {
                type string;
              }
              leaf metric {
                type union {
                  type string {
                    pattern "<.*>|$.*";
                  }
                  type uint16 {
                    range "1 .. 65535";
                  }
                }
                mandatory true;
                description
                  "Metric associated with specified bandwidth";
              }
            }
          }
        }
        leaf keychain {
          type string {
            length "1 .. 128";
          }
          description
            "Key chain name";
        }
      }
      list interface {
        key "name";
        ordered-by user;
        description
          "Include an interface in this area";
        leaf name {
          type union {
            type jt:ipv4addr-or-interface;
            type string {
              pattern "<.*>|$.*";
            }
          }
          description
            "Interface name";
        }
        uses apply-advanced;
        choice enable-disable {
          case case_1 {
            leaf disable {
              type empty;
              description
                "Disable OSPF on this interface";
            }
          }
        }
        leaf interface-type {
          type enumeration {
            enum "nbma" {
              description
                "Nonbroadcast multiaccess";
            }
            enum "p2mp" {
              description
                "Point-to-multipoint NBMA";
            }
            enum "p2p" {
              description
                "Point-to-point";
            }
            enum "p2mp-over-lan" {
              description
                "Point-to-multipoint over LAN mode";
            }
          }
          description
            "Type of interface";
        }
        container passive {
          presence "enable passive";
          description
            "Do not run OSPF, but advertise it";
          uses apply-advanced;
          container traffic-engineering {
            description
              "Advertise TE link information";
            uses apply-advanced;
            leaf remote-node-id {
              type jt:ipaddr;
              description
                "Remote address of the link";
            }
            leaf remote-node-router-id {
              type jt:ipv4addr;
              description
                "TE Router-ID of the remote node";
            }
          }
        }
        leaf secondary {
          type empty;
          description
            "Treat interface as secondary";
        }
        leaf own-router-lsa {
          type empty;
          description
            "Generate a separate router LSA for this interface";
        }
        container bandwidth-based-metrics {
          description
            "Configure bandwidth based metrics";
          uses apply-advanced;
          list bandwidth {
            key "name";
            description
              "Bandwidth threshold";
            leaf name {
              type string;
            }
            leaf metric {
              type union {
                type string {
                  pattern "<.*>|$.*";
                }
                type uint16 {
                  range "1 .. 65535";
                }
              }
              mandatory true;
              description
                "Metric associated with specified bandwidth";
            }
          }
        }
        leaf metric {
          type union {
            type string {
              pattern "<.*>|$.*";
            }
            type uint16 {
              range "1 .. 65535";
            }
          }
          description
            "Interface metric";
        }
        leaf priority {
          type union {
            type string {
              pattern "<.*>|$.*";
            }
            type uint32 {
              range "0 .. 255";
            }
          }
          description
            "Designated router priority";
        }
        leaf retransmit-interval {
          type union {
            type string {
              pattern "<.*>|$.*";
            }
            type uint32 {
              range "1 .. 65535";
            }
          }
          description
            "Retransmission interval (seconds)";
        }
        leaf transit-delay {
          type union {
            type string {
              pattern "<.*>|$.*";
            }
            type uint32 {
              range "1 .. 65535";
            }
          }
          description
            "Transit delay (seconds)";
        }
        leaf hello-interval {
          type union {
            type string {
              pattern "<.*>|$.*";
            }
            type uint32 {
              range "1 .. 255";
            }
          }
          description
            "Hello interval (seconds)";
        }
        leaf dead-interval {
          type union {
            type string {
              pattern "<.*>|$.*";
            }
            type uint32 {
              range "1 .. 65535";
            }
          }
          description
            "Dead interval (seconds)";
        }
        leaf mtu {
          type union {
            type string {
              pattern "<.*>|$.*";
            }
            type uint32 {
              range "128 .. 65535";
            }
          }
          description
            "Maximum OSPF packet size";
        }
        choice auth {
          case case_1 {
            container authentication {
              uses juniper-ospf-authentication;
            }
          }
          case case_2 {
            container authentication-key {
              status deprecated;
              description
                "Authentication key";
              leaf keyname {
                type jt:unreadable;
                mandatory true;
                description
                  "Authentication key value";
              }
              leaf key-id {
                type union {
                  type string {
                    pattern "<.*>|$.*";
                  }
                  type uint32 {
                    range "0 .. 255";
                  }
                }
                description
                  "Key ID for MD5 authentication";
              }
            }
          }
        }
        leaf demand-circuit {
          type empty;
          description
            "Interface functions as a demand circuit";
        }
        leaf flood-reduction {
          type empty;
          description
            "Enable flood reduction";
        }
        leaf no-neighbor-down-notification {
          type empty;
          description
            "Don't inform other protocols about neighbor down events";
        }
        list topology {
          key "name";
          ordered-by user;
          description
            "Topology specific attributes";
          leaf name {
            type string;
            description
              "Topology name";
          }
          uses apply-advanced;
          leaf disable {
            type empty;
            description
              "Disable this topology";
          }
          leaf metric {
            type union {
              type string {
                pattern "<.*>|$.*";
              }
              type uint16 {
                range "1 .. 65535";
              }
            }
            description
              "Topology metric";
          }
          container bandwidth-based-metrics {
            description
              "Configure bandwidth based metrics";
            uses apply-advanced;
            list bandwidth {
              key "name";
              description
                "Bandwidth threshold";
              leaf name {
                type string;
              }
              leaf metric {
                type union {
                  type string {
                    pattern "<.*>|$.*";
                  }
                  type uint16 {
                    range "1 .. 65535";
                  }
                }
                mandatory true;
                description
                  "Metric associated with specified bandwidth";
              }
            }
          }
        }
        leaf transmit-interval {
          type union {
            type string {
              pattern "<.*>|$.*";
            }
            type uint32 {
              range "1 .. 4294967295";
            }
          }
          status deprecated;
          description
            "OSPF packet transmit interval (milliseconds)";
        }
        container bfd-liveness-detection {
          description
            "Bidirectional Forwarding Detection options";
          uses apply-advanced;
          leaf version {
            type enumeration {
              enum "0" {
                description
                  "BFD version 0 (deprecated)";
              }
              enum "1" {
                description
                  "BFD version 1";
              }
              enum "automatic" {
                description
                  "Choose BFD version automatically";
              }
            }
            default "automatic";
            description
              "BFD protocol version number";
          }
          leaf minimum-interval {
            type union {
              type string {
                pattern "<.*>|$.*";
              }
              type uint32 {
                range "1 .. 255000";
              }
            }
            units "milliseconds";
            description
              "Minimum transmit and receive interval";
          }
          leaf minimum-transmit-interval {
            type union {
              type string {
                pattern "<.*>|$.*";
              }
              type uint32 {
                range "1 .. 255000";
              }
            }
            units "milliseconds";
            status deprecated;
            description
              "Minimum transmit interval";
          }
          leaf minimum-receive-interval {
            type union {
              type string {
                pattern "<.*>|$.*";
              }
              type uint32 {
                range "1 .. 255000";
              }
            }
            units "milliseconds";
            description
              "Minimum receive interval";
          }
          leaf multiplier {
            type union {
              type string {
                pattern "<.*>|$.*";
              }
              type uint32 {
                range "1 .. 255";
              }
            }
            default "3";
            description
              "Detection time multiplier";
          }
          leaf inline-disable {
            type empty;
            description
              "Disable inline mode for this BFD session";
          }
          leaf pdu-size {
            type union {
              type string {
                pattern "<.*>|$.*";
              }
              type uint32 {
                range "24 .. 16000";
              }
            }
            default "24";
            description
              "BFD transport protocol payload size";
          }
          choice adaptation-choice {
            case case_1 {
              leaf no-adaptation {
                type empty;
                description
                  "Disable adaptation";
              }
            }
          }
          container transmit-interval {
            description
              "Transmit-interval options";
            uses apply-advanced;
            leaf minimum-interval {
              type union {
                type string {
                  pattern "<.*>|$.*";
                }
                type uint32 {
                  range "1 .. 255000";
                }
              }
              units "milliseconds";
              description
                "Minimum transmit interval";
            }
            leaf threshold {
              type union {
                type uint32;
                type string {
                  pattern "<.*>|$.*";
                }
              }
              units "milliseconds";
              description
                "High transmit interval triggering a trap";
            }
          }
          container detection-time {
            description
              "Detection-time options";
            uses apply-advanced;
            leaf threshold {
              type union {
                type uint32;
                type string {
                  pattern "<.*>|$.*";
                }
              }
              units "milliseconds";
              description
                "High detection-time triggering a trap";
            }
          }
          container authentication {
            description
              "Authentication options";
            uses apply-advanced;
            leaf key-chain {
              type string;
              description
                "Key chain name";
            }
            leaf algorithm {
              type enumeration {
                enum "simple-password" {
                  description
                    "Simple password";
                }
                enum "keyed-md5" {
                  description
                    "Keyed message Digest 5";
                }
                enum "meticulous-keyed-md5" {
                  description
                    "Meticulous keyed message Digest 5";
                }
                enum "keyed-sha-1" {
                  description
                    "Keyed secure hash algorithm (SHA1) ";
                }
                enum "meticulous-keyed-sha-1" {
                  description
                    "Meticulous keyed secure hash algorithm (SHA1) ";
                }
              }
              description
                "Algorithm name";
            }
            leaf loose-check {
              type empty;
              description
                "Verify authentication only if authentication is negotiated";
            }
          }
          container echo {
            description
              "Echo mode parameters";
            uses apply-advanced;
            leaf minimum-interval {
              type union {
                type string {
                  pattern "<.*>|$.*";
                }
                type uint32 {
                  range "100 .. 255000";
                }
              }
              units "milliseconds";
              description
                "Minimum transmit and receive interval";
            }
          }
          container echo-lite {
            description
              "Echo-lite more parameters";
            uses apply-advanced;
            leaf minimum-interval {
              type union {
                type string {
                  pattern "<.*>|$.*";
                }
                type uint32 {
                  range "100 .. 255000";
                }
              }
              units "milliseconds";
              description
                "Minimum transmit and receive interval";
            }
          }
          leaf full-neighbors-only {
            type empty;
            description
              "Setup BFD sessions only to Full neighbors";
          }
          leaf holddown-interval {
            type union {
              type string {
                pattern "<.*>|$.*";
              }
              type uint32 {
                range "0 .. 255000";
              }
            }
            units "milliseconds";
            description
              "Time to hold the session-UP notification to the client";
          }
        }
        leaf dynamic-neighbors {
          type empty;
          description
            "Learn neighbors dynamically on a p2mp interface";
        }
        leaf no-advertise-adjacency-segment {
          type empty;
          description
            "Do not advertise an adjacency segment for this interface";
        }
        list neighbor {
          key "name";
          ordered-by user;
          description
            "NBMA neighbor";
          leaf name {
            type jt:ipaddr;
            description
              "Address of neighbor";
          }
          leaf eligible {
            type empty;
            description
              "Eligible to be DR on an NBMA network";
          }
        }
        leaf poll-interval {
          type union {
            type string {
              pattern "<.*>|$.*";
            }
            type uint32 {
              range "1 .. 65535";
            }
          }
          description
            "Poll interval for NBMA interfaces";
        }
        leaf no-interface-state-traps {
          type empty;
          description
            "Do not send interface state change traps";
        }
        leaf strict-bfd {
          type empty;
          description
            "Enable strict bfd over this interface";
        }
        container post-convergence-lfa {
          presence "enable post-convergence-lfa";
          description
            "Protect interface using post-convergence backup path";
          uses apply-advanced;
        }
        leaf te-metric {
          type union {
            type string {
              pattern "<.*>|$.*";
            }
            type uint32 {
              range "1 .. 4294967295";
            }
          }
          description
            "Traffic engineering metric";
        }
        container ldp-synchronization {
          presence "enable ldp-synchronization";
          description
            "Advertise maximum metric until LDP is operational";
          uses ldp-sync-obj;
        }
        container ipv4-adjacency-segment {
          description
            "Configure ipv4 adjacency segment";
          uses apply-advanced;
          container unprotected {
            description
              "Adjacency SID uneligible for protection";
            choice adjsid-type {
              case case_1 {
                container index {
                  description
                    "Adjacency SID indexed from SRGB";
                  leaf index-number {
                    type union {
                      type string {
                        pattern "<.*>|$.*";
                      }
                      type uint32 {
                        range "0 .. 199999";
                      }
                    }
                  }
                }
              }
              case case_2 {
                leaf label {
                  type union {
                    type string {
                      pattern "<.*>|$.*";
                    }
                    type uint32 {
                      range "16 .. 1048575";
                    }
                  }
                  description
                    "Adjacency SID from static label pool";
                }
              }
              case case_3 {
                leaf dynamic {
                  type empty;
                  description
                    "Dynamically allocate an adjacency segment";
                }
              }
            }
          }
        }
        list lan-neighbor {
          key "name";
          ordered-by user;
          description
            "Configuration specific to a LAN neighbor";
          leaf name {
            type jt:ipaddr;
            description
              "Address of neighbor";
          }
          uses apply-advanced;
          container ipv4-adjacency-segment {
            description
              "Configure ipv4 adjacency segment";
            uses apply-advanced;
            container protected {
              description
                "Adjacency SID is eligible for protection";
              choice adjsid-type {
                case case_1 {
                  container index {
                    description
                      "Adjacency SID indexed from SRGB";
                    leaf index-number {
                      type union {
                        type string {
                          pattern "<.*>|$.*";
                        }
                        type uint32 {
                          range "0 .. 199999";
                        }
                      }
                    }
                  }
                }
                case case_2 {
                  leaf label {
                    type union {
                      type string {
                        pattern "<.*>|$.*";
                      }
                      type uint32 {
                        range "16 .. 1048575";
                      }
                    }
                    description
                      "Adjacency SID from static label pool";
                  }
                }
                case case_3 {
                  leaf dynamic {
                    type empty;
                    description
                      "Dynamically allocate an adjacency segment";
                  }
                }
              }
            }
            container unprotected {
              description
                "Adjacency SID uneligible for protection";
              choice adjsid-type {
                case case_1 {
                  container index {
                    description
                      "Adjacency SID indexed from SRGB";
                    leaf index-number {
                      type union {
                        type string {
                          pattern "<.*>|$.*";
                        }
                        type uint32 {
                          range "0 .. 199999";
                        }
                      }
                    }
                  }
                }
                case case_2 {
                  leaf label {
                    type union {
                      type string {
                        pattern "<.*>|$.*";
                      }
                      type uint32 {
                        range "16 .. 1048575";
                      }
                    }
                    description
                      "Adjacency SID from static label pool";
                  }
                }
                case case_3 {
                  leaf dynamic {
                    type empty;
                    description
                      "Dynamically allocate an adjacency segment";
                  }
                }
              }
            }
          }
        }
        leaf delay-metric {
          type union {
            type string {
              pattern "<.*>|$.*";
            }
            type uint32 {
              range "0 .. 16777215";
            }
          }
          units "microseconds";
          description
            "Delay metric";
        }
        container delay-measurement {
          presence "enable delay-measurement";
          description
            "Enable delay measurement";
          uses apply-advanced;
          leaf probe-interval {
            type union {
              type string {
                pattern "<.*>|$.*";
              }
              type uint32 {
                range "1 .. 255";
              }
            }
            units "seconds";
            description
              "Probe interval";
          }
          leaf probe-count {
            type union {
              type string {
                pattern "<.*>|$.*";
              }
              type uint32 {
                range "1 .. 15";
              }
            }
            description
              "Probe count";
          }
          container advertisement {
            description
              "Delay advertisement";
            uses apply-advanced;
            container periodic {
              description
                "Periodic advertisement parameters";
              uses apply-advanced;
              leaf threshold {
                type union {
                  type string {
                    pattern "<.*>|$.*";
                  }
                  type uint32 {
                    range "0 .. 100";
                  }
                }
                units "percentage";
                description
                  "Threshold";
              }
              leaf interval {
                type union {
                  type string {
                    pattern "<.*>|$.*";
                  }
                  type uint32 {
                    range "30 .. 3600";
                  }
                }
                units "seconds";
                description
                  "Interval";
              }
            }
            container accelerated {
              presence "enable accelerated";
              description
                "Accelerated advertisement parameters";
              uses apply-advanced;
              leaf threshold {
                type union {
                  type string {
                    pattern "<.*>|$.*";
                  }
                  type uint32 {
                    range "0 .. 100";
                  }
                }
                units "percentage";
                description
                  "Threshold";
              }
            }
          }
        }
        container application-specific {
          description
            "Advertise application-specific TE attributes";
          uses apply-advanced;
          list attribute-group {
            key "name";
            max-elements 1;
            ordered-by user;
            description
              "Link attribute group name";
            leaf name {
              type string;
              description
                "Link attribute group name";
            }
            uses apply-advanced;
            leaf te-metric {
              type union {
                type string {
                  pattern "<.*>|$.*";
                }
                type uint32 {
                  range "1 .. 4294967295";
                }
              }
              description
                "Traffic engineering metric for this attribute group";
            }
            leaf-list admin-group {
              type string;
              max-elements 16;
              ordered-by user;
              description
                "Administrative groups for this attribute-group";
            }
            leaf delay-metric {
              type union {
                type string {
                  pattern "<.*>|$.*";
                }
                type uint32 {
                  range "0 .. 16777215";
                }
              }
              units "microseconds";
              description
                "Delay metric for this attribute-group";
            }
            leaf advertise-interface-delay {
              type empty;
              description
                "Use interface specific static/dynamic delay values as applicable in ASLA Sub-TLVs";
            }
            container application {
              description
                "Standard Applications part of this attribute-group";
              uses apply-advanced;
              leaf flex-algorithm {
                type empty;
                description
                  "Set X flag in standard application bit mask";
              }
            }
          }
        }
      }
      leaf no-source-packet-routing {
        type empty;
        description
          "Disable SPRING in this area";
      }
    }
    choice enable-disable {
      case case_1 {
        leaf disable {
          type empty;
          description
            "Disable OSPF";
        }
      }
    }
    container traceoptions {
      description
        "Trace options for OSPF";
      uses apply-advanced;
      container file {
        description
          "Trace file options";
        leaf filename {
          type string {
            length "1 .. 1024";
          }
          description
            "Name of file in which to write trace information";
        }
        leaf replace {
          type empty;
          status deprecated;
          description
            "Replace trace file rather than appending to it";
        }
        leaf size {
          type string;
          description
            "Maximum trace file size";
        }
        leaf files {
          type union {
            type string {
              pattern "<.*>|$.*";
            }
            type uint32 {
              range "2 .. 1000";
            }
          }
          default "10";
          description
            "Maximum number of trace files";
        }
        leaf no-stamp {
          type empty;
          status deprecated;
          description
            "Do not timestamp trace file";
        }
        choice world-readable-choice {
          leaf world-readable {
            type empty;
            description
              "Allow any user to read the log file";
          }
          leaf no-world-readable {
            type empty;
            description
              "Don't allow any user to read the log file";
          }
        }
      }
      list flag {
        key "name";
        ordered-by user;
        description
          "Tracing parameters";
        leaf name {
          type enumeration {
            enum "spf" {
              description
                "Trace SPF calculations";
            }
            enum "error" {
              description
                "Trace errored packets";
            }
            enum "event" {
              description
                "Trace OSPF state machine events";
            }
            enum "packet-dump" {
              description
                "Dump the contents of selected packet types";
            }
            enum "flooding" {
              description
                "Trace LSA flooding";
            }
            enum "lsa-analysis" {
              description
                "Trace LSA analysis";
            }
            enum "packets" {
              description
                "Trace all OSPF packets";
            }
            enum "hello" {
              description
                "Trace hello packets";
            }
            enum "database-description" {
              description
                "Trace database description packets";
            }
            enum "lsa-request" {
              description
                "Trace LSA request packets";
            }
            enum "lsa-update" {
              description
                "Trace LSA update packets";
            }
            enum "lsa-ack" {
              description
                "Trace LSA acknowledgment packets";
            }
            enum "ldp-synchronization" {
              description
                "Trace synchronization between OSPF and LDP";
            }
            enum "on-demand" {
              description
                "Trace demand circuit extensions";
            }
            enum "nsr-synchronization" {
              description
                "Trace NSR synchronization events";
            }
            enum "graceful-restart" {
              description
                "Trace graceful restart";
            }
            enum "restart-signaling" {
              description
                "Trace restart signaling";
            }
            enum "traffic-statistics" {
              description
                "Trace Segment Routing Traffic Statistics";
            }
            enum "backup-spf" {
              description
                "Trace backup SPF (LFA) specific events";
            }
            enum "source-packet-routing" {
              description
                "Trace source packet routing (SPRING) events";
            }
            enum "post-convergence-lfa" {
              description
                "Trace post-convergence-lfa related events";
            }
            enum "flex-algorithm" {
              description
                "Trace flex-algorithm related events";
            }
            enum "rmopd" {
              description
                "Trace rmopd interactions";
            }
            enum "route" {
              description
                "Trace routing information";
            }
            enum "normal" {
              description
                "Trace normal events";
            }
            enum "general" {
              description
                "Trace general events";
            }
            enum "state" {
              description
                "Trace state transitions";
            }
            enum "policy" {
              description
                "Trace policy processing";
            }
            enum "task" {
              description
                "Trace routing protocol task processing";
            }
            enum "timer" {
              description
                "Trace routing protocol timer processing";
            }
            enum "all" {
              description
                "Trace everything";
            }
          }
        }
        leaf send {
          type empty;
          description
            "Trace transmitted packets";
        }
        leaf receive {
          type empty;
          description
            "Trace received packets";
        }
        leaf detail {
          type empty;
          description
            "Trace detailed information";
        }
        leaf disable {
          type empty;
          description
            "Disable this trace flag";
        }
      }
    }
    leaf prefix-export-limit {
      type union {
        type string {
          pattern "<.*>|$.*";
        }
        type uint32 {
          range "0 .. 4294967295";
        }
      }
      description
        "Maximum number of prefixes that can be exported";
    }
    container rib-groups {
      description
        "Routing table groups for importing OSPF routes";
      uses apply-advanced;
      leaf inet {
        type string;
        description
          "Name of the IPv4/v6 routing table group";
      }
      leaf inet3 {
        type string;
        description
          "Name of the IPv4/v6 inet.3 routing table group";
      }
    }
    leaf job-stats {
      type empty;
      description
        "Collect job statistics";
    }
    container overload {
      presence "enable overload";
      description
        "Set the overload mode (repel transit traffic)";
      uses apply-advanced;
      leaf timeout {
        type union {
          type string {
            pattern "<.*>|$.*";
          }
          type uint32 {
            range "60 .. 3600";
          }
        }
        units "seconds";
        description
          "Time after which overload mode is reset";
      }
      leaf allow-route-leaking {
        type empty;
        description
          "Allow routes to be leaked when overload is configured";
      }
      leaf stub-network {
        type empty;
        description
          "Advertise Stub Network with maximum metric";
      }
      leaf intra-area-prefix {
        type empty;
        description
          "Advertise Intra Area Prefix with maximum metric";
      }
      leaf as-external {
        type empty;
        description
          "Advertise As External with maximum usable metric";
      }
    }
    container database-protection {
      presence "enable database-protection";
      description
        "Configure database protection attributes";
      uses apply-advanced;
      leaf maximum-lsa {
        type union {
          type string {
            pattern "<.*>|$.*";
          }
          type uint32 {
            range "1 .. 1000000";
          }
        }
        mandatory true;
        description
          "Maximum allowed non self-generated LSAs";
      }
      leaf warning-only {
        type empty;
        description
          "Emit only a warning when LSA maximum limit is exceeded";
      }
      leaf warning-threshold {
        type union {
          type string {
            pattern "<.*>|$.*";
          }
          type uint8 {
            range "30 .. 100";
          }
        }
        units "percent";
        description
          "Percentage of LSA maximum above which to trigger warning";
      }
      leaf ignore-count {
        type union {
          type string {
            pattern "<.*>|$.*";
          }
          type uint8 {
            range "1 .. 32";
          }
        }
        description
          "Maximum number of times to go into ignore state";
      }
      leaf ignore-time {
        type union {
          type string {
            pattern "<.*>|$.*";
          }
          type uint16 {
            range "30 .. 3600";
          }
        }
        units "seconds";
        description
          "Time to stay in ignore state and ignore all neighbors";
      }
      leaf reset-time {
        type union {
          type string {
            pattern "<.*>|$.*";
          }
          type uint32 {
            range "60 .. 86400";
          }
        }
        units "seconds";
        description
          "Time after which the ignore count gets reset to zero";
      }
    }
    container graceful-restart {
      description
        "Configure graceful restart attributes";
      uses apply-advanced;
      choice enable-disable {
        case case_1 {
          leaf disable {
            type empty;
            description
              "Disable OSPF graceful restart capability";
          }
        }
      }
      leaf restart-duration {
        type union {
          type string {
            pattern "<.*>|$.*";
          }
          type uint32 {
            range "1 .. 3600";
          }
        }
        units "seconds";
        description
          "Time for all neighbors to become full";
      }
      leaf notify-duration {
        type union {
          type string {
            pattern "<.*>|$.*";
          }
          type uint32 {
            range "1 .. 3600";
          }
        }
        units "seconds";
        description
          "Time to send all max-aged grace LSAs";
      }
      container helper-disable {
        presence "enable helper-disable";
        description
          "Disable graceful restart helper capability";
        uses apply-advanced;
        choice disable-choices {
          case case_1 {
            leaf standard {
              type empty;
              description
                "Disable helper-mode for rfc3623 based GR";
            }
          }
          case case_2 {
            leaf restart-signaling {
              type empty;
              description
                "Disable helper mode for restart-signaling ";
            }
          }
          case case_3 {
            leaf both {
              type empty;
              description
                "Disable helper mode for both the types of GR";
            }
          }
        }
      }
      leaf no-strict-lsa-checking {
        type empty;
        description
          "Do not abort graceful helper mode upon LSA changes";
      }
    }
    leaf route-type-community {
      type enumeration {
        enum "iana" {
          description
            "BGP extended community value used is 0x0306";
        }
        enum "vendor" {
          description
            "Vendor BGP extended community value used is 0x8000";
        }
      }
      description
        "Specify BGP extended community value to encode OSPF route type";
    }
    container domain-id {
      description
        "Configure domain ID";
      choice domain_id_or_disable {
        case case_1 {
          leaf domain-id {
            type string;
            description
              "Domain ID";
          }
        }
        case case_2 {
          leaf disable {
            type empty;
            description
              "Disable domain ID";
          }
        }
      }
    }
    choice domain_vpn_tag_or_disable {
      case case_1 {
        leaf domain-vpn-tag {
          type union {
            type string {
              pattern "<.*>|$.*";
            }
            type uint32 {
              range "0 .. 4294967295";
            }
          }
          description
            "Domain VPN tag for external LSA";
        }
      }
      case case_2 {
        leaf no-domain-vpn-tag {
          type empty;
          description
            "Disable domain VPN tag";
        }
      }
    }
    leaf preference {
      type union {
        type uint32;
        type string {
          pattern "<.*>|$.*";
        }
      }
      description
        "Preference of internal routes";
    }
    leaf external-preference {
      type union {
        type uint32;
        type string {
          pattern "<.*>|$.*";
        }
      }
      description
        "Preference of external routes";
    }
    leaf labeled-preference {
      type union {
        type uint32;
        type string {
          pattern "<.*>|$.*";
        }
      }
      description
        "Preference of labeled routes";
    }
    leaf-list export {
      type jt:policy-algebra;
      ordered-by user;
      description
        "Export policy";
    }
    leaf-list import {
      type jt:policy-algebra;
      ordered-by user;
      description
        "Import policy (for external routes or setting priority)";
    }
    leaf reference-bandwidth {
      type string;
      description
        "Bandwidth for calculating metric defaults";
    }
    leaf lsa-refresh-interval {
      type union {
        type string {
          pattern "<.*>|$.*";
        }
        type uint32 {
          range "25 .. 50";
        }
      }
      default "50";
      description
        "LSA refresh interval (minutes)";
    }
    leaf spf-delay {
      type union {
        type string {
          pattern "<.*>|$.*";
        }
        type uint32 {
          range "50 .. 8000";
        }
      }
      units "milliseconds";
      status deprecated;
      description
        "Time to wait before running an SPF";
    }
    leaf no-rfc-1583 {
      type empty;
      description
        "Disable RFC1583 compatibility";
    }
    leaf forwarding-address-to-broadcast {
      type empty;
      description
        "Set forwarding address in Type 5 LSA in broadcast network";
    }
    choice nssa-abr-option {
      case case_1 {
        leaf no-nssa-abr {
          type empty;
          description
            "Disable full NSSA functionality at ABR";
        }
      }
    }
    container sham-link {
      presence "enable sham-link";
      description
        "Configure parameters for sham links";
      uses apply-advanced;
      leaf local {
        type jt:ipaddr;
        description
          "Local sham link endpoint address";
      }
      leaf no-advertise-local {
        type empty;
        status deprecated;
        description
          "Don't advertise local sham link endpoint as stub in router LSA";
      }
    }
  }

  grouping juniper-protocols-router-discovery {
    uses apply-advanced;
    choice enable-disable {
      case case_1 {
        leaf disable {
          type empty;
          description
            "Disable router discovery";
        }
      }
    }
    container traceoptions {
      description
        "Trace options for router discovery";
      uses apply-advanced;
      container file {
        description
          "Trace file options";
        leaf filename {
          type string {
            length "1 .. 1024";
          }
          description
            "Name of file in which to write trace information";
        }
        leaf replace {
          type empty;
          status deprecated;
          description
            "Replace trace file rather than appending to it";
        }
        leaf size {
          type string;
          description
            "Maximum trace file size";
        }
        leaf files {
          type union {
            type string {
              pattern "<.*>|$.*";
            }
            type uint32 {
              range "2 .. 1000";
            }
          }
          default "10";
          description
            "Maximum number of trace files";
        }
        leaf no-stamp {
          type empty;
          status deprecated;
          description
            "Do not timestamp trace file";
        }
        choice world-readable-choice {
          leaf world-readable {
            type empty;
            description
              "Allow any user to read the log file";
          }
          leaf no-world-readable {
            type empty;
            description
              "Don't allow any user to read the log file";
          }
        }
      }
      list flag {
        key "name";
        ordered-by user;
        description
          "Tracing parameters";
        leaf name {
          type enumeration {
            enum "route" {
              description
                "Trace routing information";
            }
            enum "normal" {
              description
                "Trace normal events";
            }
            enum "general" {
              description
                "Trace general events";
            }
            enum "state" {
              description
                "Trace state transitions";
            }
            enum "policy" {
              description
                "Trace policy processing";
            }
            enum "task" {
              description
                "Trace routing protocol task processing";
            }
            enum "timer" {
              description
                "Trace routing protocol timer processing";
            }
            enum "all" {
              description
                "Trace everything";
            }
          }
        }
      }
    }
    list interface {
      key "name";
      ordered-by user;
      description
        "Interfaces on which to configure router discovery";
      leaf name {
        type union {
          type jt:interface-name;
          type string {
            pattern "<.*>|$.*";
          }
        }
        description
          "Interface name";
      }
      uses apply-advanced;
      leaf max-advertisement-interval {
        type union {
          type string {
            pattern "<.*>|$.*";
          }
          type uint32 {
            range "4 .. 1800";
          }
        }
        units "seconds";
        description
          "Maximum time before sending advertisements";
      }
      leaf min-advertisement-interval {
        type union {
          type string {
            pattern "<.*>|$.*";
          }
          type uint32 {
            range "3 .. 1800";
          }
        }
        units "seconds";
        description
          "Minimum time before sending advertisements";
      }
      leaf lifetime {
        type union {
          type string {
            pattern "<.*>|$.*";
          }
          type uint32 {
            range "3 .. 9000";
          }
        }
        units "seconds";
        description
          "How long addresses in advertisements are valid";
      }
    }
    list address {
      key "name";
      ordered-by user;
      description
        "IP addresses to include in advertisements";
      leaf name {
        type jt:ipv4addr;
        description
          "IP addresses to include in router advertisements";
      }
      uses apply-advanced;
      leaf advertise {
        type empty;
        description
          "Advertise the IP address in advertisements";
      }
      leaf ignore {
        type empty;
        description
          "Do not advertise the IP address in advertisements";
      }
      leaf broadcast {
        type empty;
        description
          "Include IP address only in broadcast advertisements";
      }
      leaf multicast {
        type empty;
        description
          "Include IP address only in multicast advertisements";
      }
      leaf ineligible {
        type empty;
        description
          "IP address can never become a default router";
      }
      leaf priority {
        type union {
          type int32;
          type string {
            pattern "<.*>|$.*";
          }
        }
        description
          "Preference of the address to become a default router";
      }
    }
  }

  grouping juniper-routing-instance {
    description
      "Routing instance";
    leaf name {
      type string;
      description
        "Routing instance name";
    }
    uses apply-advanced;
    leaf instance-type {
      type enumeration {
        enum "mac-vrf" {
          description
            "MAC-VRF routing instance";
        }
        enum "virtual-switch" {
          description
            "Virtual switch routing instance";
        }
        enum "forwarding" {
          description
            "Forwarding instance";
        }
        enum "no-forwarding" {
          description
            "Nonforwarding instance";
        }
        enum "l2vpn" {
          description
            "Layer 2 VPN routing instance";
        }
        enum "vpls" {
          description
            "VPLS routing instance";
        }
        enum "virtual-router" {
          description
            "Virtual routing instance";
        }
        enum "l2backhaul-vpn" {
          description
            "L2Backhaul/L2Wholesale routing instance";
        }
        enum "mpls-internet-multicast" {
          description
            "Internet Multicast over MPLS routing instance";
        }
        enum "evpn" {
          description
            "EVPN routing instance";
        }
        enum "mpls-forwarding" {
          description
            "Routing instance provides a MPLS forwarding-context";
        }
        enum "evpn-vpws" {
          description
            "EVPN VPWS routing instance";
        }
        enum "vrf" {
          description
            "Virtual routing forwarding instance";
        }
      }
      description
        "Type of routing instance";
    }
    container routing-options {
      description
        "Protocol-independent routing option configuration";
      uses juniper-routing-options;
    }
    container protocols {
      description
        "Routing protocol configuration";
      uses apply-advanced;
      container bfd {
        presence "enable bfd";
        uses juniper-ri-protocols-bfd;
      }
      container bgp {
        description
          "BGP options";
        uses juniper-protocols-bgp;
      }
      container evpn {
        presence "enable evpn";
        description
          "EVPN configuration";
        uses juniper-protocols-l2vpn;
      }
      container router-discovery {
        description
          "ICMP router discovery options";
        uses juniper-protocols-router-discovery;
      }
      container isis {
        description
          "IS-IS configuration";
        uses juniper-protocols-isis;
      }
      container ldp {
        description
          "LDP configuration";
        uses juniper-protocols-ldp;
      }
      container mpls {
        description
          "MPLS configuration";
        uses juniper-protocols-mpls;
      }
      container ospf {
        description
          "OSPF configuration";
        uses juniper-protocols-ospf;
      }
      container ospf3 {
        description
          "OSPF3 configuration";
        uses juniper-protocols-ospf3;
      }
      container mvrp {
        description
          "MVRP configuration";
        uses juniper-protocols-mvrp;
      }
    }
    leaf service-type {
      type enumeration {
        enum "vlan-bundle" {
          description
            "Instance service type vlan-bundle";
        }
        enum "vlan-aware" {
          description
            "Instance service type vlan-aware";
        }
      }
      description
        "Sevice type";
    }
    container vtep-source-interface {
      description
        "Source layer-3 IFL for VXLAN";
      leaf interface-name {
        type union {
          type jt:interface-name;
          type string {
            pattern "<.*>|$.*";
          }
        }
      }
      container inet {
        presence "enable inet";
        description
          "IPv4 source";
        uses apply-advanced;
      }
      container inet6 {
        presence "enable inet6";
        description
          "IPv6 source";
        uses apply-advanced;
      }
    }
    container bridge-options {
      description
        "Bridge options";
      uses apply-advanced;
      container traceoptions {
        description
          "Bridge trace options";
        uses apply-advanced;
        container file {
          description
            "Trace file options";
          leaf filename {
            type string {
              length "1 .. 1024";
            }
            description
              "Name of file in which to write trace information";
          }
          leaf replace {
            type empty;
            status deprecated;
            description
              "Replace trace file rather than appending to it";
          }
          leaf size {
            type string;
            description
              "Maximum trace file size";
          }
          leaf files {
            type union {
              type string {
                pattern "<.*>|$.*";
              }
              type uint32 {
                range "2 .. 1000";
              }
            }
            default "10";
            description
              "Maximum number of trace files";
          }
          leaf no-stamp {
            type empty;
            status deprecated;
            description
              "Do not timestamp trace file";
          }
          choice world-readable-choice {
            leaf world-readable {
              type empty;
              description
                "Allow any user to read the log file";
            }
            leaf no-world-readable {
              type empty;
              description
                "Don't allow any user to read the log file";
            }
          }
        }
        list flag {
          key "name";
          description
            "Tracing parameters";
          leaf name {
            type enumeration {
              enum "kernel" {
                description
                  "Log configuration IPC messages to kernel";
              }
              enum "error" {
                description
                  "Log error events";
              }
              enum "warning" {
                description
                  "Log warning events";
              }
              enum "notice" {
                description
                  "Log notification events";
              }
              enum "info" {
                description
                  "Log informations";
              }
              enum "debugging" {
                description
                  "Log debug events";
              }
              enum "route" {
                description
                  "Trace routing information";
              }
              enum "normal" {
                description
                  "Trace normal events";
              }
              enum "general" {
                description
                  "Trace general events";
              }
              enum "state" {
                description
                  "Trace state transitions";
              }
              enum "policy" {
                description
                  "Trace policy processing";
              }
              enum "task" {
                description
                  "Trace routing protocol task processing";
              }
              enum "timer" {
                description
                  "Trace routing protocol timer processing";
              }
              enum "all" {
                description
                  "Trace everything";
              }
            }
          }
        }
      }
    }
    container bridge-domains {
      description
        "Bridge domain configuration";
      uses apply-advanced;
      list domain {
        key "name";
        uses juniper-bridge-domains;
      }
    }
    list interface {
      key "name";
      description
        "Interface name for this routing instance";
      leaf name {
        type string;
      }
      uses apply-advanced;
      choice mode {
        case case_1 {
          leaf any {
            type empty;
            description
              "Interface used for both unicast and multicast traffic";
          }
        }
        case case_2 {
          leaf unicast {
            type empty;
            description
              "Interface used for unicast traffic only";
          }
        }
        case case_3 {
          leaf multicast {
            type empty;
            description
              "Interface used for multicast traffic only";
          }
        }
      }
      leaf primary {
        type empty;
        description
          "Preferred multicast vt interface for the routing-instance";
      }
      leaf protect-interface {
        type union {
          type jt:interface-name;
          type string {
            pattern "<.*>|$.*";
          }
        }
        description
          "Name of protect interface";
      }
    }
    container route-distinguisher {
      description
        "Route distinguisher for this instance";
      leaf rd-type {
        type string;
        description
          "Number in (16 bit:32 bit) or (32 bit 'L':16 bit) or (IP address:16 bit) format";
      }
    }
    leaf-list vrf-import {
      type jt:policy-algebra;
      ordered-by user;
      description
        "Import policy for VRF instance RIBs";
    }
    leaf-list vrf-export {
      type jt:policy-algebra;
      ordered-by user;
      description
        "Export policy for VRF instance RIBs";
    }
    leaf export-default-action {
      type enumeration {
        enum "accept" {
          description
            "Default action is accept";
        }
        enum "reject" {
          description
            "Default action is reject";
        }
      }
      description
        "Default action for export in routing-instance";
    }
    leaf import-default-action {
      type enumeration {
        enum "accept" {
          description
            "Default action is accept";
        }
        enum "reject" {
          description
            "Default action is reject";
        }
      }
      description
        "Default action for import in routing-instance";
    }
    container vrf-target {
      description
        "VRF target community configuration";
      uses apply-advanced;
      leaf community {
        type string;
        description
          "Target community to use in import and export";
      }
      leaf import {
        type string;
        description
          "Target community to use when filtering on import";
      }
      leaf export {
        type string;
        description
          "Target community to use when marking routes on export";
      }
      leaf auto {
        type empty;
        description
          "Auto derive import and export target community from BGP AS & L2";
      }
    }
    leaf no-vrf-advertise {
      type empty;
      description
        "Don't advertise this instance to remote PEs";
    }
    container vrf-table-label {
      presence "enable vrf-table-label";
      description
        "Advertise a single VPN label for all routes in the VRF";
      leaf static {
        type union {
          type string {
            pattern "<.*>|$.*";
          }
          type uint32 {
            range "16 .. 1048575";
          }
        }
        description
          "Specify label value to be used";
      }
      leaf source-class-usage {
        type empty;
        description
          "Enable source class usage";
      }
    }
    choice vrf-propagate-ttl-or-no-vrf-propagate-ttl {
      case case_1;
      case case_2;
    }
  }

  grouping juniper-bridge-domains {
    description
      "Bridge domains";
    leaf name {
      type string;
      description
        "Bridge domain name";
    }
    uses apply-advanced;
    leaf description {
      type string;
      description
        "Text description of bridge domain";
    }
    choice vlan_choice {
      case case_1 {
        leaf vlan-id {
          type string;
          description
            "IEEE 802.1q VLAN identifier for bridging domain";
        }
      }
    }
    leaf no-local-switching {
      type empty;
      description
        "Disable local switching within CE-facing interfaces";
    }
    list interface {
      key "name";
      ordered-by user;
      description
        "Interface name for this bridge domain";
      leaf name {
        type string;
      }
      uses apply-advanced;
    }
    leaf routing-interface {
      type union {
        type jt:interface-unit;
        type string {
          pattern "<.*>|$.*";
        }
      }
      description
        "Routing interface name for this bridge-domain";
    }
    container bridge-options {
      description
        "Bridge options configuration";
      uses apply-advanced;
      list interface {
        key "name";
        ordered-by user;
        description
          "Interface name";
        leaf name {
          type union {
            type jt:interface-name;
            type string {
              pattern "<.*>|$.*";
            }
          }
          description
            "Interface name";
        }
        uses apply-advanced;
        list static-mac {
          key "name";
          ordered-by user;
          description
            "Static MAC addresses assigned to this interface";
          leaf name {
            type jt:mac-addr;
            description
              "MAC address";
          }
          uses apply-advanced;
          list vlan-id {
            key "name";
            ordered-by user;
            description
              "VLAN ID of learning VLAN";
            leaf name {
              type union {
                type string {
                  pattern "<.*>|$.*";
                }
                type uint32 {
                  range "0 .. 4094";
                }
              }
              description
                "Learning VLAN";
            }
            uses apply-advanced;
          }
        }
        leaf no-mac-learning {
          type empty;
          description
            "Disable dynamic MAC address learning";
        }
      }
    }
    container vxlan {
      description
        "VXLAN options";
      uses apply-advanced;
      leaf vni {
        type union {
          type string {
            pattern "<.*>|$.*";
          }
          type uint32 {
            range "0 .. 16777214";
          }
        }
        mandatory true;
        description
          "VXLAN identifier";
      }
      leaf destination-udp-port {
        type union {
          type string {
            pattern "<.*>|$.*";
          }
          type uint16 {
            range "4789 .. 65535";
          }
        }
        default "4789";
        description
          "VXLAN destination UDP port";
      }
      leaf mtu {
        type union {
          type string {
            pattern "<.*>|$.*";
          }
          type uint16 {
            range "100 .. 65535";
          }
        }
        default "9216";
        description
          "Maximum transmit packet size";
      }
    }
    container forwarding-options {
      presence "enable forwarding-options";
      description
        "Forwarding options configuration";
      uses apply-advanced;
      container filter {
        description
          "Filtering for bridge forwarding table";
        uses apply-advanced;
        leaf input {
          type string;
        }
      }
    }
  }

  grouping juniper-protocols-l2vpn {
    description
      "Layer 2 VPN, VPLS or EVPN configuration";
    uses apply-advanced;
    list interface {
      key "name";
      description
        "Interface that connect this site to the VPN";
      leaf name {
        type union {
          type jt:interface-name;
          type string {
            pattern "<.*>|$.*";
          }
        }
        description
          "Interface name";
      }
      uses apply-advanced;
      container vpws-service-id {
        presence "enable vpws-service-id";
        description
          "Service-id for EVPN VPWS routing instance";
        uses apply-advanced;
        leaf local {
          type union {
            type string {
              pattern "<.*>|$.*";
            }
            type uint32 {
              range "1 .. 16777215";
            }
          }
          mandatory true;
          description
            "Local EVPN VPWS service id";
        }
        leaf remote {
          type union {
            type string {
              pattern "<.*>|$.*";
            }
            type uint32 {
              range "1 .. 16777215";
            }
          }
          mandatory true;
          description
            "Remote EVPN VPWS service id";
        }
        container source-packet-routing {
          presence "enable source-packet-routing";
          uses apply-advanced;
          container srv6 {
            description
              "Enable IPv6 segment routing (SRv6)";
            container locator {
              description
                "SRv6 locator";
              leaf loc-name {
                type string;
                mandatory true;
                description
                  "Locator name";
              }
              choice mode {
                case case_1 {
                  leaf end-dx2-sid {
                    type jt:ipv6addr;
                    description
                      "Segment routing header based end dx2 sid";
                  }
                }
                case case_2 {
                  container micro-dx2-sid {
                    presence "enable micro-dx2-sid";
                    description
                      "Micro dx2 sid";
                    uses apply-advanced;
                    leaf micro-sid-value {
                      type union {
                        type uint32;
                        type string {
                          pattern "<.*>|$.*";
                        }
                      }
                      mandatory true;
                      description
                        "Static micro sid value 16-bit or 32-bit";
                    }
                  }
                }
              }
            }
          }
        }
      }
      leaf flow-label-transmit-static {
        type empty;
        description
          "Push Flow Label on PW packets sent to remote PE";
      }
      leaf flow-label-receive-static {
        type empty;
        description
          "Pop Flow Label from PW packets received from remote PE";
      }
      leaf remote-site-id {
        type union {
          type string {
            pattern "<.*>|$.*";
          }
          type uint32 {
            range "1 .. 65534";
          }
        }
        description
          "Site identifier associated with this interface";
      }
      leaf target-attachment-identifier {
        type string;
        description
          "FEC 129 VPWS target attachment identifier";
      }
      leaf flow-label-transmit {
        type empty;
        description
          "Advertise capability to push Flow Label in transmit direction to remote PE";
      }
      leaf flow-label-receive {
        type empty;
        description
          "Advertise capability to pop Flow Label in receive direction to remote PE";
      }
      choice cword {
        case case_1 {
          leaf control-word {
            type empty;
            description
              "Add control word to the Layer 2 encapsulation";
          }
        }
        case case_2 {
          leaf no-control-word {
            type empty;
            description
              "Disables control word on the Layer 2 encapsulation";
          }
        }
      }
      leaf encapsulation-type {
        type enumeration {
          enum "atm-aal5" {
            description
              "ATM AAL/5 encapsulation";
          }
          enum "atm-cell" {
            description
              "ATM port promiscuous mode cell encapsulation";
          }
          enum "atm-cell-port-mode" {
            description
              "ATM port promiscuous mode cell encapsulation";
          }
          enum "atm-cell-vp-mode" {
            description
              "ATM VP promiscuous mode cell encapsulation";
          }
          enum "atm-cell-vc-mode" {
            description
              "ATM non-promiscuous cell encapsulation";
          }
          enum "frame-relay" {
            description
              "Frame Relay encapsulation";
          }
          enum "ppp" {
            description
              "PPP encapsulation";
          }
          enum "cisco-hdlc" {
            description
              "Cisco-compatible HDLC encapsulation";
          }
          enum "ethernet-vlan" {
            description
              "Ethernet VLAN encapsulation";
          }
          enum "ethernet" {
            description
              "Ethernet encapsulation";
          }
          enum "interworking" {
            description
              "Layer 2.5 interworking VPN";
          }
          enum "frame-relay-port-mode" {
            description
              "Frame Relay port mode encapsulation";
          }
          enum "satop-t1" {
            description
              "SATOP-T1 based Layer 2 VPN";
          }
          enum "satop-e1" {
            description
              "SATOP-E1 based Layer 2 VPN";
          }
          enum "satop-t3" {
            description
              "SATOP-T3 based Layer 2 VPN";
          }
          enum "satop-e3" {
            description
              "SATOP-E3 based Layer 2 VPN";
          }
          enum "cesop" {
            description
              "CESOP based Layer 2 VPN";
          }
        }
        description
          "Encapsulation type for VPN";
      }
      leaf ignore-encapsulation-mismatch {
        type empty;
        description
          "Allow different encapsulation types on local and remote end";
      }
      leaf mtu {
        type union {
          type string {
            pattern "<.*>|$.*";
          }
          type uint16 {
            range "512 .. 65535";
          }
        }
        description
          "MTU to be advertised to the remote end";
      }
      leaf ignore-mtu-mismatch {
        type empty;
        description
          "Allow different MTU values on local and remote end";
      }
      leaf pseudowire-status-tlv {
        type empty;
        description
          "Send pseudowire status TLV";
      }
      leaf community {
        type string;
        description
          "Community associated with this interface";
      }
      leaf description {
        type string;
        description
          "Text description";
      }
    }
    leaf designated-forwarder-election-hold-time {
      type union {
        type string {
          pattern "<.*>|$.*";
        }
        type uint32 {
          range "1 .. 1800";
        }
      }
      units "seconds";
      description
        "Time to wait before electing a DF(seconds)";
    }
    choice df-preference-alg {
      case case_1 {
        leaf designated-forwarder-preference-least {
          type empty;
          description
            "Use least preference in DF election";
        }
      }
      case case_2 {
        leaf designated-forwarder-preference-highest {
          type empty;
          description
            "Use highest preference in DF election";
        }
      }
    }
    leaf encapsulation {
      type enumeration {
        enum "mpls" {
          description
            "MPLS encapsulation";
        }
        enum "vxlan" {
          description
            "VXLAN encapsulation";
        }
        enum "mpls-inet6" {
          description
            "MPLS over IPv6 encapsulation";
        }
        enum "srv6" {
          description
            "SRv6 encapsulation";
        }
      }
      default "mpls";
      description
        "Encapsulation type for EVPN";
    }
    leaf default-gateway {
      type enumeration {
        enum "advertise" {
          description
            "Advertise IRB MACs with default gateway community";
        }
        enum "no-gateway-community" {
          description
            "Advertise IRB MACs without default gateway community";
        }
        enum "do-not-advertise" {
          description
            "Do not advertise IRB MACs";
        }
      }
      description
        "Default gateway mode";
    }
    container duplicate-mac-detection {
      description
        "Duplicate MAC detection settings";
      uses apply-advanced;
      leaf detection-threshold {
        type union {
          type string {
            pattern "<.*>|$.*";
          }
          type uint32 {
            range "2 .. 20";
          }
        }
        description
          "Number of moves to trigger duplicate MAC detection";
      }
      leaf detection-window {
        type union {
          type string {
            pattern "<.*>|$.*";
          }
          type uint32 {
            range "5 .. 600";
          }
        }
        units "seconds";
        description
          "Time window for detection of duplicate MACs";
      }
      leaf auto-recovery-time {
        type union {
          type string {
            pattern "<.*>|$.*";
          }
          type uint32 {
            range "1 .. 360";
          }
        }
        units "minutes";
        description
          "Automatically unblock duplicate MACs after a time delay";
      }
      leaf auto-recovery-time-seconds {
        type union {
          type string {
            pattern "<.*>|$.*";
          }
          type uint32 {
            range "1 .. 21600";
          }
        }
        units "seconds";
        description
          "Automatically unblock duplicate MACs after a time delay";
      }
      leaf include-local-moves {
        type empty;
        description
          "Include local moves in duplicate MAC detection";
      }
      leaf action {
        type enumeration {
          enum "block" {
            description
              "Drop packet with duplicate MAC as source or destination";
          }
          enum "shutdown" {
            description
              "Shutdown the port to prevent loop";
          }
          enum "no-mac-suppression" {
            description
              "Disable MAC suppression for duplicate MACs";
          }
        }
        description
          "Loop protection action";
      }
    }
    container irb-symmetric-routing {
      presence "enable irb-symmetric-routing";
      description
        "Enable EVPN T-2 symmetric routing";
      uses apply-advanced;
      leaf vni {
        type union {
          type string {
            pattern "<.*>|$.*";
          }
          type uint32 {
            range "1 .. 16777214";
          }
        }
        description
          "VXLAN network identifier used for T-2 symmetric routing IP prefixes";
      }
    }
    container source-packet-routing {
      presence "enable source-packet-routing";
      uses apply-advanced;
      container srv6 {
        description
          "Enable IPv6 segment routing (SRv6)";
        container locator {
          description
            "SRv6 locator";
          leaf loc-name {
            type string;
            mandatory true;
            description
              "Locator name";
          }
          choice mode {
            case case_1 {
              leaf end-dt2-sid {
                type empty;
                description
                  "Segment Routing Header-based End.DT2 SIDs";
              }
            }
            case case_2 {
              leaf micro-dt2-sid {
                type empty;
                description
                  "Micro-SID based End.DT2 SIDs";
              }
            }
          }
        }
      }
    }
    container ip-prefix-routes {
      presence "enable ip-prefix-routes";
      description
        "Advertise IP prefixes through EVPN";
      uses apply-advanced;
      leaf advertise {
        type enumeration {
          enum "gateway-address" {
            description
              "Advertise a gateway address in exported IP prefix routes";
          }
          enum "direct-nexthop" {
            description
              "Advertise a direct nexthop in exported IP prefix routes";
          }
        }
        mandatory true;
        description
          "Advertisement attributes for IP prefixes";
      }
      leaf encapsulation {
        type enumeration {
          enum "mpls" {
            description
              "MPLS encapsulation";
          }
          enum "vxlan" {
            description
              "VXLAN encapsulation";
          }
          enum "srv6" {
            description
              "SRV6 encapsulation";
          }
        }
        description
          "Encapsulation used for IP prefixes";
      }
      leaf reject-asymmetric-vni {
        type empty;
        description
          "Disable Type-5 asymmetric-vni";
      }
      leaf vni {
        type union {
          type string {
            pattern "<.*>|$.*";
          }
          type uint32 {
            range "1 .. 16777214";
          }
        }
        description
          "VXLAN network identifier used for IP prefixes";
      }
      leaf-list import {
        type jt:policy-algebra;
        ordered-by user;
        description
          "Policy to control import of IP prefixes from EVPN";
      }
      leaf-list export {
        type jt:policy-algebra;
        ordered-by user;
        description
          "Policy to control export of IP prefixes through EVPN";
      }
      container route-attributes {
        description
          "Route Attribute Import Export Option";
        uses apply-advanced;
        container as-path {
          description
            "AS-PATH Attribute";
          uses apply-advanced;
          leaf import-action {
            type enumeration {
              enum "allow" {
                description
                  "Inherit as-path from EVPN routes to IP routes";
              }
              enum "skip" {
                description
                  "Donot inehrit as-path from EVPN routes to IP routes";
              }
            }
            description
              "AS-PATH Attribute Inherit Option on Import";
          }
          leaf export-action {
            type enumeration {
              enum "allow" {
                description
                  "Inherit as-path from IP routes to EVPN routes";
              }
              enum "skip" {
                description
                  "Donot inherit as-path from IP routes to EVPN routes";
              }
            }
            description
              "AS-PATH Attribute Inherit Option on Export";
          }
        }
        container preference {
          description
            "Preference Attribute";
          uses apply-advanced;
          leaf import-action {
            type enumeration {
              enum "allow" {
                description
                  "Inherit preference from EVPN routes to IP routes";
              }
              enum "skip" {
                description
                  "Donot inherit preference from EVPN routes to EVPN routes";
              }
            }
            description
              "Preference Attribute Inerit Option on Import";
          }
          leaf export-action {
            type enumeration {
              enum "allow" {
                description
                  "Inherit preference from IP routes to EVPN routes";
              }
              enum "skip" {
                description
                  "Donot inherit preference from IP routes to EVPN routes";
              }
            }
            description
              "Preference Attribute Inherit Option on Export";
          }
        }
        container community {
          description
            "Community Attribute";
          uses apply-advanced;
          leaf import-action {
            type enumeration {
              enum "allow" {
                description
                  "Inherit community from EVPN routes to IP routes";
              }
              enum "skip" {
                description
                  "Donot inherit community from EVPN routes to IP routes";
              }
            }
            description
              "Community Attribute Inherit Option on Import";
          }
          leaf export-action {
            type enumeration {
              enum "allow" {
                description
                  "Inherit community from IP routes to EVPN routes";
              }
              enum "skip" {
                description
                  "Donot inherit community from IP route to EVPN routes";
              }
            }
            description
              "Community Attribute Inherit Option on Export";
          }
        }
      }
      container source-packet-routing {
        description
          "Enable source packet routing";
        uses apply-advanced;
        container srv6 {
          description
            "Enable IPv6 segment souting (SRv6)";
          uses apply-advanced;
          list locator {
            key "name";
            ordered-by user;
            description
              "SRv6 locator";
            leaf name {
              type string;
              description
                "Locator name";
            }
            uses apply-advanced;
            container end-dt4-sid {
              presence "enable end-dt4-sid";
              description
                "End dt4 sid";
            }
            container end-dt6-sid {
              presence "enable end-dt6-sid";
              description
                "End dt6 sid";
            }
            container end-dt46-sid {
              presence "enable end-dt46-sid";
              description
                "End dt46 sid";
            }
            container micro-dt4-sid {
              presence "enable micro-dt4-sid";
              description
                "Micro dt4 sid";
            }
            container micro-dt6-sid {
              presence "enable micro-dt6-sid";
              description
                "Micro dt6 sid";
            }
            container micro-dt46-sid {
              presence "enable micro-dt46-sid";
              description
                "Micro dt46 sid";
            }
          }
        }
      }
    }
    choice flexible-cross-connect-type {
      case case_1;
      case case_2;
    }
    container traceoptions {
      description
        "Trace options for Layer 2 VPNs";
      uses apply-advanced;
      container file {
        description
          "Trace file options";
        leaf filename {
          type string {
            length "1 .. 1024";
          }
          description
            "Name of file in which to write trace information";
        }
        leaf replace {
          type empty;
          status deprecated;
          description
            "Replace trace file rather than appending to it";
        }
        leaf size {
          type string;
          description
            "Maximum trace file size";
        }
        leaf files {
          type union {
            type string {
              pattern "<.*>|$.*";
            }
            type uint32 {
              range "2 .. 1000";
            }
          }
          default "10";
          description
            "Maximum number of trace files";
        }
        leaf no-stamp {
          type empty;
          status deprecated;
          description
            "Do not timestamp trace file";
        }
        choice world-readable-choice {
          leaf world-readable {
            type empty;
            description
              "Allow any user to read the log file";
          }
          leaf no-world-readable {
            type empty;
            description
              "Don't allow any user to read the log file";
          }
        }
      }
      list flag {
        key "name";
        ordered-by user;
        description
          "Tracing parameters";
        leaf name {
          type enumeration {
            enum "error" {
              description
                "Trace errors";
            }
            enum "topology" {
              description
                "Trace Layer 2 VPN, VPLS and EVPN topology changes";
            }
            enum "nlri" {
              description
                "Trace Layer 2 VPN, VPLS and EVPN remote site advertisements";
            }
            enum "connections" {
              description
                "Trace Layer 2 VPN and VPLS connections";
            }
            enum "automatic-site" {
              description
                "Trace VPLS automatic site state";
            }
            enum "oam" {
              description
                "Trace OAM messages";
            }
            enum "mac-database" {
              description
                "Trace MAC route database in a EVPN instance";
            }
            enum "nsr" {
              description
                "Trace NSR in a EVPN instance";
            }
            enum "egress-protection" {
              description
                "Trace Edge Protection messages";
            }
            enum "instance" {
              description
                "Evpn instance related messages";
            }
            enum "interface" {
              description
                "Interface related messages";
            }
            enum "l2aldsync" {
              description
                "Messages related to EVPN-L2ALD communication";
            }
            enum "p2mp" {
              description
                "P2MP messages";
            }
            enum "esi" {
              description
                "Evpn ethernet segment related messages";
            }
            enum "mcsn" {
              description
                "Evpn multicast snooping related messages";
            }
            enum "vpws" {
              description
                "VPWS messages";
            }
            enum "irb" {
              description
                "Integrated routing bridging messages";
            }
            enum "ar" {
              description
                "Assisted-replication messages";
            }
            enum "etree" {
              description
                "Evpn etree messages";
            }
            enum "kernel" {
              description
                "Messages related to rpd-kernel communication";
            }
            enum "bd" {
              description
                "Evpn bridge domain messages";
            }
            enum "pbb" {
              description
                "Evpn provider backbone bridging messages";
            }
            enum "infra" {
              description
                "Messages related to infrastructure in evpn";
            }
            enum "pfxdb" {
              description
                "Type-5 related messages";
            }
            enum "peg-df" {
              description
                "PIM EVPN Gateway DF-Election related messages";
            }
            enum "gbptagdb" {
              description
                "Trace message related to gbptagdb";
            }
            enum "route" {
              description
                "Trace routing information";
            }
            enum "normal" {
              description
                "Trace normal events";
            }
            enum "general" {
              description
                "Trace general events";
            }
            enum "state" {
              description
                "Trace state transitions";
            }
            enum "policy" {
              description
                "Trace policy processing";
            }
            enum "task" {
              description
                "Trace routing protocol task processing";
            }
            enum "timer" {
              description
                "Trace routing protocol timer processing";
            }
            enum "all" {
              description
                "Trace everything";
            }
          }
        }
        leaf send {
          type empty;
          description
            "Trace transmitted packets";
        }
        leaf receive {
          type empty;
          description
            "Trace received packets";
        }
        leaf detail {
          type empty;
          description
            "Trace detailed information";
        }
        leaf disable {
          type empty;
          description
            "Disable this trace flag";
        }
      }
    }
    leaf encapsulation-type {
      type enumeration {
        enum "atm-aal5" {
          description
            "ATM AAL/5 encapsulation";
        }
        enum "atm-cell" {
          description
            "ATM port promiscuous mode cell encapsulation";
        }
        enum "atm-cell-port-mode" {
          description
            "ATM port promiscuous mode cell encapsulation";
        }
        enum "atm-cell-vp-mode" {
          description
            "ATM VP promiscuous mode cell encapsulation";
        }
        enum "atm-cell-vc-mode" {
          description
            "ATM non-promiscuous cell encapsulation";
        }
        enum "frame-relay" {
          description
            "Frame Relay encapsulation";
        }
        enum "ppp" {
          description
            "PPP encapsulation";
        }
        enum "cisco-hdlc" {
          description
            "Cisco-compatible HDLC encapsulation";
        }
        enum "ethernet-vlan" {
          description
            "Ethernet VLAN encapsulation";
        }
        enum "ethernet" {
          description
            "Ethernet encapsulation";
        }
        enum "interworking" {
          description
            "Layer 2.5 interworking VPN";
        }
        enum "frame-relay-port-mode" {
          description
            "Frame Relay port mode encapsulation";
        }
        enum "satop-t1" {
          description
            "SATOP-T1 based Layer 2 VPN";
        }
        enum "satop-e1" {
          description
            "SATOP-E1 based Layer 2 VPN";
        }
        enum "satop-t3" {
          description
            "SATOP-T3 based Layer 2 VPN";
        }
        enum "satop-e3" {
          description
            "SATOP-E3 based Layer 2 VPN";
        }
        enum "cesop" {
          description
            "CESOP based Layer 2 VPN";
        }
      }
      description
        "Encapsulation type for VPN";
    }
    leaf control-word {
      type empty;
      description
        "Add control word to the Layer 2 encapsulation";
    }
    leaf no-control-word {
      type empty;
      description
        "Disables control word on the Layer 2 encapsulation";
    }
    leaf site-range {
      type union {
        type string {
          pattern "<.*>|$.*";
        }
        type uint32 {
          range "1 .. 65534";
        }
      }
      description
        "Maximum site identifier in this VPLS domain";
    }
    leaf label-block-size {
      type enumeration {
        enum "2" {
          description
            "Label block size of 2";
        }
        enum "4" {
          description
            "Label block size of 4";
        }
        enum "8" {
          description
            "Label block size of 8";
        }
        enum "16" {
          description
            "Label block size of 16";
        }
      }
      description
        "Label block size for this VPLS instance";
    }
    choice tunnel-services-choice {
      case case_1 {
        container tunnel-services {
          description
            "Use tunnel services for this VPLS instance";
          uses apply-advanced;
          leaf-list devices {
            type union {
              type jt:interface-device;
              type string {
                pattern "<.*>|$.*";
              }
            }
            ordered-by user;
            description
              "Tunnel services devices to use for this VPLS instance";
          }
          leaf primary {
            type union {
              type jt:interface-device;
              type string {
                pattern "<.*>|$.*";
              }
            }
            description
              "Primary tunnel services device to use for VPLS instance";
          }
        }
      }
      case case_2 {
        leaf no-tunnel-services {
          type empty;
          description
            "Do not use tunnel services for this VPLS instance";
        }
      }
    }
    list site {
      key "name";
      description
        "Sites connected to this provider equipment";
      leaf name {
        type string;
        description
          "Name of Layer 2 VPN or VPLS site";
      }
      uses apply-advanced;
      choice site-identifier-mode {
        case case_1 {
          leaf site-identifier {
            type union {
              type string {
                pattern "<.*>|$.*";
              }
              type uint32 {
                range "1 .. 65534";
              }
            }
            description
              "Layer 2 VPN or VPLS site identifier (unique in the VPN)";
          }
        }
        case case_2 {
          container automatic-site-id {
            presence "enable automatic-site-id";
            description
              "Enable automatic assignment of site identifier";
            uses apply-advanced;
            leaf startup-wait-time {
              type union {
                type string {
                  pattern "<.*>|$.*";
                }
                type uint32 {
                  range "1 .. 3600";
                }
              }
              units "seconds";
              description
                "Time to wait at startup before claming a site identifier (seconds)";
            }
            leaf new-site-wait-time {
              type union {
                type string {
                  pattern "<.*>|$.*";
                }
                type uint32 {
                  range "1 .. 3600";
                }
              }
              units "seconds";
              description
                "Time to wait before claiming a site identifier";
            }
            leaf collision-detect-time {
              type union {
                type string {
                  pattern "<.*>|$.*";
                }
                type uint32 {
                  range "1 .. 3600";
                }
              }
              units "seconds";
              description
                "Time to wait for detecting a collision";
            }
            container reclaim-wait-time {
              presence "enable reclaim-wait-time";
              description
                "Time to wait for reclaiming a site identifier";
              leaf minimum {
                type union {
                  type uint32;
                  type string {
                    pattern "<.*>|$.*";
                  }
                }
                units "milliseconds";
                mandatory true;
                description
                  "Minimum wait time";
              }
              leaf maximum {
                type union {
                  type uint32;
                  type string {
                    pattern "<.*>|$.*";
                  }
                }
                units "milliseconds";
                mandatory true;
                description
                  "Maximum wait time";
              }
            }
          }
        }
      }
      leaf source-attachment-identifier {
        type string;
        description
          "FEC 129 VPWS source attachment identifier";
      }
      leaf flow-label-transmit {
        type empty;
        description
          "Advertise capability to push Flow Label in transmit direction to remote PE";
      }
      leaf flow-label-receive {
        type empty;
        description
          "Advertise capability to push Flow Label in receive direction to remote PE";
      }
      leaf encapsulation-type {
        type enumeration {
          enum "atm-aal5" {
            description
              "ATM AAL/5 encapsulation";
          }
          enum "atm-cell" {
            description
              "ATM port promiscuous mode cell encapsulation";
          }
          enum "atm-cell-port-mode" {
            description
              "ATM port promiscuous mode cell encapsulation";
          }
          enum "atm-cell-vp-mode" {
            description
              "ATM VP promiscuous mode cell encapsulation";
          }
          enum "atm-cell-vc-mode" {
            description
              "ATM non-promiscuous cell encapsulation";
          }
          enum "frame-relay" {
            description
              "Frame Relay encapsulation";
          }
          enum "ppp" {
            description
              "PPP encapsulation";
          }
          enum "cisco-hdlc" {
            description
              "Cisco-compatible HDLC encapsulation";
          }
          enum "ethernet-vlan" {
            description
              "Ethernet VLAN encapsulation";
          }
          enum "ethernet" {
            description
              "Ethernet encapsulation";
          }
          enum "interworking" {
            description
              "Layer 2.5 interworking VPN";
          }
          enum "frame-relay-port-mode" {
            description
              "Frame Relay port mode encapsulation";
          }
          enum "satop-t1" {
            description
              "SATOP-T1 based Layer 2 VPN";
          }
          enum "satop-e1" {
            description
              "SATOP-E1 based Layer 2 VPN";
          }
          enum "satop-t3" {
            description
              "SATOP-T3 based Layer 2 VPN";
          }
          enum "satop-e3" {
            description
              "SATOP-E3 based Layer 2 VPN";
          }
          enum "cesop" {
            description
              "CESOP based Layer 2 VPN";
          }
        }
        description
          "Encapsulation type for VPN";
      }
      leaf ignore-encapsulation-mismatch {
        type empty;
        description
          "Allow different encapsulation types on local and remote end";
      }
      choice cword {
        case case_1 {
          leaf control-word {
            type empty;
            description
              "Adds control-word to the Layer 2 encapsulation";
          }
        }
        case case_2 {
          leaf no-control-word {
            type empty;
            description
              "Disables control-word to the Layer 2 encapsulation";
          }
        }
      }
      leaf pseudowire-status-tlv {
        type empty;
        description
          "Send pseudowire status TLV";
      }
      leaf community {
        type string;
        description
          "Community associated with this site";
      }
      container multi-homing {
        presence "enable multi-homing";
        description
          "Enable multi-homing functionality for this site";
        uses apply-advanced;
        leaf hold-time {
          type union {
            type string {
              pattern "<.*>|$.*";
            }
            type uint32 {
              range "1 .. 18000";
            }
          }
          units "seconds";
          description
            "Enable multi-homing non-designated forwarder hold time (seconds)";
        }
      }
      leaf site-preference {
        type string;
        description
          "Layer 2 VPN or VPLS site preference";
      }
      leaf hot-standby {
        type empty;
        description
          "Keep backup pseudowire in continuous standby mode and ready for traffic forwarding";
      }
      leaf mtu {
        type union {
          type string {
            pattern "<.*>|$.*";
          }
          type uint16 {
            range "512 .. 65535";
          }
        }
        description
          "MTU to be advertised to the remote end";
      }
      leaf ignore-mtu-mismatch {
        type empty;
        description
          "Allow different MTU values on local and remote end";
      }
      list mesh-group {
        key "name";
        ordered-by user;
        description
          "Mesh-groups that are part of this site";
        leaf name {
          type string;
          description
            "Mesh-group name";
        }
        uses apply-advanced;
      }
      container active-interface {
        description
          "Configure interface to designate as active";
        choice interface_name {
          case case_1 {
            leaf any {
              type empty;
              description
                "One configured interface is designated active at random";
            }
          }
          case case_2 {
            leaf primary {
              type union {
                type jt:interface-name;
                type string {
                  pattern "<.*>|$.*";
                }
              }
              description
                "Interface to designate as active if it is operational";
            }
          }
        }
      }
      leaf best-site {
        type empty;
        description
          "Activates best-site functionality for this instance";
      }
      list interface {
        key "name";
        description
          "Interface that connect this site to the VPN";
        leaf name {
          type union {
            type jt:interface-name;
            type string {
              pattern "<.*>|$.*";
            }
          }
          description
            "Interface name";
        }
        uses apply-advanced;
        leaf remote-site-id {
          type union {
            type string {
              pattern "<.*>|$.*";
            }
            type uint32 {
              range "1 .. 65534";
            }
          }
          description
            "Site identifier associated with this interface";
        }
        leaf target-attachment-identifier {
          type string;
          description
            "FEC 129 VPWS target attachment identifier";
        }
        leaf flow-label-transmit {
          type empty;
          description
            "Advertise capability to push Flow Label in transmit direction to remote PE";
        }
        leaf flow-label-receive {
          type empty;
          description
            "Advertise capability to pop Flow Label in receive direction to remote PE";
        }
        choice cword {
          case case_1 {
            leaf control-word {
              type empty;
              description
                "Add control word to the Layer 2 encapsulation";
            }
          }
          case case_2 {
            leaf no-control-word {
              type empty;
              description
                "Disables control word on the Layer 2 encapsulation";
            }
          }
        }
        leaf encapsulation-type {
          type enumeration {
            enum "atm-aal5" {
              description
                "ATM AAL/5 encapsulation";
            }
            enum "atm-cell" {
              description
                "ATM port promiscuous mode cell encapsulation";
            }
            enum "atm-cell-port-mode" {
              description
                "ATM port promiscuous mode cell encapsulation";
            }
            enum "atm-cell-vp-mode" {
              description
                "ATM VP promiscuous mode cell encapsulation";
            }
            enum "atm-cell-vc-mode" {
              description
                "ATM non-promiscuous cell encapsulation";
            }
            enum "frame-relay" {
              description
                "Frame Relay encapsulation";
            }
            enum "ppp" {
              description
                "PPP encapsulation";
            }
            enum "cisco-hdlc" {
              description
                "Cisco-compatible HDLC encapsulation";
            }
            enum "ethernet-vlan" {
              description
                "Ethernet VLAN encapsulation";
            }
            enum "ethernet" {
              description
                "Ethernet encapsulation";
            }
            enum "interworking" {
              description
                "Layer 2.5 interworking VPN";
            }
            enum "frame-relay-port-mode" {
              description
                "Frame Relay port mode encapsulation";
            }
            enum "satop-t1" {
              description
                "SATOP-T1 based Layer 2 VPN";
            }
            enum "satop-e1" {
              description
                "SATOP-E1 based Layer 2 VPN";
            }
            enum "satop-t3" {
              description
                "SATOP-T3 based Layer 2 VPN";
            }
            enum "satop-e3" {
              description
                "SATOP-E3 based Layer 2 VPN";
            }
            enum "cesop" {
              description
                "CESOP based Layer 2 VPN";
            }
          }
          description
            "Encapsulation type for VPN";
        }
        leaf ignore-encapsulation-mismatch {
          type empty;
          description
            "Allow different encapsulation types on local and remote end";
        }
        leaf mtu {
          type union {
            type string {
              pattern "<.*>|$.*";
            }
            type uint16 {
              range "512 .. 65535";
            }
          }
          description
            "MTU to be advertised to the remote end";
        }
        leaf ignore-mtu-mismatch {
          type empty;
          description
            "Allow different MTU values on local and remote end";
        }
        leaf pseudowire-status-tlv {
          type empty;
          description
            "Send pseudowire status TLV";
        }
        leaf community {
          type string;
          description
            "Community associated with this interface";
        }
        leaf description {
          type string;
          description
            "Text description";
        }
      }
    }
    leaf community {
      type string;
      description
        "Community associated with this VPLS instance";
    }
    leaf vpls-id {
      type string;
      description
        "Identifier for this VPLS instance";
    }
    leaf mtu {
      type union {
        type string {
          pattern "<.*>|$.*";
        }
        type uint16 {
          range "512 .. 65535";
        }
      }
      description
        "MTU to be advertised to the remote end";
    }
    leaf ignore-mtu-mismatch {
      type empty;
      description
        "Allow different MTU values on local and remote end";
    }
    container mac-flush {
      presence "enable mac-flush";
      description
        "Enables mac-flush processing";
      uses apply-advanced;
      leaf any-interface {
        type empty;
        description
          "Send mac-flush when any AC interface goes down";
      }
      leaf any-spoke {
        type empty;
        description
          "Send mac-flush when any spoke pseudo wire goes down";
      }
      leaf propagate {
        type empty;
        description
          "Propagate mac-flush to the core";
      }
    }
    leaf ignore-encapsulation-mismatch {
      type empty;
      description
        "Allow different encapsulation types on local and remote end";
    }
    leaf pseudowire-status-tlv {
      type empty;
      description
        "Send pseudowire status TLV";
    }
    list neighbor {
      key "name";
      ordered-by user;
      description
        "Neighbor for this VPLS instance";
      leaf name {
        type jt:ipv4addr;
        description
          "Neighbor ID";
      }
      uses apply-advanced;
      container static {
        presence "enable static";
        description
          "Configuration of static vpls";
        uses apply-advanced;
        leaf incoming-label {
          type union {
            type uint32;
            type string {
              pattern "<.*>|$.*";
            }
          }
          mandatory true;
          description
            "VPLS incoming static label [1000000 - 1048575] or [29696 - 41983]";
        }
        leaf outgoing-label {
          type union {
            type string {
              pattern "<.*>|$.*";
            }
            type uint32 {
              range "16 .. 1048575";
            }
          }
          mandatory true;
          description
            "VPLS outgoing static label";
        }
        choice cword {
          case case_1 {
            leaf control-word {
              type empty;
              description
                "Adds control-word to the Layer 2 encapsulation";
            }
          }
          case case_2 {
            leaf no-control-word {
              type empty;
              description
                "Disables control-word to the Layer 2 encapsulation";
            }
          }
        }
      }
      leaf psn-tunnel-endpoint {
        type jt:ipv4addr;
        description
          "Endpoint of the transport tunnel on the remote PE";
      }
      leaf community {
        type string;
        description
          "Community associated with this neighbor";
      }
      leaf encapsulation-type {
        type enumeration {
          enum "ethernet-vlan" {
            description
              "Ethernet VLAN encapsulation";
          }
          enum "ethernet" {
            description
              "Ethernet encapsulation";
          }
        }
        description
          "Encapsulation type for VPN";
      }
      leaf ignore-encapsulation-mismatch {
        type empty;
        description
          "Allow different encapsulation types on local and remote end";
      }
      container pseudowire-status-tlv {
        presence "enable pseudowire-status-tlv";
        description
          "Send pseudowire status TLV";
        uses apply-advanced;
        leaf hot-standby-vc-on {
          type empty;
          description
            "Activate pseudowire upon arrival of 'hot-standby' status TLV message";
        }
      }
      leaf switchover-delay {
        type union {
          type string {
            pattern "<.*>|$.*";
          }
          type uint32 {
            range "0 .. 180000";
          }
        }
        units "milliseconds";
        default "10000";
        description
          "Pseudowire switchover delay ";
      }
      container revert-time {
        presence "enable revert-time";
        description
          "Enable pseudowire redundancy reversion (seconds)";
        leaf delay {
          type union {
            type string {
              pattern "<.*>|$.*";
            }
            type uint32 {
              range "0 .. 3600";
            }
          }
          units "seconds";
          mandatory true;
          description
            "Reversion timer (seconds)";
        }
        leaf maximum {
          type union {
            type string {
              pattern "<.*>|$.*";
            }
            type uint32 {
              range "0 .. 7200";
            }
          }
          units "seconds";
          description
            "Maximum reversion interval to add over revert-time delay";
        }
      }
      leaf connection-protection {
        type empty;
        description
          "End-2-end protection via OAM failure detection";
      }
      list backup-neighbor {
        key "name";
        ordered-by user;
        description
          "Configuration of redundant l2circuit";
        leaf name {
          type jt:ipv4addr;
          description
            "Neighbor ID";
        }
        uses apply-advanced;
        container static {
          presence "enable static";
          description
            "Configuration of static vpls";
          uses apply-advanced;
          leaf incoming-label {
            type union {
              type uint32;
              type string {
                pattern "<.*>|$.*";
              }
            }
            mandatory true;
            description
              "VPLS incoming static label [1000000 - 1048575] or [29696 - 41983]";
          }
          leaf outgoing-label {
            type union {
              type string {
                pattern "<.*>|$.*";
              }
              type uint32 {
                range "16 .. 1048575";
              }
            }
            mandatory true;
            description
              "VPLS outgoing static label";
          }
        }
        leaf community {
          type string;
          description
            "Community associated with this Layer 2 circuit";
        }
        leaf psn-tunnel-endpoint {
          type jt:ipv4addr;
          description
            "Endpoint of the transport tunnel on the remote PE";
        }
        leaf standby {
          type empty;
          description
            "Keep backup pseudowire in continuous standby";
        }
        leaf hot-standby {
          type empty;
          description
            "Keep backup pseudowire in continuous standby mode and ready for traffic forwarding";
        }
      }
    }
    leaf flow-label-transmit {
      type empty;
      description
        "Advertise capability to push Flow Label in transmit direction to remote PE";
    }
    leaf flow-label-receive {
      type empty;
      description
        "Advertise capability to pop Flow Label in receive direction to remote PE";
    }
    leaf flow-label-transmit-static {
      type empty;
      description
        "Push Flow Label on PW packets sent to remote PE";
    }
    leaf flow-label-receive-static {
      type empty;
      description
        "Pop Flow Label from PW packets received from remote PE";
    }
    leaf flow-label {
      type empty;
      description
        "Advertise flow-label capability";
    }
    leaf flow-label-static {
      type empty;
      description
        "Static flow-label";
    }
    list mesh-group {
      key "name";
      description
        "Mesh-group under this VPLS instance";
      leaf name {
        type string;
        description
          "Mesh-group name";
      }
      uses apply-advanced;
      choice peer-as-choice {
        case case_1 {
          container peer-as {
            description
              "Autonomous system of the peer";
            uses apply-advanced;
            leaf all {
              type empty;
              description
                "Include peers from all autonomous systems";
            }
          }
        }
      }
      leaf vpls-id {
        type string;
        description
          "LDP VPLS Identifier for this mesh-group";
      }
      leaf-list vrf-import {
        type jt:policy-algebra;
        ordered-by user;
        description
          "Import policy for VPLS instance mesh-group";
      }
      leaf-list vrf-export {
        type jt:policy-algebra;
        ordered-by user;
        description
          "Export policy for VPLS instance mesh-group";
      }
      container vrf-target {
        description
          "VPLS mesh-group target community configuration";
        uses apply-advanced;
        leaf community {
          type string;
          description
            "Target community to use in import and export";
        }
        leaf import {
          type string;
          description
            "Target community to use when filtering on import";
        }
        leaf export {
          type string;
          description
            "Target community to use when marking routes on export";
        }
      }
      container mac-flush {
        presence "enable mac-flush";
        description
          "Enables mac-flush processing";
        uses apply-advanced;
        leaf any-interface {
          type empty;
          description
            "Send mac-flush when any AC interface goes down";
        }
        leaf any-spoke {
          type empty;
          description
            "Send mac-flush when any spoke pseudo wire goes down";
        }
        leaf propagate {
          type empty;
          description
            "Propagate mac-flush to the core";
        }
      }
      list neighbor {
        key "name";
        ordered-by user;
        description
          "Neighbor belonging to this mesh-group";
        leaf name {
          type jt:ipv4addr;
          description
            "Neighbor ID";
        }
        uses apply-advanced;
        container static {
          presence "enable static";
          description
            "Configuration of static vpls";
          uses apply-advanced;
          leaf incoming-label {
            type union {
              type uint32;
              type string {
                pattern "<.*>|$.*";
              }
            }
            mandatory true;
            description
              "VPLS incoming static label [1000000 - 1048575] or [29696 - 41983]";
          }
          leaf outgoing-label {
            type union {
              type string {
                pattern "<.*>|$.*";
              }
              type uint32 {
                range "16 .. 1048575";
              }
            }
            mandatory true;
            description
              "VPLS outgoing static label";
          }
          choice cword {
            case case_1 {
              leaf control-word {
                type empty;
                description
                  "Adds control-word to the Layer 2 encapsulation";
              }
            }
            case case_2 {
              leaf no-control-word {
                type empty;
                description
                  "Disables control-word to the Layer 2 encapsulation";
              }
            }
          }
        }
        leaf psn-tunnel-endpoint {
          type jt:ipv4addr;
          description
            "Endpoint of the transport tunnel on the remote PE";
        }
        leaf community {
          type string;
          description
            "Community associated with this neighbor";
        }
        leaf encapsulation-type {
          type enumeration {
            enum "ethernet-vlan" {
              description
                "Ethernet VLAN encapsulation";
            }
            enum "ethernet" {
              description
                "Ethernet encapsulation";
            }
          }
          description
            "Encapsulation type for VPN";
        }
        leaf ignore-encapsulation-mismatch {
          type empty;
          description
            "Allow different encapsulation types on local and remote end";
        }
        container pseudowire-status-tlv {
          presence "enable pseudowire-status-tlv";
          description
            "Send pseudowire status TLV";
          uses apply-advanced;
          leaf hot-standby-vc-on {
            type empty;
            description
              "Activate pseudowire upon arrival of 'hot-standby' status TLV message";
          }
        }
        leaf switchover-delay {
          type union {
            type string {
              pattern "<.*>|$.*";
            }
            type uint32 {
              range "0 .. 180000";
            }
          }
          units "milliseconds";
          default "10000";
          description
            "Pseudowire switchover delay ";
        }
        container revert-time {
          presence "enable revert-time";
          description
            "Enable pseudowire redundancy reversion (seconds)";
          leaf delay {
            type union {
              type string {
                pattern "<.*>|$.*";
              }
              type uint32 {
                range "0 .. 3600";
              }
            }
            units "seconds";
            mandatory true;
            description
              "Reversion timer (seconds)";
          }
          leaf maximum {
            type union {
              type string {
                pattern "<.*>|$.*";
              }
              type uint32 {
                range "0 .. 7200";
              }
            }
            units "seconds";
            description
              "Maximum reversion interval to add over revert-time delay";
          }
        }
        leaf connection-protection {
          type empty;
          description
            "End-2-end protection via OAM failure detection";
        }
        list backup-neighbor {
          key "name";
          ordered-by user;
          description
            "Configuration of redundant l2circuit";
          leaf name {
            type jt:ipv4addr;
            description
              "Neighbor ID";
          }
          uses apply-advanced;
          container static {
            presence "enable static";
            description
              "Configuration of static vpls";
            uses apply-advanced;
            leaf incoming-label {
              type union {
                type uint32;
                type string {
                  pattern "<.*>|$.*";
                }
              }
              mandatory true;
              description
                "VPLS incoming static label [1000000 - 1048575] or [29696 - 41983]";
            }
            leaf outgoing-label {
              type union {
                type string {
                  pattern "<.*>|$.*";
                }
                type uint32 {
                  range "16 .. 1048575";
                }
              }
              mandatory true;
              description
                "VPLS outgoing static label";
            }
          }
          leaf community {
            type string;
            description
              "Community associated with this Layer 2 circuit";
          }
          leaf psn-tunnel-endpoint {
            type jt:ipv4addr;
            description
              "Endpoint of the transport tunnel on the remote PE";
          }
          leaf standby {
            type empty;
            description
              "Keep backup pseudowire in continuous standby";
          }
          leaf hot-standby {
            type empty;
            description
              "Keep backup pseudowire in continuous standby mode and ready for traffic forwarding";
          }
        }
        leaf-list vpls-id-list {
          type union {
            type string {
              pattern "<.*>|$.*";
            }
            type uint32 {
              range "1 .. 4294967295";
            }
          }
          ordered-by user;
          description
            "LDP VPLS Identifier list for this neighbor";
        }
      }
      container route-distinguisher {
        description
          "Route distinguisher for this mesh-group";
        leaf rd-type {
          type string;
          description
            "Number in (16 bit:32 bit) or (32 bit 'L':16 bit) or (IP address:16 bit) format";
        }
      }
    }
    leaf connectivity-type {
      type enumeration {
        enum "ce" {
          description
            "CE interface is required";
        }
        enum "irb" {
          description
            "IRB interface is sufficient";
        }
        enum "permanent" {
          description
            "Pseudowire permanently up";
        }
      }
      description
        "Specify type of interface sufficient to bring vpls connection up";
    }
    list import-labeled-routes {
      key "name";
      ordered-by user;
      description
        "Import ingress label route to instance.mpls.0 from mpls.0";
      leaf name {
        type string;
        description
          "Routing instance name where label route has to be imported";
      }
    }
    container multi-homing {
      description
        "Multi-homing configuration for FEC129 VPLS";
      uses apply-advanced;
      leaf peer-active {
        type empty;
        description
          "Keep CE interfaces in up state when all BGP peers go down";
      }
      list site {
        key "name";
        description
          "Sites connected to this provider equipment";
        leaf name {
          type string;
          description
            "Name of Layer 2 VPN or VPLS site";
        }
        uses apply-advanced;
        leaf identifier {
          type union {
            type string {
              pattern "<.*>|$.*";
            }
            type uint16 {
              range "1 .. 65534";
            }
          }
          description
            "Layer 2 VPN or VPLS multi-homing identifier";
        }
        leaf preference {
          type string;
          description
            "Layer 2 VPN or VPLS multi-homing preference";
        }
        container active-interface {
          description
            "Configure interface to designate as active";
          uses apply-advanced;
          choice interface_name {
            case case_1 {
              leaf any {
                type empty;
                description
                  "One configured interface is designated active at random";
              }
            }
            case case_2 {
              leaf primary {
                type union {
                  type jt:interface-name;
                  type string {
                    pattern "<.*>|$.*";
                  }
                }
                description
                  "Interface to designate as active if it is operational";
              }
            }
          }
        }
        list interface {
          key "name";
          ordered-by user;
          description
            "Interface that connects this site to the VPN";
          leaf name {
            type union {
              type jt:interface-name;
              type string {
                pattern "<.*>|$.*";
              }
            }
            description
              "Interface name";
          }
          uses apply-advanced;
          leaf preference {
            type union {
              type string {
                pattern "<.*>|$.*";
              }
              type uint16 {
                range "1 .. 65535";
              }
            }
            description
              "Layer 2 VPN or VPLS multi-homing preference for the interface";
          }
        }
        leaf peer-active {
          type empty;
          description
            "Keep CE interfaces in up state when all BGP peers go down";
        }
      }
    }
    leaf service-type {
      type enumeration {
        enum "single" {
          description
            "Only one service for the virtual-switch";
        }
      }
      description
        "Specify service type for vpls";
    }
  }

  grouping juniper-ri-protocols-bfd {
    uses apply-advanced;
    container sbfd {
      description
        "Seamless BFD parameters";
      uses apply-advanced;
      leaf-list pool {
        type union {
          type uint32;
          type string {
            pattern "<.*>|$.*";
          }
        }
        description
          "List of seamless BFD endpoints";
      }
      list local-discriminator {
        key "name";
        ordered-by user;
        description
          "Local discriminator for seamless BFD responder";
        leaf name {
          type union {
            type string {
              pattern "<.*>|$.*";
            }
            type uint32 {
              range "1 .. 4294967295";
            }
          }
          description
            "Local discriminator for seamless BFD responder";
        }
        uses apply-advanced;
        leaf minimum-receive-interval {
          type union {
            type string {
              pattern "<.*>|$.*";
            }
            type uint32 {
              range "10 .. 255000";
            }
          }
          units "milliseconds";
          description
            "Minimum receive interval for seamless BFD responder";
        }
        leaf local-ip-address {
          type jt:ipv4addr;
          description
            "IPv4 source address";
        }
        leaf local-ipv6-address {
          type jt:ipv6addr;
          description
            "IPv6 source address";
        }
      }
      list local-discriminator-ip {
        key "name";
        ordered-by user;
        description
          "Local discriminator IP address for sBFD responder";
        leaf name {
          type jt:ipv4addr;
          description
            "Local discriminator IP address for sBFD responder";
        }
        uses apply-advanced;
        leaf minimum-receive-interval {
          type union {
            type string {
              pattern "<.*>|$.*";
            }
            type uint32 {
              range "10 .. 255000";
            }
          }
          units "milliseconds";
          description
            "Minimum receive interval for seamless BFD responder";
        }
        leaf local-ip-address {
          type jt:ipv4addr;
          description
            "IPv4 source address";
        }
      }
    }
  }

  grouping juniper-routing-options {
    uses apply-advanced;
    list flex-algorithm {
      key "name";
      description
        "Configure flex-algorithms supported by this node.";
      leaf name {
        type union {
          type string {
            pattern "<.*>|$.*";
          }
          type uint32 {
            range "128 .. 255";
          }
        }
        description
          "Algorithm id";
      }
      uses apply-advanced;
      container definition {
        description
          "Configure flex-algorithm definition.";
        uses apply-advanced;
        leaf metric-type {
          type enumeration {
            enum "igp-metric" {
              description
                "Metric configured to be used for IGP";
            }
            enum "te-metric" {
              description
                "Traffic-engineering metric";
            }
            enum "delay-metric" {
              description
                "Min unidirectional link delay metric";
            }
          }
        }
        choice calculation-type {
          case case_1 {
            leaf spf {
              type empty;
              description
                "Normal SPF of type 0";
            }
          }
          case case_2 {
            leaf strict-spf {
              type empty;
              description
                "Strict SPF";
            }
          }
        }
        leaf use-flex-algorithm-prefix-metric {
          type empty;
          description
            "Set M flag in the flex-algorithm definition flags";
        }
        leaf priority {
          type union {
            type string {
              pattern "<.*>|$.*";
            }
            type uint32 {
              range "0 .. 255";
            }
          }
          description
            "Priority of the flex-algorithm advertisement.";
        }
        leaf-list exclude-srlg {
          type string;
          max-elements 16;
          ordered-by user;
          description
            "SRLG Name";
        }
        container admin-group {
          description
            "Administrative group policy";
          uses admin_group_include_exclude;
        }
      }
      leaf color {
        type union {
          type uint32;
          type string {
            pattern "<.*>|$.*";
          }
        }
        description
          "Color to be associated with this flex-algorithm";
      }
      container use-transport-class {
        presence "enable use-transport-class";
        description
          "Install ingress routes via transport class RIBs";
        uses apply-advanced;
        leaf inet3-install {
          type empty;
          description
            "Install flex-algo routes in inet{6}.3 table";
        }
      }
    }
    container source-packet-routing {
      description
        "Source packet routing (SPRING)";
      uses apply-advanced;
      list mapping-server-entry {
        key "name";
        ordered-by user;
        description
          "Mapping server entry";
        leaf name {
          type string {
            length "1 .. 64";
          }
          description
            "Mapping server entry name";
        }
        uses apply-advanced;
        list prefix-segment {
          key "name";
          max-elements 256;
          ordered-by user;
          description
            "Prefix segment";
          leaf name {
            type jt:ipprefix;
            description
              "Prefix segment prefix";
          }
          uses apply-advanced;
          leaf index {
            type union {
              type string {
                pattern "<.*>|$.*";
              }
              type uint32 {
                range "0 .. 199999";
              }
            }
            mandatory true;
            description
              "Prefix segment index";
          }
          leaf attached {
            type empty;
            description
              "Set attached flag in IS-IS mapping server advertisement";
          }
          leaf domain-wide-flooding {
            type empty;
            description
              "Set S-flag in IS-IS mapping server advertisement";
          }
          leaf no-node-segment {
            type empty;
            description
              "Clear node segment flag in mapping server prefix segment";
          }
        }
        list prefix-segment-range {
          key "name";
          max-elements 256;
          ordered-by user;
          description
            "Prefix segment range";
          leaf name {
            type string {
              length "1 .. 64";
            }
            description
              "Prefix segment range name";
          }
          uses apply-advanced;
          leaf start-prefix {
            type jt:ipprefix;
            mandatory true;
            description
              "Start prefix";
          }
          leaf start-index {
            type union {
              type string {
                pattern "<.*>|$.*";
              }
              type uint32 {
                range "0 .. 199999";
              }
            }
            mandatory true;
            description
              "Start index";
          }
          leaf size {
            type union {
              type string {
                pattern "<.*>|$.*";
              }
              type uint32 {
                range "1 .. 1024";
              }
            }
            mandatory true;
            description
              "Size of prefix segment range";
          }
          leaf attached {
            type empty;
            description
              "Set attached flag in IS-IS mapping server advertisement";
          }
          leaf domain-wide-flooding {
            type empty;
            description
              "Set S-flag in IS-IS mapping server advertisement";
          }
          leaf no-node-segment {
            type empty;
            description
              "Clear node segment flag in mapping server prefix segment";
          }
        }
      }
      container srv6 {
        description
          "SRv6 source-packet-routing";
        uses apply-advanced;
        list block {
          key "name";
          ordered-by user;
          description
            "Block configuration options";
          leaf name {
            type string {
              length "1 .. 63";
            }
            description
              "Block name";
          }
          uses apply-advanced;
          leaf address {
            type jt:ipv6prefix-mandatory;
            mandatory true;
            description
              "Block prefix for SRv6";
          }
          container global-micro-sid {
            description
              "Global micro SID block range parameters";
            uses apply-advanced;
            leaf maximum-sids {
              type union {
                type string {
                  pattern "<.*>|$.*";
                }
                type uint32 {
                  range "0 .. 65536";
                }
              }
              description
                "Maximum number of SIDs used for global block";
            }
            leaf maximum-static-sids {
              type union {
                type string {
                  pattern "<.*>|$.*";
                }
                type uint32 {
                  range "0 .. 65536";
                }
              }
              description
                "Maximum number of static SIDs used for global block";
            }
          }
          container local-micro-sid {
            description
              "Local micro SID block range parameters";
            uses apply-advanced;
            leaf maximum-static-sids {
              type union {
                type string {
                  pattern "<.*>|$.*";
                }
                type uint32 {
                  range "0 .. 65536";
                }
              }
              description
                "Maximum number of static SIDs used for local block";
            }
          }
        }
        list locator {
          key "name";
          ordered-by user;
          leaf name {
            type string {
              length "1 .. 64";
            }
            description
              "Locator entry name";
          }
          uses apply-advanced;
          leaf algorithm {
            type union {
              type string {
                pattern "<.*>|$.*";
              }
              type uint32 {
                range "0 .. 255";
              }
            }
            description
              "Algorithm associated with this locator";
          }
          leaf address {
            type jt:ipv6prefix;
            mandatory true;
            description
              "Configure Locator Service for SRv6";
          }
          leaf block-length {
            type union {
              type string {
                pattern "<.*>|$.*";
              }
              type uint32 {
                range "0 .. 112";
              }
            }
            description
              "Block length associated with this locator";
          }
          leaf function-length {
            type union {
              type string {
                pattern "<.*>|$.*";
              }
              type uint32 {
                range "16 .. 32";
              }
            }
            description
              "Function length associated with this locator";
          }
          leaf static-function-max-entries {
            type union {
              type string {
                pattern "<.*>|$.*";
              }
              type uint32 {
                range "0 .. 4294967295";
              }
            }
            description
              "Static function maximum entries";
          }
          container micro-sid {
            presence "enable micro-sid";
            description
              "Enable micro SID locator";
            uses apply-advanced;
            leaf block-name {
              type string {
                length "1 .. 63";
              }
              description
                "Block name of micro SID locator";
            }
            container flavor {
              description
                "Flavor of micro SID locator";
              uses apply-advanced;
              leaf psp {
                type empty;
                description
                  "Penultimate segment pop of the SRH";
              }
              leaf usp {
                type empty;
                description
                  "Ultimate segment pop of the SRH";
              }
              leaf usd {
                type empty;
                description
                  "Ultimate segment decapsulation";
              }
              leaf none {
                type empty;
                description
                  "No flavor";
              }
            }
            leaf anycast {
              type empty;
              description
                "Anycast locator";
            }
          }
        }
        container traceoptions {
          presence "enable traceoptions";
          description
            "Trace options for SRv6 process";
          uses apply-advanced;
          leaf no-remote-trace {
            type empty;
            description
              "Disable remote tracing";
          }
          container file {
            description
              "Trace file information";
            leaf filename {
              type string {
                length "1 .. 1024";
              }
              description
                "Name of file in which to write trace information";
            }
            leaf size {
              type string;
              description
                "Maximum trace file size";
            }
            leaf files {
              type union {
                type string {
                  pattern "<.*>|$.*";
                }
                type uint32 {
                  range "2 .. 1000";
                }
              }
              default "3";
              description
                "Maximum number of trace files";
            }
            choice world-readable-choice {
              leaf world-readable {
                type empty;
                description
                  "Allow any user to read the log file";
              }
              leaf no-world-readable {
                type empty;
                description
                  "Don't allow any user to read the log file";
              }
            }
            leaf match {
              type jt:regular-expression;
              description
                "Regular expression for lines to be logged";
            }
          }
          list flag {
            key "name";
            ordered-by user;
            description
              "Tracing parameters";
            leaf name {
              type enumeration {
                enum "srv6-oam-recv" {
                  description
                    "Trace recv activity";
                }
                enum "srv6-oam-err" {
                  description
                    "Trace error activity";
                }
              }
            }
          }
        }
      }
    }
    leaf route-distinguisher-id {
      type jt:ipv4addr;
      description
        "Identifier used in route distinguishers for routing instances";
    }
    list domain-path-id {
      key "name";
      max-elements 2;
      ordered-by user;
      description
        "VRF domain id path configuration";
      uses domain-id-type;
    }
    list rib {
      key "name";
      description
        "Routing table options";
      leaf name {
        type string;
        description
          "Routing table name";
      }
      uses apply-advanced;
      container static {
        description
          "Static routes";
        uses apply-advanced;
        leaf rib-group {
          type string;
          description
            "Routing table group";
        }
        container defaults {
          description
            "Global route options";
          uses apply-advanced;
          choice retain-choice {
            leaf retain {
              type empty;
              description
                "Always keep route in forwarding table";
            }
            leaf no-retain {
              type empty;
              description
                "Don't always keep route in forwarding table";
            }
          }
          choice install-choice {
            leaf install {
              type empty;
              description
                "Install route into forwarding table";
            }
            leaf no-install {
              type empty;
              description
                "Don't install route into forwarding table";
            }
          }
          choice readvertise-choice {
            leaf readvertise {
              type empty;
              description
                "Mark route as eligible to be readvertised";
            }
            leaf no-readvertise {
              type empty;
              description
                "Don't mark route as eligible to be readvertised";
            }
          }
          choice resolve-choice {
            leaf resolve {
              type empty;
              description
                "Allow resolution of indirectly connected next hops";
            }
            leaf no-resolve {
              type empty;
              description
                "Don't allow resolution of indirectly connected next hops";
            }
          }
          leaf explicit-null {
            type empty;
            description
              "Allows service label to be popped and will lookup nexthop-table inet6.0";
          }
          choice longest-match-choice {
            leaf longest-match {
              type empty;
              description
                "Always use longest prefix match to resolve next hops";
            }
            leaf no-longest-match {
              type empty;
              description
                "Don't always use longest prefix match to resolve next hops";
            }
          }
          choice passive_flag {
            case case_1 {
              leaf active {
                type empty;
                description
                  "Remove inactive route from forwarding table";
              }
            }
            case case_2 {
              leaf passive {
                type empty;
                description
                  "Retain inactive route in forwarding table";
              }
            }
          }
          container metric {
            presence "enable metric";
            description
              "Metric value";
            uses rib_static_metric_type;
          }
          container metric2 {
            presence "enable metric2";
            description
              "Metric value 2";
            uses rib_static_metric_type;
          }
          container metric3 {
            presence "enable metric3";
            description
              "Metric value 3";
            uses rib_static_metric_type;
          }
          container metric4 {
            presence "enable metric4";
            description
              "Metric value 4";
            uses rib_static_metric_type;
          }
          container tag {
            presence "enable tag";
            description
              "Tag string";
            uses rib_static_metric_type;
          }
          container tag2 {
            presence "enable tag2";
            description
              "Tag string 2";
            uses rib_static_metric_type;
          }
          container preference {
            presence "enable preference";
            description
              "Preference value";
            uses rib_static_metric_type;
          }
          container preference2 {
            presence "enable preference2";
            description
              "Preference value 2";
            uses rib_static_metric_type;
          }
          container color {
            presence "enable color";
            description
              "Color (preference) value";
            uses rib_static_metric_type;
          }
          container color2 {
            presence "enable color2";
            description
              "Color (preference) value 2";
            uses rib_static_metric_type;
          }
          leaf-list community {
            type jt:community;
            ordered-by user;
            description
              "BGP community identifier";
          }
          container as-path {
            description
              "Autonomous system path";
            uses apply-advanced;
            leaf path {
              type string;
              description
                "Autonomous system path";
            }
            leaf origin {
              type enumeration {
                enum "igp" {
                  description
                    "Path originated in the local IGP";
                }
                enum "egp" {
                  description
                    "Path originated in another AS";
                }
                enum "incomplete" {
                  description
                    "Path was learned by some other means";
                }
              }
            }
            leaf atomic-aggregate {
              type empty;
              description
                "Add ATOMIC_AGGREGATE path attribute to route";
            }
            container aggregator {
              presence "enable aggregator";
              description
                "Add AGGREGATOR path attribute to route";
            }
            leaf as-number {
              type string;
              description
                " Autonomous system number in plain number or 'higher 16bits'.'Lower 16 bits' (asdot notation) format";
            }
            leaf address {
              type jt:ipv4addr;
              description
                "Address of BGP system that formed the route";
            }
          }
        }
        list route {
          key "name";
          description
            "Static route";
          leaf name {
            type jt:ipprefix;
          }
          uses apply-advanced;
          leaf priority {
            type enumeration {
              enum "medium" {
                description
                  "Static route medium priority";
              }
              enum "low" {
                description
                  "Static route low priority";
              }
              enum "high" {
                description
                  "Static route high priority";
              }
            }
            description
              "Static route priority high/medium/low";
          }
          choice next_hop {
            case case_1 {
              leaf-list next-hop {
                type union {
                  type jt:ipaddr-or-interface;
                  type string {
                    pattern "<.*>|$.*";
                  }
                }
                ordered-by user;
                description
                  "Next hop to destination";
              }
            }
            case case_2 {
              leaf reject {
                type empty;
                description
                  "Drop packets to destination; send ICMP unreachables";
              }
            }
            case case_3 {
              leaf discard {
                type empty;
                description
                  "Drop packets to destination; send no ICMP unreachables";
              }
            }
            case case_4 {
              leaf receive {
                type empty;
                description
                  "Install a receive route for the destination";
              }
            }
            case case_5 {
              leaf next-table {
                type string;
                description
                  "Next hop to another table";
              }
            }
          }
          leaf description {
            type string;
            description
              "Static route description";
          }
          list qualified-next-hop {
            key "name";
            ordered-by user;
            description
              "Next hop with qualifiers";
            uses qualified_nh_obj;
          }
          leaf backup-pe-group {
            type string;
            description
              "Multicast source redundancy group";
          }
          container bfd-liveness-detection {
            description
              "Bidirectional Forwarding Detection (BFD) options";
            uses apply-advanced;
            leaf version {
              type enumeration {
                enum "0" {
                  description
                    "BFD version 0 (deprecated)";
                }
                enum "1" {
                  description
                    "BFD version 1";
                }
                enum "automatic" {
                  description
                    "Choose BFD version automatically";
                }
              }
              default "automatic";
              description
                "BFD protocol version number";
            }
            leaf minimum-interval {
              type union {
                type string {
                  pattern "<.*>|$.*";
                }
                type uint32 {
                  range "1 .. 255000";
                }
              }
              units "milliseconds";
              description
                "Minimum transmit and receive interval";
            }
            leaf minimum-transmit-interval {
              type union {
                type string {
                  pattern "<.*>|$.*";
                }
                type uint32 {
                  range "1 .. 255000";
                }
              }
              units "milliseconds";
              status deprecated;
              description
                "Minimum transmit interval";
            }
            leaf minimum-receive-interval {
              type union {
                type string {
                  pattern "<.*>|$.*";
                }
                type uint32 {
                  range "1 .. 255000";
                }
              }
              units "milliseconds";
              description
                "Minimum receive interval";
            }
            leaf multiplier {
              type union {
                type string {
                  pattern "<.*>|$.*";
                }
                type uint32 {
                  range "1 .. 255";
                }
              }
              default "3";
              description
                "Detection time multiplier";
            }
            leaf inline-disable {
              type empty;
              description
                "Disable inline mode for this BFD session";
            }
            leaf pdu-size {
              type union {
                type string {
                  pattern "<.*>|$.*";
                }
                type uint32 {
                  range "24 .. 16000";
                }
              }
              default "24";
              description
                "BFD transport protocol payload size";
            }
            choice adaptation-choice {
              case case_1 {
                leaf no-adaptation {
                  type empty;
                  description
                    "Disable adaptation";
                }
              }
            }
            container transmit-interval {
              description
                "Transmit-interval options";
              uses apply-advanced;
              leaf minimum-interval {
                type union {
                  type string {
                    pattern "<.*>|$.*";
                  }
                  type uint32 {
                    range "1 .. 255000";
                  }
                }
                units "milliseconds";
                description
                  "Minimum transmit interval";
              }
              leaf threshold {
                type union {
                  type uint32;
                  type string {
                    pattern "<.*>|$.*";
                  }
                }
                units "milliseconds";
                description
                  "High transmit interval triggering a trap";
              }
            }
            container detection-time {
              description
                "Detection-time options";
              uses apply-advanced;
              leaf threshold {
                type union {
                  type uint32;
                  type string {
                    pattern "<.*>|$.*";
                  }
                }
                units "milliseconds";
                description
                  "High detection-time triggering a trap";
              }
            }
            container authentication {
              description
                "Authentication options";
              uses apply-advanced;
              leaf key-chain {
                type string;
                description
                  "Key chain name";
              }
              leaf algorithm {
                type enumeration {
                  enum "simple-password" {
                    description
                      "Simple password";
                  }
                  enum "keyed-md5" {
                    description
                      "Keyed message Digest 5";
                  }
                  enum "meticulous-keyed-md5" {
                    description
                      "Meticulous keyed message Digest 5";
                  }
                  enum "keyed-sha-1" {
                    description
                      "Keyed secure hash algorithm (SHA1) ";
                  }
                  enum "meticulous-keyed-sha-1" {
                    description
                      "Meticulous keyed secure hash algorithm (SHA1) ";
                  }
                }
                description
                  "Algorithm name";
              }
              leaf loose-check {
                type empty;
                description
                  "Verify authentication only if authentication is negotiated";
              }
            }
            container echo {
              description
                "Echo mode parameters";
              uses apply-advanced;
              leaf minimum-interval {
                type union {
                  type string {
                    pattern "<.*>|$.*";
                  }
                  type uint32 {
                    range "100 .. 255000";
                  }
                }
                units "milliseconds";
                description
                  "Minimum transmit and receive interval";
              }
            }
            container echo-lite {
              description
                "Echo-lite more parameters";
              uses apply-advanced;
              leaf minimum-interval {
                type union {
                  type string {
                    pattern "<.*>|$.*";
                  }
                  type uint32 {
                    range "100 .. 255000";
                  }
                }
                units "milliseconds";
                description
                  "Minimum transmit and receive interval";
              }
            }
            leaf neighbor {
              type jt:ipaddr;
              description
                "BFD neighbor address";
            }
            leaf local-address {
              type jt:ipaddr;
              description
                "BFD local address (for multihop only)";
            }
            leaf holddown-interval {
              type union {
                type string {
                  pattern "<.*>|$.*";
                }
                type uint32 {
                  range "0 .. 255000";
                }
              }
              units "milliseconds";
              description
                "Time to hold the session-UP notification to the client";
            }
            leaf minimum-receive-ttl {
              type union {
                type string {
                  pattern "<.*>|$.*";
                }
                type uint8 {
                  range "1 .. 255";
                }
              }
              description
                "Minimum receive TTL below which to drop";
            }
          }
          choice retain-choice {
            leaf retain {
              type empty;
              description
                "Always keep route in forwarding table";
            }
            leaf no-retain {
              type empty;
              description
                "Don't always keep route in forwarding table";
            }
          }
          choice install-choice {
            leaf install {
              type empty;
              description
                "Install route into forwarding table";
            }
            leaf no-install {
              type empty;
              description
                "Don't install route into forwarding table";
            }
          }
          choice readvertise-choice {
            leaf readvertise {
              type empty;
              description
                "Mark route as eligible to be readvertised";
            }
            leaf no-readvertise {
              type empty;
              description
                "Don't mark route as eligible to be readvertised";
            }
          }
          choice resolve-choice {
            leaf resolve {
              type empty;
              description
                "Allow resolution of indirectly connected next hops";
            }
            leaf no-resolve {
              type empty;
              description
                "Don't allow resolution of indirectly connected next hops";
            }
          }
          leaf explicit-null {
            type empty;
            description
              "Allows service label to be popped and will lookup nexthop-table inet6.0";
          }
          choice longest-match-choice {
            leaf longest-match {
              type empty;
              description
                "Always use longest prefix match to resolve next hops";
            }
            leaf no-longest-match {
              type empty;
              description
                "Don't always use longest prefix match to resolve next hops";
            }
          }
          choice passive_flag {
            case case_1 {
              leaf active {
                type empty;
                description
                  "Remove inactive route from forwarding table";
              }
            }
            case case_2 {
              leaf passive {
                type empty;
                description
                  "Retain inactive route in forwarding table";
              }
            }
          }
          container metric {
            presence "enable metric";
            description
              "Metric value";
            uses rib_static_metric_type;
          }
          container metric2 {
            presence "enable metric2";
            description
              "Metric value 2";
            uses rib_static_metric_type;
          }
          container metric3 {
            presence "enable metric3";
            description
              "Metric value 3";
            uses rib_static_metric_type;
          }
          container metric4 {
            presence "enable metric4";
            description
              "Metric value 4";
            uses rib_static_metric_type;
          }
          container tag {
            presence "enable tag";
            description
              "Tag string";
            uses rib_static_metric_type;
          }
          container tag2 {
            presence "enable tag2";
            description
              "Tag string 2";
            uses rib_static_metric_type;
          }
          container preference {
            presence "enable preference";
            description
              "Preference value";
            uses rib_static_metric_type;
          }
          container preference2 {
            presence "enable preference2";
            description
              "Preference value 2";
            uses rib_static_metric_type;
          }
          container color {
            presence "enable color";
            description
              "Color (preference) value";
            uses rib_static_metric_type;
          }
          container color2 {
            presence "enable color2";
            description
              "Color (preference) value 2";
            uses rib_static_metric_type;
          }
          leaf-list community {
            type jt:community;
            ordered-by user;
            description
              "BGP community identifier";
          }
          container as-path {
            description
              "Autonomous system path";
            uses apply-advanced;
            leaf path {
              type string;
              description
                "Autonomous system path";
            }
            leaf origin {
              type enumeration {
                enum "igp" {
                  description
                    "Path originated in the local IGP";
                }
                enum "egp" {
                  description
                    "Path originated in another AS";
                }
                enum "incomplete" {
                  description
                    "Path was learned by some other means";
                }
              }
            }
            leaf atomic-aggregate {
              type empty;
              description
                "Add ATOMIC_AGGREGATE path attribute to route";
            }
            container aggregator {
              presence "enable aggregator";
              description
                "Add AGGREGATOR path attribute to route";
            }
            leaf as-number {
              type string;
              description
                " Autonomous system number in plain number or 'higher 16bits'.'Lower 16 bits' (asdot notation) format";
            }
            leaf address {
              type jt:ipv4addr;
              description
                "Address of BGP system that formed the route";
            }
          }
          list lsp-next-hop {
            key "name";
            ordered-by user;
            description
              "LSP next hop";
            uses lsp_nh_obj;
          }
          list p2mp-lsp-next-hop {
            key "name";
            max-elements 1;
            ordered-by user;
            description
              "Point-to-multipoint LSP next hop";
            uses lsp_nh_obj;
          }
          container spring-te-lsp-next-hop {
            description
              "SPRING-TE LSP next hop";
            uses springte_lsp_nh_obj;
          }
          container p2mp-ldp-next-hop {
            description
              "Point-to-multipoint LDP LSP next hop";
            uses p2mp_ldp_lsp_nh_obj;
          }
          list static-lsp-next-hop {
            key "name";
            ordered-by user;
            description
              "Static LSP next hop";
            uses lsp_nh_obj;
          }
        }
        leaf protocol-instance-name {
          type string;
          description
            "Name of protocol instance under routing instance";
        }
        container static-route {
          description
            "Static route Status";
          leaf bfd-admin-down {
            type enumeration {
              enum "active" {
                description
                  "Static route will be inactive on bfd-admin-down";
              }
              enum "passive" {
                description
                  "Static route will remain active on bfd-admin-down";
              }
            }
            description
              "Static route State on BFD ADMIN DOWN";
          }
        }
        list route-target-filter {
          key "name";
          ordered-by user;
          description
            "Route-target-filter route";
          leaf name {
            type string {
              length "1 .. 47";
            }
          }
          uses apply-advanced;
          leaf-list neighbor {
            type jt:ipaddr-scoped;
            ordered-by user;
            description
              "BGP peers for filter";
          }
          leaf-list group {
            type string;
            ordered-by user;
            description
              "BGP groups for filter";
          }
          leaf local {
            type empty;
            description
              "Locally originated filter";
          }
        }
      }
      list martians {
        key "address choice-ident choice-value";
        ordered-by user;
        description
          "Invalid routes";
        uses martian_type;
      }
      container aggregate {
        description
          "Coalesced routes";
        uses rib_aggregate_type;
      }
      container generate {
        description
          "Route of last resort";
        uses rib_aggregate_type;
      }
      choice maximum-paths-type {
        case case_1 {
          container maximum-routes {
            status deprecated;
            description
              "Maximum number of routes";
            leaf limit {
              type union {
                type string {
                  pattern "<.*>|$.*";
                }
                type uint32 {
                  range "1 .. 4294967295";
                }
              }
              mandatory true;
              description
                "Maximum number of routes";
            }
            choice log_type {
              case case_1 {
                leaf threshold {
                  type union {
                    type string {
                      pattern "<.*>|$.*";
                    }
                    type uint32 {
                      range "1 .. 100";
                    }
                  }
                  description
                    "Percentage of limit at which to start generating warnings";
                }
              }
              case case_2 {
                leaf log-only {
                  type empty;
                  description
                    "Generate warning messages only";
                }
              }
            }
            leaf log-interval {
              type union {
                type string {
                  pattern "<.*>|$.*";
                }
                type uint32 {
                  range "5 .. 86400";
                }
              }
              units "seconds";
              description
                "Minimum interval between log messages";
            }
          }
        }
        case case_2 {
          container maximum-paths {
            description
              "Maximum number of paths";
            leaf limit {
              type union {
                type string {
                  pattern "<.*>|$.*";
                }
                type uint32 {
                  range "1 .. 4294967295";
                }
              }
              mandatory true;
              description
                "Maximum number of paths";
            }
            choice log_type {
              case case_1 {
                leaf threshold {
                  type union {
                    type string {
                      pattern "<.*>|$.*";
                    }
                    type uint32 {
                      range "1 .. 100";
                    }
                  }
                  description
                    "Percentage of limit at which to start generating warnings";
                }
              }
              case case_2 {
                leaf log-only {
                  type empty;
                  description
                    "Generate warning messages only";
                }
              }
            }
            leaf log-interval {
              type union {
                type string {
                  pattern "<.*>|$.*";
                }
                type uint32 {
                  range "5 .. 86400";
                }
              }
              units "seconds";
              description
                "Minimum interval between log messages";
            }
          }
        }
      }
      container maximum-prefixes {
        description
          "Maximum number of prefixes";
        leaf limit {
          type union {
            type string {
              pattern "<.*>|$.*";
            }
            type uint32 {
              range "1 .. 4294967295";
            }
          }
          mandatory true;
          description
            "Maximum number of prefixes";
        }
        choice log_type {
          case case_1 {
            leaf threshold {
              type union {
                type string {
                  pattern "<.*>|$.*";
                }
                type uint32 {
                  range "1 .. 100";
                }
              }
              description
                "Percentage of limit at which to start generating warnings";
            }
          }
          case case_2 {
            leaf log-only {
              type empty;
              description
                "Generate warning messages only";
            }
          }
        }
        leaf log-interval {
          type union {
            type string {
              pattern "<.*>|$.*";
            }
            type uint32 {
              range "5 .. 86400";
            }
          }
          units "seconds";
          description
            "Minimum interval between log messages";
        }
      }
      container multipath {
        presence "enable multipath";
        description
          "Protocol-independent load balancing";
        uses apply-advanced;
        container vpn-unequal-cost {
          presence "enable vpn-unequal-cost";
          description
            "Include VPN routes with unequal IGP metrics";
          leaf equal-external-internal {
            type empty;
            description
              "Include external and internal VPN routes";
          }
        }
        leaf as-path-compare {
          type empty;
          description
            "Compare AS path sequences in addition to AS path length";
        }
        leaf preserve-nexthop-hierarchy {
          type empty;
          description
            "Force multipath to create List nexthop";
        }
      }
      container policy-multipath {
        description
          "Policy based multipath";
        uses apply-advanced;
        leaf-list policy {
          type jt:policy-algebra;
          ordered-by user;
          description
            "Import policy to create policy based multipath";
        }
        container traceoptions {
          description
            "Trace options";
          uses apply-advanced;
          container file {
            description
              "Trace file options";
            leaf filename {
              type string {
                length "1 .. 1024";
              }
              description
                "Name of file in which to write trace information";
            }
            leaf replace {
              type empty;
              status deprecated;
              description
                "Replace trace file rather than appending to it";
            }
            leaf size {
              type string;
              description
                "Maximum trace file size";
            }
            leaf files {
              type union {
                type string {
                  pattern "<.*>|$.*";
                }
                type uint32 {
                  range "2 .. 1000";
                }
              }
              default "10";
              description
                "Maximum number of trace files";
            }
            leaf no-stamp {
              type empty;
              status deprecated;
              description
                "Do not timestamp trace file";
            }
            choice world-readable-choice {
              leaf world-readable {
                type empty;
                description
                  "Allow any user to read the log file";
              }
              leaf no-world-readable {
                type empty;
                description
                  "Don't allow any user to read the log file";
              }
            }
          }
          list flag {
            key "name";
            ordered-by user;
            description
              "Tracing parameters";
            leaf name {
              type enumeration {
                enum "route" {
                  description
                    "Policy-multipath route tracing.";
                }
              }
            }
            leaf send {
              type empty;
              description
                "Trace transmitted packets";
            }
            leaf receive {
              type empty;
              description
                "Trace received packets";
            }
            leaf detail {
              type empty;
              description
                "Trace detailed information";
            }
            leaf disable {
              type empty;
              description
                "Disable this trace flag";
            }
          }
        }
        leaf preserve-nexthop-hierarchy {
          type empty;
          description
            "Enable preserved nexthop hierarchy";
        }
      }
      container protect {
        description
          "Protocol-independent protection";
        leaf core {
          type empty;
          description
            "Protect against unreachability to service-edge router";
        }
      }
      container access {
        description
          "Access routes";
        uses apply-advanced;
        list route {
          key "name";
          ordered-by user;
          description
            "Access route";
          leaf name {
            type jt:ipprefix;
            description
              "IP address of destination";
          }
          uses apply-advanced;
          leaf-list next-hop {
            type union {
              type jt:ipaddr-or-interface;
              type string {
                pattern "<.*>|$.*";
              }
            }
            ordered-by user;
            description
              "Next hop to destination";
          }
          list qualified-next-hop {
            key "name";
            ordered-by user;
            description
              "Next hop with qualifiers";
            uses qualified_nh_obj;
          }
          leaf metric {
            type union {
              type string {
                pattern "<.*>|$.*";
              }
              type uint32 {
                range "1 .. 255";
              }
            }
            description
              "Metric value";
          }
          leaf preference {
            type union {
              type uint32;
              type string {
                pattern "<.*>|$.*";
              }
            }
            description
              "Preference value";
          }
          leaf tag {
            type union {
              type uint32;
              type string {
                pattern "<.*>|$.*";
              }
            }
            description
              "Tag string";
          }
          leaf tag2 {
            type union {
              type uint32;
              type string {
                pattern "<.*>|$.*";
              }
            }
            description
              "Tag2 string";
          }
        }
      }
      container access-internal {
        description
          "Access-internal routes";
        uses apply-advanced;
        list route {
          key "name";
          ordered-by user;
          description
            "Access-internal route";
          leaf name {
            type jt:ipprefix;
            description
              "IP address and optional prefix length of destination";
          }
          uses apply-advanced;
          leaf-list next-hop {
            type union {
              type jt:ipaddr-or-interface;
              type string {
                pattern "<.*>|$.*";
              }
            }
            ordered-by user;
            description
              "Next hop to destination";
          }
          list qualified-next-hop {
            key "name";
            ordered-by user;
            description
              "Next hop with qualifiers";
            uses qualified_nh_obj;
          }
        }
      }
      container bgp-static {
        description
          "Routes for BGP static advertisements";
        uses apply-advanced;
        list route {
          key "name";
          ordered-by user;
          description
            "BGP-static route";
          leaf name {
            type jt:ipprefix;
            description
              "IP address and optional prefix length of destination";
          }
          uses apply-advanced;
          container metric {
            presence "enable metric";
            description
              "Metric value";
            uses rib_static_metric_type;
          }
          container metric2 {
            presence "enable metric2";
            description
              "Metric value 2";
            uses rib_static_metric_type;
          }
          container metric3 {
            presence "enable metric3";
            description
              "Metric value 3";
            uses rib_static_metric_type;
          }
          container metric4 {
            presence "enable metric4";
            description
              "Metric value 4";
            uses rib_static_metric_type;
          }
          container tag {
            presence "enable tag";
            description
              "Tag string";
            uses rib_static_metric_type;
          }
          container tag2 {
            presence "enable tag2";
            description
              "Tag string 2";
            uses rib_static_metric_type;
          }
          container preference {
            presence "enable preference";
            description
              "Preference value";
            uses rib_static_metric_type;
          }
          container preference2 {
            presence "enable preference2";
            description
              "Preference value 2";
            uses rib_static_metric_type;
          }
          container color {
            presence "enable color";
            description
              "Color (preference) value";
            uses rib_static_metric_type;
          }
          container color2 {
            presence "enable color2";
            description
              "Color (preference) value 2";
            uses rib_static_metric_type;
          }
          leaf-list community {
            type jt:community;
            ordered-by user;
            description
              "BGP community identifier";
          }
          container as-path {
            description
              "Autonomous system path";
            uses apply-advanced;
            leaf path {
              type string;
              description
                "Autonomous system path";
            }
            leaf origin {
              type enumeration {
                enum "igp" {
                  description
                    "Path originated in the local IGP";
                }
                enum "egp" {
                  description
                    "Path originated in another AS";
                }
                enum "incomplete" {
                  description
                    "Path was learned by some other means";
                }
              }
            }
            leaf atomic-aggregate {
              type empty;
              description
                "Add ATOMIC_AGGREGATE path attribute to route";
            }
            container aggregator {
              presence "enable aggregator";
              description
                "Add AGGREGATOR path attribute to route";
            }
            leaf as-number {
              type string;
              description
                " Autonomous system number in plain number or 'higher 16bits'.'Lower 16 bits' (asdot notation) format";
            }
            leaf address {
              type jt:ipv4addr;
              description
                "Address of BGP system that formed the route";
            }
          }
        }
      }
      container flow {
        description
          "Locally defined flow routing information";
        uses apply-advanced;
        container validation {
          presence "enable validation";
          description
            "Flow route validation options";
          uses flow-validation;
        }
        list route {
          key "name";
          ordered-by user;
          description
            "Flow route";
          uses flow-route-inet6;
        }
        list security-group {
          key "name";
          ordered-by user;
          description
            "Security groups";
          leaf name {
            type string {
              length "1 .. 16";
            }
            description
              "Name of the security group";
          }
          uses apply-advanced;
          list rule {
            key "name";
            ordered-by user;
            description
              "Flow route";
            uses flow-rule-inet6;
          }
        }
        container interface-group {
          description
            "Interface-group for applying flow-spec filter";
          uses flow-interface-group;
        }
        leaf discard-action-for-unresolved-redir-addr {
          type empty;
          description
            "For action redirect IP if redirect address is unresolved install discard action filter";
        }
        choice per-route-accounting-choice {
          leaf per-route-accounting {
            type empty;
            description
              "Enable traffic accounting per flowspec route";
          }
          leaf no-per-route-accounting {
            type empty;
            description
              "Don't enable traffic accounting per flowspec route";
          }
        }
      }
      container label {
        presence "enable label";
        description
          "Label processing";
        uses apply-advanced;
        leaf-list allocation {
          type jt:policy-algebra;
          ordered-by user;
          description
            "Label allocation policy";
        }
        leaf-list substitution {
          type jt:policy-algebra;
          ordered-by user;
          description
            "Label substitution policy";
        }
      }
      leaf-list vpn-global-import {
        type jt:policy-algebra;
        ordered-by user;
        description
          "Import policy for L3VPN routes to global RIB";
      }
    }
    container label {
      presence "enable label";
      description
        "Label processing";
      uses apply-advanced;
      leaf-list allocation {
        type jt:policy-algebra;
        ordered-by user;
        description
          "Label allocation policy";
      }
      leaf-list substitution {
        type jt:policy-algebra;
        ordered-by user;
        description
          "Label substitution policy";
      }
    }
    leaf-list vpn-global-import {
      type jt:policy-algebra;
      ordered-by user;
      description
        "Import policy for L3VPN routes to global RIB";
    }
    container options {
      description
        "Miscellaneous options";
      uses apply-advanced;
      leaf no-send {
        type empty;
        status deprecated;
        description
          "Listen only; do not send protocol packets";
      }
      leaf no-resolve {
        type empty;
        status deprecated;
        description
          "Do not use DNS name resolution";
      }
      container syslog {
        description
          "Set system logging level";
        uses apply-advanced;
        container level {
          description
            "Logging level";
          leaf emergency {
            type empty;
            description
              "Emergency level";
          }
          leaf alert {
            type empty;
            description
              "Alert level";
          }
          leaf critical {
            type empty;
            description
              "Critical level";
          }
          leaf error {
            type empty;
            description
              "Error level";
          }
          leaf warning {
            type empty;
            description
              "Warning level";
          }
          leaf notice {
            type empty;
            description
              "Notice level";
          }
          leaf info {
            type empty;
            description
              "Informational level";
          }
          leaf debug {
            type empty;
            description
              "Debugging level";
          }
        }
        leaf upto {
          type enumeration {
            enum "emergency" {
              description
                "Emergency level";
            }
            enum "alert" {
              description
                "Alert level";
            }
            enum "critical" {
              description
                "Critical level";
            }
            enum "error" {
              description
                "Error level";
            }
            enum "warning" {
              description
                "Warning level";
            }
            enum "notice" {
              description
                "Notice level";
            }
            enum "info" {
              description
                "Informational level";
            }
            enum "debug" {
              description
                "Debugging level";
            }
          }
          description
            "Log up to a particular logging level";
        }
      }
      leaf mark {
        type union {
          type int32;
          type string {
            pattern "<.*>|$.*";
          }
        }
        units "seconds";
        description
          "Periodically mark the trace file";
      }
    }
    container resolution {
      presence "enable resolution";
      description
        "Route next-hop resolution options";
      uses apply-advanced;
      leaf-list tracefilter {
        type jt:policy-algebra;
        ordered-by user;
        description
          "Filter policy";
      }
      container traceoptions {
        description
          "Trace options";
        uses apply-advanced;
        container file {
          description
            "Trace file options";
          leaf filename {
            type string {
              length "1 .. 1024";
            }
            description
              "Name of file in which to write trace information";
          }
          leaf replace {
            type empty;
            status deprecated;
            description
              "Replace trace file rather than appending to it";
          }
          leaf size {
            type string;
            description
              "Maximum trace file size";
          }
          leaf files {
            type union {
              type string {
                pattern "<.*>|$.*";
              }
              type uint32 {
                range "2 .. 1000";
              }
            }
            default "10";
            description
              "Maximum number of trace files";
          }
          leaf no-stamp {
            type empty;
            status deprecated;
            description
              "Do not timestamp trace file";
          }
          choice world-readable-choice {
            leaf world-readable {
              type empty;
              description
                "Allow any user to read the log file";
            }
            leaf no-world-readable {
              type empty;
              description
                "Don't allow any user to read the log file";
            }
          }
        }
        list flag {
          key "name";
          ordered-by user;
          description
            "Tracing parameters";
          leaf name {
            type enumeration {
              enum "event" {
                description
                  "Event processing";
              }
              enum "flash" {
                description
                  "Flash processing";
              }
              enum "kernel" {
                description
                  "Kernel communication";
              }
              enum "indirect" {
                description
                  "Indirect next-hop addition, change, or deletion";
              }
              enum "task" {
                description
                  "Task or job processing";
              }
              enum "igp-frr" {
                description
                  "IGP triggered FRR events";
              }
              enum "igp-frr-extensive" {
                description
                  "IGP triggered FRR Extensive events";
              }
              enum "tunnel" {
                description
                  "Resolver dynamic tunnel events";
              }
              enum "all" {
                description
                  "Trace everything";
              }
            }
          }
          leaf send {
            type empty;
            description
              "Trace transmitted packets";
          }
          leaf receive {
            type empty;
            description
              "Trace received packets";
          }
          leaf detail {
            type empty;
            description
              "Trace detailed information";
          }
          leaf disable {
            type empty;
            description
              "Disable this trace flag";
          }
        }
      }
      choice preserve-nexthop-hierarchy-choice {
        leaf preserve-nexthop-hierarchy {
          type empty;
          description
            "Preserve nexthop hierarchy when installing nexthop to forwarding plane";
        }
        leaf no-preserve-nexthop-hierarchy {
          type empty;
          description
            "Don't preserve nexthop hierarchy when installing nexthop to forwarding plane";
        }
      }
      list rib {
        key "name";
        ordered-by user;
        description
          "Routing table resolution options";
        leaf name {
          type string;
          description
            "Routing table name";
        }
        uses apply-advanced;
        leaf-list resolution-family {
          type string;
          ordered-by user;
          description
            "Family of resultion tree";
        }
        leaf-list resolution-ribs {
          type string;
          ordered-by user;
          description
            "Routing tables to use for default routing table family resolution";
        }
        leaf-list inet-resolution-ribs {
          type string;
          ordered-by user;
          description
            "Routing tables to use for ipv4 family protocol-next-hop resolution";
        }
        leaf-list inet6-resolution-ribs {
          type string;
          ordered-by user;
          description
            "Routing tables to use for ipv6 family protocol-next-hop resolution";
        }
        leaf-list iso-resolution-ribs {
          type string;
          ordered-by user;
          description
            "Routing tables to use for iso family protocol-next-hop resolution";
        }
        leaf-list import {
          type jt:policy-algebra;
          ordered-by user;
          description
            "Import policy";
        }
        leaf-list inet-import {
          type jt:policy-algebra;
          ordered-by user;
          description
            "Import policy for IPV4 family resolution tree";
        }
        leaf-list inet6-import {
          type jt:policy-algebra;
          ordered-by user;
          description
            "Import policy for IPV6 family resolution tree";
        }
        leaf-list iso-import {
          type jt:policy-algebra;
          ordered-by user;
          description
            "Import policy for ISO family resolution tree";
        }
        leaf-list inetcolor-import {
          type jt:policy-algebra;
          ordered-by user;
          description
            "Import policy for INETCOLOR family resolution tree";
        }
        leaf-list inet6color-import {
          type jt:policy-algebra;
          ordered-by user;
          description
            "Import policy for INET6COLOR family resolution tree";
        }
        leaf preserve-nexthop-hierarchy {
          type empty;
          description
            "Preserve nexthop hierarchy when installing nexthop to forwarding plane";
        }
      }
      choice prefer-recursive-primary-path-choice {
        leaf prefer-recursive-primary-path {
          type empty;
          description
            "Prefer primary path to resolve nexthop during recursive-resolution";
        }
        leaf no-prefer-recursive-primary-path {
          type empty;
          description
            "Don't prefer primary path to resolve nexthop during recursive-resolution";
        }
      }
      leaf disable-auto-resolve-on-scheme-changes {
        type empty;
        description
          "Manually trigger route re-resolution on Resolution Scheme changes.";
      }
      list scheme {
        key "name";
        ordered-by user;
        description
          "Nexthop resolution fallback";
        leaf name {
          type string;
          description
            "Name the resolution scheme";
        }
        uses apply-advanced;
        leaf-list resolution-ribs {
          type string;
          ordered-by user;
          description
            "Routing tables to use for nexthop resolution, in fallback order";
        }
        leaf mapping-community {
          type string;
          mandatory true;
          description
            "Community on route that maps to this resolution scheme";
        }
      }
    }
    container interface-routes {
      description
        "Define routing table groups for interface routes";
      uses apply-advanced;
      container rib-group {
        description
          "Routing table group";
        uses rib_group_type;
      }
      list family {
        key "name";
        ordered-by user;
        description
          "Address family";
        leaf name {
          type enumeration {
            enum "inet" {
              description
                "IPv4 family";
            }
            enum "inet6" {
              description
                "IPv6 family";
            }
          }
        }
        uses apply-advanced;
        leaf-list import {
          type jt:policy-algebra;
          ordered-by user;
          description
            "Import policy";
        }
        container export {
          description
            "Control exportability of local routes";
          uses apply-advanced;
          leaf point-to-point {
            type empty;
            description
              "Make point-to-point routes exportable";
          }
          leaf lan {
            type empty;
            description
              "Make LAN routes exportable";
          }
        }
      }
    }
    leaf loopback-strict-disable {
      type empty;
      description
        "Completely disable lo0 host prefix when in admin-down state";
    }
    container traceoptions {
      description
        "Global routing protocol trace options";
      uses apply-advanced;
      container file {
        description
          "Trace file options";
        leaf filename {
          type string {
            length "1 .. 1024";
          }
          description
            "Name of file in which to write trace information";
        }
        leaf replace {
          type empty;
          status deprecated;
          description
            "Replace trace file rather than appending to it";
        }
        leaf size {
          type string;
          description
            "Maximum trace file size";
        }
        leaf files {
          type union {
            type string {
              pattern "<.*>|$.*";
            }
            type uint32 {
              range "2 .. 1000";
            }
          }
          default "10";
          description
            "Maximum number of trace files";
        }
        leaf no-stamp {
          type empty;
          status deprecated;
          description
            "Do not timestamp trace file";
        }
        choice world-readable-choice {
          leaf world-readable {
            type empty;
            description
              "Allow any user to read the log file";
          }
          leaf no-world-readable {
            type empty;
            description
              "Don't allow any user to read the log file";
          }
        }
      }
      list flag {
        key "name";
        ordered-by user;
        description
          "Tracing parameters";
        leaf name {
          type enumeration {
            enum "parse" {
              description
                "Trace configuration parsing";
            }
            enum "regex-parse" {
              description
                "Trace regular-expression parsing";
            }
            enum "config-internal" {
              description
                "Trace configuration internals";
            }
            enum "nsr-synchronization" {
              description
                "Trace nonstop routing synchronization events";
            }
            enum "condition-manager" {
              description
                "Trace condition manager events";
            }
            enum "graceful-restart" {
              description
                "Trace Graceful Restart events";
            }
            enum "session" {
              description
                "Trace Session ID allocations/deallocations";
            }
            enum "hfrr-fsm" {
              description
                "Host FRR FSM events tracing";
            }
            enum "hfrr-route" {
              description
                "Host FRR route events tracing";
            }
            enum "statistics-id-group" {
              description
                "Trace Statistics ID Group operations";
            }
            enum "route-record" {
              description
                "Trace route-record server-side events";
            }
            enum "jvision-lsp" {
              description
                "Trace Jvision events and errors";
            }
            enum "dyn-nh-template" {
              description
                "Dynamic nexthops template events tracing";
            }
            enum "read-route" {
              description
                "Read route events tracing";
            }
            enum "events" {
              description
                "Trace-events events tracing";
            }
            enum "route" {
              description
                "Trace routing information";
            }
            enum "normal" {
              description
                "Trace normal events";
            }
            enum "general" {
              description
                "Trace general events";
            }
            enum "state" {
              description
                "Trace state transitions";
            }
            enum "policy" {
              description
                "Trace policy processing";
            }
            enum "task" {
              description
                "Trace routing protocol task processing";
            }
            enum "timer" {
              description
                "Trace routing protocol timer processing";
            }
            enum "all" {
              description
                "Trace everything";
            }
          }
        }
        leaf disable {
          type empty;
          description
            "Disable this trace flag";
        }
      }
    }
    container topologies {
      description
        "Define routing topologies";
      uses apply-advanced;
      list family {
        key "name";
        ordered-by user;
        description
          "Address family";
        leaf name {
          type enumeration {
            enum "inet" {
              description
                "IPv4 family";
            }
            enum "inet6" {
              description
                "IPv6 family";
            }
          }
        }
        uses apply-advanced;
        list topology {
          key "name";
          ordered-by user;
          description
            "Topology information";
          leaf name {
            type string;
            description
              "Topology name";
          }
          uses apply-advanced;
          leaf table-id {
            type union {
              type uint16;
              type string {
                pattern "<.*>|$.*";
              }
            }
            description
              "Table-id";
          }
        }
      }
    }
    leaf router-id {
      type jt:ipv4addr;
      description
        "Router identifier";
    }
    leaf route-distinguisher-id-use-router-id {
      type empty;
      description
        "Use Master instance Router-ID as route-distinguisher-id";
    }
    container autonomous-system {
      description
        "Autonomous system number";
      uses apply-advanced;
      leaf as-number {
        type string;
        description
          " Autonomous system number in plain number or 'higher 16bits'.'Lower 16 bits' (asdot notation) format";
      }
      leaf loops {
        type union {
          type string {
            pattern "<.*>|$.*";
          }
          type int32 {
            range "1 .. 10";
          }
        }
        description
          "Maximum number of times this AS can be in an AS path";
      }
      leaf asdot-notation {
        type empty;
        description
          "Use AS-Dot notation to display true 4 byte AS numbers";
      }
      container independent-domain {
        presence "enable independent-domain";
        description
          "Independent autonomous-system domain from master instance";
        uses apply-advanced;
        container no-attrset {
          presence "enable no-attrset";
          description
            "Do not tunnel ce bgp attributes across provider network";
        }
      }
    }
    container confederation {
      description
        "Confederation autonomous system number";
      leaf confederation-as {
        type string;
        description
          " Autonomous system number in plain number or 'higher 16bits'.'Lower 16 bits' (asdot notation) format";
      }
      leaf-list members {
        type string;
        ordered-by user;
        description
          " Autonomous system number in plain number or 'higher 16bits'.'Lower 16 bits' (asdot notation) format";
      }
    }
    leaf ipv6-router-id {
      type string;
      description
        "IPv6 router identifier";
    }
    container graceful-restart {
      presence "enable graceful-restart";
      description
        "Graceful or hitless routing restart options";
      uses apply-advanced;
      choice enable-disable {
        case case_1 {
          leaf disable {
            type empty;
            description
              "Disable graceful restart";
          }
        }
      }
      leaf restart-duration {
        type union {
          type string {
            pattern "<.*>|$.*";
          }
          type uint32 {
            range "120 .. 10000";
          }
        }
        description
          "Maximum time for which router is in graceful restart";
      }
    }
    container flow {
      description
        "Locally defined flow routing information";
      uses apply-advanced;
      leaf firewall-install-disable {
        type empty;
        description
          "Disable installing flowspec firewall filters in dfwd ";
      }
      choice per-route-accounting-choice {
        leaf per-route-accounting {
          type empty;
          description
            "Enable traffic accounting per flowspec route";
        }
        leaf no-per-route-accounting {
          type empty;
          description
            "Don't enable traffic accounting per flowspec route";
        }
      }
      container validation {
        presence "enable validation";
        description
          "Flow route validation options";
        uses flow-validation;
      }
      container interface-group {
        description
          "Interface-group for applying flow-spec filter";
        uses flow-interface-group;
      }
      list route {
        key "name";
        ordered-by user;
        description
          "Flow route";
        uses flow-route-inet;
      }
      leaf term-order {
        type enumeration {
          enum "legacy" {
            description
              "Legacy term order (default)";
          }
          enum "standard" {
            description
              "RFC compliant term order";
          }
        }
        description
          "Term evaluation order for flow routes";
      }
      leaf discard-action-for-unresolved-redir-addr {
        type empty;
        description
          "For action redirect IP if redirect address is unresolved install discard action filter";
      }
      list security-group {
        key "name";
        ordered-by user;
        description
          "Security groups";
        leaf name {
          type string {
            length "1 .. 16";
          }
          description
            "Name of the security group";
        }
        uses apply-advanced;
        list rule {
          key "name";
          ordered-by user;
          description
            "Flow route";
          uses flow-rule-inet;
        }
      }
    }
    leaf no-soft-core {
      type empty;
      description
        "Disable soft assert to generate core and just log the event";
    }
    leaf med-igp-update-interval {
      type union {
        type string {
          pattern "<.*>|$.*";
        }
        type uint32 {
          range "10 .. 600";
        }
      }
      description
        "Delay (in minutes) in updating MED IGP for bgp groups with 'delay-med-update' ";
    }
    container bmp {
      presence "enable bmp";
      description
        "BGP Monitoring Protocol (BMP) configuration";
      uses apply-advanced;
      leaf authentication-key {
        type string {
          length "1 .. 126";
        }
        description
          "MD5 authentication key";
      }
      leaf authentication-algorithm {
        type enumeration {
          enum "md5" {
            description
              "Message Digest 5";
          }
          enum "hmac-sha-1-96" {
            description
              "Hash-based Message Authentication Code (SHA1) (96 bits)";
          }
          enum "aes-128-cmac-96" {
            description
              "Cipher-based Message Authentication Code (AES128) (96 bits)";
          }
          enum "ao" {
            description
              "TCP Authentication Option";
          }
        }
        default "hmac-sha-1-96";
        description
          "Authentication algorithm name";
      }
      leaf tcpao-auth-mismatch {
        type enumeration {
          enum "allow-without-tcpao" {
            description
              "Allow the connection establishment without TCP-AO";
          }
        }
        description
          "Continue without TCP-AO if any one TCP endpoint does not have TCP-AO configured";
      }
      leaf authentication-key-chain {
        type string {
          length "1 .. 128";
        }
        description
          "Key chain name";
      }
      container hold-down {
        presence "enable hold-down";
        leaf hold-down-time {
          type union {
            type string {
              pattern "<.*>|$.*";
            }
            type uint32 {
              range "30 .. 65535";
            }
          }
          units "seconds";
          mandatory true;
          description
            "Prevent re-establishment for this time";
        }
        leaf flaps {
          type union {
            type string {
              pattern "<.*>|$.*";
            }
            type uint32 {
              range "2 .. 10";
            }
          }
          mandatory true;
          description
            "Number of flaps before damping";
        }
        leaf period {
          type union {
            type string {
              pattern "<.*>|$.*";
            }
            type uint32 {
              range "30 .. 65535";
            }
          }
          units "seconds";
          mandatory true;
          description
            "Time period for flaps";
        }
      }
      leaf initiation-message {
        type string {
          length "1 .. 255";
        }
        description
          "User string sent with the initiation message";
      }
      leaf local-address {
        type jt:ipaddr;
        description
          "Address of local end of BMP session";
      }
      leaf local-port {
        type union {
          type string {
            pattern "<.*>|$.*";
          }
          type uint32 {
            range "1024 .. 65535";
          }
        }
        description
          "Local port for listening";
      }
      leaf connection-mode {
        type enumeration {
          enum "active" {
            description
              "Initiate the connection";
          }
          enum "passive" {
            description
              "Listen for the connection";
          }
        }
        description
          "Specify active or passive";
      }
      leaf priority {
        type enumeration {
          enum "low" {
            description
              "Lowest priority";
          }
          enum "medium" {
            description
              "Medium priority";
          }
          enum "high" {
            description
              "Highest priority";
          }
        }
        description
          "Relative dispatch priority";
      }
      leaf monitor {
        type enumeration {
          enum "enable" {
            description
              "Enable monitoring of BGP peer(s)";
          }
          enum "disable" {
            description
              "Disable monitoring of BGP peer(s)";
          }
        }
        description
          "Enable/Disable monitoring";
      }
      container route-monitoring {
        description
          "Control route monitoring settings";
        uses apply-advanced;
        leaf none {
          type empty;
          description
            "Do not send route monitoring messages";
        }
        container loc-rib {
          presence "enable loc-rib";
          description
            "Send local-rib route monitoring messages";
          uses apply-advanced;
          leaf-list rib-filter {
            type jt:policy-algebra;
            ordered-by user;
            description
              "Policy for RIB filtering";
          }
          leaf-list route-filter {
            type jt:policy-algebra;
            ordered-by user;
            description
              "Policy for route filtering";
          }
        }
        container pre-policy {
          presence "enable pre-policy";
          description
            "Send pre policy route monitoring messages";
          leaf exclude-non-feasible {
            type empty;
            description
              "Exclude looped routes, etc";
          }
        }
        container post-policy {
          presence "enable post-policy";
          description
            "Send post policy route monitoring messages";
          leaf exclude-non-eligible {
            type empty;
            description
              "Exclude unresolved routes, etc.";
          }
        }
        container rib-out {
          presence "enable rib-out";
          description
            "Send adj-ribs-out route monitoring messages";
          leaf pre-policy {
            type empty;
            description
              "Send pre-policy adj-ribs-out route monitoring messages";
          }
          leaf post-policy {
            type empty;
            description
              "Send post-policy adj-ribs-out route monitoring messages";
          }
        }
      }
      leaf max-loc-rib-buffer-count {
        type union {
          type string {
            pattern "<.*>|$.*";
          }
          type uint32 {
            range "1 .. 50";
          }
        }
        description
          "Max number of loc-rib outstanding buffers before blocking";
      }
      leaf station-address {
        type jt:ipaddr;
        description
          "Address/name of monitoring station";
      }
      leaf routing-instance {
        type string;
        description
          "Routing-instance through which BMP station is reachable";
      }
      leaf station-port {
        type union {
          type string {
            pattern "<.*>|$.*";
          }
          type uint32 {
            range "1 .. 65535";
          }
        }
        description
          "Port of monitoring station";
      }
      leaf statistics-timeout {
        type union {
          type string {
            pattern "<.*>|$.*";
          }
          type uint32 {
            range "0 .. 65535";
          }
        }
        units "seconds";
        description
          "Statistics message timer, 15-65535, or 0 for no messages";
      }
      leaf keep-advertisement-state {
        type empty;
        description
          "Keep BMP advertisement state";
      }
      leaf in-memory-profiling {
        type empty;
        description
          "Turn on in-memory profiling to collect time-series data";
      }
      leaf bmp-server {
        type empty;
        description
          "BMP server";
      }
      leaf max-clients {
        type union {
          type string {
            pattern "<.*>|$.*";
          }
          type uint32 {
            range "1 .. 500";
          }
        }
        description
          "Max number of BMP server clients";
      }
      container traceoptions {
        description
          "Trace options";
        uses apply-advanced;
        container file {
          description
            "Trace file options";
          leaf filename {
            type string {
              length "1 .. 1024";
            }
            description
              "Name of file in which to write trace information";
          }
          leaf replace {
            type empty;
            status deprecated;
            description
              "Replace trace file rather than appending to it";
          }
          leaf size {
            type string;
            description
              "Maximum trace file size";
          }
          leaf files {
            type union {
              type string {
                pattern "<.*>|$.*";
              }
              type uint32 {
                range "2 .. 1000";
              }
            }
            default "10";
            description
              "Maximum number of trace files";
          }
          leaf no-stamp {
            type empty;
            status deprecated;
            description
              "Do not timestamp trace file";
          }
          choice world-readable-choice {
            leaf world-readable {
              type empty;
              description
                "Allow any user to read the log file";
            }
            leaf no-world-readable {
              type empty;
              description
                "Don't allow any user to read the log file";
            }
          }
        }
        list flag {
          key "name";
          ordered-by user;
          description
            "Trace flag information";
          leaf name {
            type enumeration {
              enum "packets" {
                description
                  "Trace all messages";
              }
              enum "up" {
                description
                  "Trace up messages";
              }
              enum "down" {
                description
                  "Trace down messages";
              }
              enum "statistics" {
                description
                  "Trace statistics messages";
              }
              enum "route-monitoring" {
                description
                  "Trace route monitoring messages";
              }
              enum "event" {
                description
                  "Trace major events, station establishment, errors, events";
              }
              enum "error" {
                description
                  "Trace error conditions";
              }
              enum "write" {
                description
                  "Trace writing of messages";
              }
              enum "route" {
                description
                  "Trace routing information";
              }
              enum "normal" {
                description
                  "Trace normal events";
              }
              enum "general" {
                description
                  "Trace general events";
              }
              enum "state" {
                description
                  "Trace state transitions";
              }
              enum "policy" {
                description
                  "Trace policy processing";
              }
              enum "task" {
                description
                  "Trace routing protocol task processing";
              }
              enum "timer" {
                description
                  "Trace routing protocol timer processing";
              }
              enum "all" {
                description
                  "Trace everything";
              }
            }
          }
          leaf send {
            type empty;
            description
              "Trace transmitted packets";
          }
          leaf receive {
            type empty;
            description
              "Trace received packets";
          }
          leaf detail {
            type empty;
            description
              "Trace detailed information";
          }
          leaf disable {
            type empty;
            description
              "Disable this trace flag";
          }
        }
      }
      container bmp-loc-rib-add-path {
        presence "enable bmp-loc-rib-add-path";
        description
          "Advertise multiple paths for a prefix";
        uses bmp-loc-rib-apath-options;
      }
      container kafka {
        presence "enable kafka";
        description
          "Kafka broker configuration";
        uses apply-advanced;
        leaf broker-address {
          type string;
          mandatory true;
          description
            "Kafka broker address";
        }
        container producer {
          presence "enable producer";
          description
            "Producer of a topic";
          uses apply-advanced;
          leaf topic-metadata {
            type string {
              length "1 .. 255";
            }
            description
              "Metadata string for all messages";
          }
        }
      }
      list station {
        key "name";
        description
          "Define a BMP station";
        leaf name {
          type string;
          description
            "Station name";
        }
        uses apply-advanced;
        leaf authentication-key {
          type string {
            length "1 .. 126";
          }
          description
            "MD5 authentication key";
        }
        leaf authentication-algorithm {
          type enumeration {
            enum "md5" {
              description
                "Message Digest 5";
            }
            enum "hmac-sha-1-96" {
              description
                "Hash-based Message Authentication Code (SHA1) (96 bits)";
            }
            enum "aes-128-cmac-96" {
              description
                "Cipher-based Message Authentication Code (AES128) (96 bits)";
            }
            enum "ao" {
              description
                "TCP Authentication Option";
            }
          }
          description
            "Authentication algorithm name";
        }
        leaf tcpao-auth-mismatch {
          type enumeration {
            enum "allow-without-tcpao" {
              description
                "Allow the connection establishment without TCP-AO";
            }
          }
          description
            "Continue without TCP-AO if any one TCP endpoint does not have TCP-AO configured";
        }
        leaf authentication-key-chain {
          type string {
            length "1 .. 128";
          }
          description
            "Key chain name";
        }
        container hold-down {
          presence "enable hold-down";
          leaf hold-down-time {
            type union {
              type string {
                pattern "<.*>|$.*";
              }
              type uint32 {
                range "30 .. 65535";
              }
            }
            units "seconds";
            mandatory true;
            description
              "Prevent re-establishment for this time";
          }
          leaf flaps {
            type union {
              type string {
                pattern "<.*>|$.*";
              }
              type uint32 {
                range "2 .. 10";
              }
            }
            mandatory true;
            description
              "Number of flaps before damping";
          }
          leaf period {
            type union {
              type string {
                pattern "<.*>|$.*";
              }
              type uint32 {
                range "30 .. 65535";
              }
            }
            units "seconds";
            mandatory true;
            description
              "Time period for flaps";
          }
        }
        leaf initiation-message {
          type string {
            length "1 .. 255";
          }
          description
            "User string sent with the initiation message";
        }
        leaf local-address {
          type jt:ipaddr;
          description
            "Address of local end of BMP session";
        }
        leaf local-port {
          type union {
            type string {
              pattern "<.*>|$.*";
            }
            type uint32 {
              range "1024 .. 65535";
            }
          }
          description
            "Local port for listening";
        }
        leaf connection-mode {
          type enumeration {
            enum "active" {
              description
                "Initiate the connection";
            }
            enum "passive" {
              description
                "Listen for the connection";
            }
          }
          description
            "Specify active or passive";
        }
        leaf priority {
          type enumeration {
            enum "low" {
              description
                "Lowest priority";
            }
            enum "medium" {
              description
                "Medium priority";
            }
            enum "high" {
              description
                "Highest priority";
            }
          }
          description
            "Relative dispatch priority";
        }
        leaf monitor {
          type enumeration {
            enum "enable" {
              description
                "Enable monitoring of BGP peer(s)";
            }
            enum "disable" {
              description
                "Disable monitoring of BGP peer(s)";
            }
          }
          description
            "Enable/Disable monitoring";
        }
        container route-monitoring {
          description
            "Control route monitoring settings";
          uses apply-advanced;
          leaf none {
            type empty;
            description
              "Do not send route monitoring messages";
          }
          container loc-rib {
            presence "enable loc-rib";
            description
              "Send local-rib route monitoring messages";
            uses apply-advanced;
            leaf-list rib-filter {
              type jt:policy-algebra;
              ordered-by user;
              description
                "Policy for RIB filtering";
            }
            leaf-list route-filter {
              type jt:policy-algebra;
              ordered-by user;
              description
                "Policy for route filtering";
            }
          }
          container pre-policy {
            presence "enable pre-policy";
            description
              "Send pre policy route monitoring messages";
            leaf exclude-non-feasible {
              type empty;
              description
                "Exclude looped routes, etc";
            }
          }
          container post-policy {
            presence "enable post-policy";
            description
              "Send post policy route monitoring messages";
            leaf exclude-non-eligible {
              type empty;
              description
                "Exclude unresolved routes, etc.";
            }
          }
          container rib-out {
            presence "enable rib-out";
            description
              "Send adj-ribs-out route monitoring messages";
            leaf pre-policy {
              type empty;
              description
                "Send pre-policy adj-ribs-out route monitoring messages";
            }
            leaf post-policy {
              type empty;
              description
                "Send post-policy adj-ribs-out route monitoring messages";
            }
          }
        }
        leaf max-loc-rib-buffer-count {
          type union {
            type string {
              pattern "<.*>|$.*";
            }
            type uint32 {
              range "1 .. 50";
            }
          }
          description
            "Max number of loc-rib outstanding buffers before blocking";
        }
        leaf station-address {
          type jt:ipaddr;
          description
            "Address/name of monitoring station";
        }
        leaf routing-instance {
          type string;
          description
            "Routing-instance through which BMP station is reachable";
        }
        leaf station-port {
          type union {
            type string {
              pattern "<.*>|$.*";
            }
            type uint32 {
              range "1 .. 65535";
            }
          }
          description
            "Port of monitoring station";
        }
        leaf statistics-timeout {
          type union {
            type string {
              pattern "<.*>|$.*";
            }
            type uint32 {
              range "0 .. 65535";
            }
          }
          units "seconds";
          description
            "Statistics message timer, 15-65535, or 0 for no messages";
        }
        leaf keep-advertisement-state {
          type empty;
          description
            "Keep BMP advertisement state";
        }
        leaf in-memory-profiling {
          type empty;
          description
            "Turn on in-memory profiling to collect time-series data";
        }
        leaf bmp-server {
          type empty;
          description
            "BMP server";
        }
        leaf max-clients {
          type union {
            type string {
              pattern "<.*>|$.*";
            }
            type uint32 {
              range "1 .. 500";
            }
          }
          description
            "Max number of BMP server clients";
        }
        container traceoptions {
          description
            "Trace options";
          uses apply-advanced;
          container file {
            description
              "Trace file options";
            leaf filename {
              type string {
                length "1 .. 1024";
              }
              description
                "Name of file in which to write trace information";
            }
            leaf replace {
              type empty;
              status deprecated;
              description
                "Replace trace file rather than appending to it";
            }
            leaf size {
              type string;
              description
                "Maximum trace file size";
            }
            leaf files {
              type union {
                type string {
                  pattern "<.*>|$.*";
                }
                type uint32 {
                  range "2 .. 1000";
                }
              }
              default "10";
              description
                "Maximum number of trace files";
            }
            leaf no-stamp {
              type empty;
              status deprecated;
              description
                "Do not timestamp trace file";
            }
            choice world-readable-choice {
              leaf world-readable {
                type empty;
                description
                  "Allow any user to read the log file";
              }
              leaf no-world-readable {
                type empty;
                description
                  "Don't allow any user to read the log file";
              }
            }
          }
          list flag {
            key "name";
            ordered-by user;
            description
              "Trace flag information";
            leaf name {
              type enumeration {
                enum "packets" {
                  description
                    "Trace all messages";
                }
                enum "up" {
                  description
                    "Trace up messages";
                }
                enum "down" {
                  description
                    "Trace down messages";
                }
                enum "statistics" {
                  description
                    "Trace statistics messages";
                }
                enum "route-monitoring" {
                  description
                    "Trace route monitoring messages";
                }
                enum "event" {
                  description
                    "Trace major events, station establishment, errors, events";
                }
                enum "error" {
                  description
                    "Trace error conditions";
                }
                enum "write" {
                  description
                    "Trace writing of messages";
                }
                enum "route" {
                  description
                    "Trace routing information";
                }
                enum "normal" {
                  description
                    "Trace normal events";
                }
                enum "general" {
                  description
                    "Trace general events";
                }
                enum "state" {
                  description
                    "Trace state transitions";
                }
                enum "policy" {
                  description
                    "Trace policy processing";
                }
                enum "task" {
                  description
                    "Trace routing protocol task processing";
                }
                enum "timer" {
                  description
                    "Trace routing protocol timer processing";
                }
                enum "all" {
                  description
                    "Trace everything";
                }
              }
            }
            leaf send {
              type empty;
              description
                "Trace transmitted packets";
            }
            leaf receive {
              type empty;
              description
                "Trace received packets";
            }
            leaf detail {
              type empty;
              description
                "Trace detailed information";
            }
            leaf disable {
              type empty;
              description
                "Disable this trace flag";
            }
          }
        }
        container bmp-loc-rib-add-path {
          presence "enable bmp-loc-rib-add-path";
          description
            "Advertise multiple paths for a prefix";
          uses bmp-loc-rib-apath-options;
        }
        container kafka {
          presence "enable kafka";
          description
            "Kafka broker configuration";
          uses apply-advanced;
          leaf broker-address {
            type string;
            mandatory true;
            description
              "Kafka broker address";
          }
          container producer {
            presence "enable producer";
            description
              "Producer of a topic";
            uses apply-advanced;
            leaf topic-metadata {
              type string {
                length "1 .. 255";
              }
              description
                "Metadata string for all messages";
            }
          }
        }
      }
    }
    leaf bgp-orf-cisco-mode {
      type empty;
      description
        "Using BGP ORF capability code 130 and Prefix ORF type 128";
    }
    leaf highwatermark-log-interval {
      type union {
        type string {
          pattern "<.*>|$.*";
        }
        type uint32 {
          range "5 .. 1200";
        }
      }
      units "seconds";
      description
        "High watermark log interval (default 30 seconds)";
    }
    leaf time-averaged-watermark-interval {
      type union {
        type string {
          pattern "<.*>|$.*";
        }
        type uint32 {
          range "1 .. 15";
        }
      }
      units "days";
      description
        "For calculating average watermark";
    }
    container ppm {
      presence "enable ppm";
      description
        "Set periodic packet management properties";
      uses apply-advanced;
      leaf delegate-processing {
        type empty;
        status deprecated;
        description
          "Enable distribution of PPM sessions";
      }
      leaf no-delegate-processing {
        type empty;
        description
          "Disable PPM sessions distribution";
      }
      leaf bfd-redirect-rule-delay {
        type union {
          type string {
            pattern "<.*>|$.*";
          }
          type uint32 {
            range "1 .. 120";
          }
        }
        description
          "Time to wait after installing redirect rule for BFD sessions";
      }
      leaf redistribution-timer {
        type union {
          type string {
            pattern "<.*>|$.*";
          }
          type uint32 {
            range "1 .. 120";
          }
        }
        description
          "Time to wait after switchover before starting timers";
      }
    }
    leaf no-bfd-triggered-local-repair {
      type empty;
      description
        "Disable bfd triggered local repair";
    }
    leaf maximum-ecmp {
      type enumeration {
        enum "16" {
          description
            "Maximum 16 ECMP routes";
        }
        enum "32" {
          description
            "Maximum 32 ECMP routes";
        }
        enum "64" {
          description
            "Maximum 64 ECMP routes";
        }
        enum "96" {
          description
            "Maximum 96 ECMP routes";
        }
        enum "128" {
          description
            "Maximum 128 ECMP routes";
        }
        enum "160" {
          description
            "Maximum 160 ECMP routes";
        }
        enum "192" {
          description
            "Maximum 192 ECMP routes";
        }
        enum "224" {
          description
            "Maximum 224 ECMP routes";
        }
        enum "256" {
          description
            "Maximum 256 ECMP routes";
        }
        enum "288" {
          description
            "Maximum 288 ECMP routes";
        }
        enum "320" {
          description
            "Maximum 320 ECMP routes";
        }
        enum "352" {
          description
            "Maximum 352 ECMP routes";
        }
        enum "384" {
          description
            "Maximum 384 ECMP routes";
        }
        enum "416" {
          description
            "Maximum 416 ECMP routes";
        }
        enum "448" {
          description
            "Maximum 448 ECMP routes";
        }
        enum "480" {
          description
            "Maximum 480 ECMP routes";
        }
        enum "512" {
          description
            "Maximum 512 ECMP routes";
        }
      }
      description
        "Maximum ECMP limit for nexthops";
    }
    container static {
      description
        "Static routes";
      uses apply-advanced;
      leaf rib-group {
        type string;
        description
          "Routing table group";
      }
      container defaults {
        description
          "Global route options";
        uses apply-advanced;
        choice retain-choice {
          leaf retain {
            type empty;
            description
              "Always keep route in forwarding table";
          }
          leaf no-retain {
            type empty;
            description
              "Don't always keep route in forwarding table";
          }
        }
        choice install-choice {
          leaf install {
            type empty;
            description
              "Install route into forwarding table";
          }
          leaf no-install {
            type empty;
            description
              "Don't install route into forwarding table";
          }
        }
        choice readvertise-choice {
          leaf readvertise {
            type empty;
            description
              "Mark route as eligible to be readvertised";
          }
          leaf no-readvertise {
            type empty;
            description
              "Don't mark route as eligible to be readvertised";
          }
        }
        choice resolve-choice {
          leaf resolve {
            type empty;
            description
              "Allow resolution of indirectly connected next hops";
          }
          leaf no-resolve {
            type empty;
            description
              "Don't allow resolution of indirectly connected next hops";
          }
        }
        leaf explicit-null {
          type empty;
          description
            "Allows service label to be popped and will lookup nexthop-table inet6.0";
        }
        choice longest-match-choice {
          leaf longest-match {
            type empty;
            description
              "Always use longest prefix match to resolve next hops";
          }
          leaf no-longest-match {
            type empty;
            description
              "Don't always use longest prefix match to resolve next hops";
          }
        }
        choice passive_flag {
          case case_1 {
            leaf active {
              type empty;
              description
                "Remove inactive route from forwarding table";
            }
          }
          case case_2 {
            leaf passive {
              type empty;
              description
                "Retain inactive route in forwarding table";
            }
          }
        }
        container metric {
          presence "enable metric";
          description
            "Metric value";
          uses rib_static_metric_type;
        }
        container metric2 {
          presence "enable metric2";
          description
            "Metric value 2";
          uses rib_static_metric_type;
        }
        container metric3 {
          presence "enable metric3";
          description
            "Metric value 3";
          uses rib_static_metric_type;
        }
        container metric4 {
          presence "enable metric4";
          description
            "Metric value 4";
          uses rib_static_metric_type;
        }
        container tag {
          presence "enable tag";
          description
            "Tag string";
          uses rib_static_metric_type;
        }
        container tag2 {
          presence "enable tag2";
          description
            "Tag string 2";
          uses rib_static_metric_type;
        }
        container preference {
          presence "enable preference";
          description
            "Preference value";
          uses rib_static_metric_type;
        }
        container preference2 {
          presence "enable preference2";
          description
            "Preference value 2";
          uses rib_static_metric_type;
        }
        container color {
          presence "enable color";
          description
            "Color (preference) value";
          uses rib_static_metric_type;
        }
        container color2 {
          presence "enable color2";
          description
            "Color (preference) value 2";
          uses rib_static_metric_type;
        }
        leaf-list community {
          type jt:community;
          ordered-by user;
          description
            "BGP community identifier";
        }
        container as-path {
          description
            "Autonomous system path";
          uses apply-advanced;
          leaf path {
            type string;
            description
              "Autonomous system path";
          }
          leaf origin {
            type enumeration {
              enum "igp" {
                description
                  "Path originated in the local IGP";
              }
              enum "egp" {
                description
                  "Path originated in another AS";
              }
              enum "incomplete" {
                description
                  "Path was learned by some other means";
              }
            }
          }
          leaf atomic-aggregate {
            type empty;
            description
              "Add ATOMIC_AGGREGATE path attribute to route";
          }
          container aggregator {
            presence "enable aggregator";
            description
              "Add AGGREGATOR path attribute to route";
          }
          leaf as-number {
            type string;
            description
              " Autonomous system number in plain number or 'higher 16bits'.'Lower 16 bits' (asdot notation) format";
          }
          leaf address {
            type jt:ipv4addr;
            description
              "Address of BGP system that formed the route";
          }
        }
      }
      list route {
        key "name";
        description
          "Static route";
        leaf name {
          type jt:ipprefix;
        }
        uses apply-advanced;
        leaf priority {
          type enumeration {
            enum "medium" {
              description
                "Static route medium priority";
            }
            enum "low" {
              description
                "Static route low priority";
            }
            enum "high" {
              description
                "Static route high priority";
            }
          }
          description
            "Static route priority high/medium/low";
        }
        choice next_hop {
          case case_1 {
            leaf-list next-hop {
              type union {
                type jt:ipaddr-or-interface;
                type string {
                  pattern "<.*>|$.*";
                }
              }
              ordered-by user;
              description
                "Next hop to destination";
            }
          }
          case case_2 {
            leaf reject {
              type empty;
              description
                "Drop packets to destination; send ICMP unreachables";
            }
          }
          case case_3 {
            leaf discard {
              type empty;
              description
                "Drop packets to destination; send no ICMP unreachables";
            }
          }
          case case_4 {
            leaf receive {
              type empty;
              description
                "Install a receive route for the destination";
            }
          }
          case case_5 {
            leaf next-table {
              type string;
              description
                "Next hop to another table";
            }
          }
        }
        leaf description {
          type string;
          description
            "Static route description";
        }
        list qualified-next-hop {
          key "name";
          ordered-by user;
          description
            "Next hop with qualifiers";
          uses qualified_nh_obj;
        }
        leaf backup-pe-group {
          type string;
          description
            "Multicast source redundancy group";
        }
        container bfd-liveness-detection {
          description
            "Bidirectional Forwarding Detection (BFD) options";
          uses apply-advanced;
          leaf version {
            type enumeration {
              enum "0" {
                description
                  "BFD version 0 (deprecated)";
              }
              enum "1" {
                description
                  "BFD version 1";
              }
              enum "automatic" {
                description
                  "Choose BFD version automatically";
              }
            }
            default "automatic";
            description
              "BFD protocol version number";
          }
          leaf minimum-interval {
            type union {
              type string {
                pattern "<.*>|$.*";
              }
              type uint32 {
                range "1 .. 255000";
              }
            }
            units "milliseconds";
            description
              "Minimum transmit and receive interval";
          }
          leaf minimum-transmit-interval {
            type union {
              type string {
                pattern "<.*>|$.*";
              }
              type uint32 {
                range "1 .. 255000";
              }
            }
            units "milliseconds";
            status deprecated;
            description
              "Minimum transmit interval";
          }
          leaf minimum-receive-interval {
            type union {
              type string {
                pattern "<.*>|$.*";
              }
              type uint32 {
                range "1 .. 255000";
              }
            }
            units "milliseconds";
            description
              "Minimum receive interval";
          }
          leaf multiplier {
            type union {
              type string {
                pattern "<.*>|$.*";
              }
              type uint32 {
                range "1 .. 255";
              }
            }
            default "3";
            description
              "Detection time multiplier";
          }
          leaf inline-disable {
            type empty;
            description
              "Disable inline mode for this BFD session";
          }
          leaf pdu-size {
            type union {
              type string {
                pattern "<.*>|$.*";
              }
              type uint32 {
                range "24 .. 16000";
              }
            }
            default "24";
            description
              "BFD transport protocol payload size";
          }
          choice adaptation-choice {
            case case_1 {
              leaf no-adaptation {
                type empty;
                description
                  "Disable adaptation";
              }
            }
          }
          container transmit-interval {
            description
              "Transmit-interval options";
            uses apply-advanced;
            leaf minimum-interval {
              type union {
                type string {
                  pattern "<.*>|$.*";
                }
                type uint32 {
                  range "1 .. 255000";
                }
              }
              units "milliseconds";
              description
                "Minimum transmit interval";
            }
            leaf threshold {
              type union {
                type uint32;
                type string {
                  pattern "<.*>|$.*";
                }
              }
              units "milliseconds";
              description
                "High transmit interval triggering a trap";
            }
          }
          container detection-time {
            description
              "Detection-time options";
            uses apply-advanced;
            leaf threshold {
              type union {
                type uint32;
                type string {
                  pattern "<.*>|$.*";
                }
              }
              units "milliseconds";
              description
                "High detection-time triggering a trap";
            }
          }
          container authentication {
            description
              "Authentication options";
            uses apply-advanced;
            leaf key-chain {
              type string;
              description
                "Key chain name";
            }
            leaf algorithm {
              type enumeration {
                enum "simple-password" {
                  description
                    "Simple password";
                }
                enum "keyed-md5" {
                  description
                    "Keyed message Digest 5";
                }
                enum "meticulous-keyed-md5" {
                  description
                    "Meticulous keyed message Digest 5";
                }
                enum "keyed-sha-1" {
                  description
                    "Keyed secure hash algorithm (SHA1) ";
                }
                enum "meticulous-keyed-sha-1" {
                  description
                    "Meticulous keyed secure hash algorithm (SHA1) ";
                }
              }
              description
                "Algorithm name";
            }
            leaf loose-check {
              type empty;
              description
                "Verify authentication only if authentication is negotiated";
            }
          }
          container echo {
            description
              "Echo mode parameters";
            uses apply-advanced;
            leaf minimum-interval {
              type union {
                type string {
                  pattern "<.*>|$.*";
                }
                type uint32 {
                  range "100 .. 255000";
                }
              }
              units "milliseconds";
              description
                "Minimum transmit and receive interval";
            }
          }
          container echo-lite {
            description
              "Echo-lite more parameters";
            uses apply-advanced;
            leaf minimum-interval {
              type union {
                type string {
                  pattern "<.*>|$.*";
                }
                type uint32 {
                  range "100 .. 255000";
                }
              }
              units "milliseconds";
              description
                "Minimum transmit and receive interval";
            }
          }
          leaf neighbor {
            type jt:ipaddr;
            description
              "BFD neighbor address";
          }
          leaf local-address {
            type jt:ipaddr;
            description
              "BFD local address (for multihop only)";
          }
          leaf holddown-interval {
            type union {
              type string {
                pattern "<.*>|$.*";
              }
              type uint32 {
                range "0 .. 255000";
              }
            }
            units "milliseconds";
            description
              "Time to hold the session-UP notification to the client";
          }
          leaf minimum-receive-ttl {
            type union {
              type string {
                pattern "<.*>|$.*";
              }
              type uint8 {
                range "1 .. 255";
              }
            }
            description
              "Minimum receive TTL below which to drop";
          }
        }
        choice retain-choice {
          leaf retain {
            type empty;
            description
              "Always keep route in forwarding table";
          }
          leaf no-retain {
            type empty;
            description
              "Don't always keep route in forwarding table";
          }
        }
        choice install-choice {
          leaf install {
            type empty;
            description
              "Install route into forwarding table";
          }
          leaf no-install {
            type empty;
            description
              "Don't install route into forwarding table";
          }
        }
        choice readvertise-choice {
          leaf readvertise {
            type empty;
            description
              "Mark route as eligible to be readvertised";
          }
          leaf no-readvertise {
            type empty;
            description
              "Don't mark route as eligible to be readvertised";
          }
        }
        choice resolve-choice {
          leaf resolve {
            type empty;
            description
              "Allow resolution of indirectly connected next hops";
          }
          leaf no-resolve {
            type empty;
            description
              "Don't allow resolution of indirectly connected next hops";
          }
        }
        leaf explicit-null {
          type empty;
          description
            "Allows service label to be popped and will lookup nexthop-table inet6.0";
        }
        choice longest-match-choice {
          leaf longest-match {
            type empty;
            description
              "Always use longest prefix match to resolve next hops";
          }
          leaf no-longest-match {
            type empty;
            description
              "Don't always use longest prefix match to resolve next hops";
          }
        }
        choice passive_flag {
          case case_1 {
            leaf active {
              type empty;
              description
                "Remove inactive route from forwarding table";
            }
          }
          case case_2 {
            leaf passive {
              type empty;
              description
                "Retain inactive route in forwarding table";
            }
          }
        }
        container metric {
          presence "enable metric";
          description
            "Metric value";
          uses rib_static_metric_type;
        }
        container metric2 {
          presence "enable metric2";
          description
            "Metric value 2";
          uses rib_static_metric_type;
        }
        container metric3 {
          presence "enable metric3";
          description
            "Metric value 3";
          uses rib_static_metric_type;
        }
        container metric4 {
          presence "enable metric4";
          description
            "Metric value 4";
          uses rib_static_metric_type;
        }
        container tag {
          presence "enable tag";
          description
            "Tag string";
          uses rib_static_metric_type;
        }
        container tag2 {
          presence "enable tag2";
          description
            "Tag string 2";
          uses rib_static_metric_type;
        }
        container preference {
          presence "enable preference";
          description
            "Preference value";
          uses rib_static_metric_type;
        }
        container preference2 {
          presence "enable preference2";
          description
            "Preference value 2";
          uses rib_static_metric_type;
        }
        container color {
          presence "enable color";
          description
            "Color (preference) value";
          uses rib_static_metric_type;
        }
        container color2 {
          presence "enable color2";
          description
            "Color (preference) value 2";
          uses rib_static_metric_type;
        }
        leaf-list community {
          type jt:community;
          ordered-by user;
          description
            "BGP community identifier";
        }
        container as-path {
          description
            "Autonomous system path";
          uses apply-advanced;
          leaf path {
            type string;
            description
              "Autonomous system path";
          }
          leaf origin {
            type enumeration {
              enum "igp" {
                description
                  "Path originated in the local IGP";
              }
              enum "egp" {
                description
                  "Path originated in another AS";
              }
              enum "incomplete" {
                description
                  "Path was learned by some other means";
              }
            }
          }
          leaf atomic-aggregate {
            type empty;
            description
              "Add ATOMIC_AGGREGATE path attribute to route";
          }
          container aggregator {
            presence "enable aggregator";
            description
              "Add AGGREGATOR path attribute to route";
          }
          leaf as-number {
            type string;
            description
              " Autonomous system number in plain number or 'higher 16bits'.'Lower 16 bits' (asdot notation) format";
          }
          leaf address {
            type jt:ipv4addr;
            description
              "Address of BGP system that formed the route";
          }
        }
        list lsp-next-hop {
          key "name";
          ordered-by user;
          description
            "LSP next hop";
          uses lsp_nh_obj;
        }
        list p2mp-lsp-next-hop {
          key "name";
          max-elements 1;
          ordered-by user;
          description
            "Point-to-multipoint LSP next hop";
          uses lsp_nh_obj;
        }
        container spring-te-lsp-next-hop {
          description
            "SPRING-TE LSP next hop";
          uses springte_lsp_nh_obj;
        }
        container p2mp-ldp-next-hop {
          description
            "Point-to-multipoint LDP LSP next hop";
          uses p2mp_ldp_lsp_nh_obj;
        }
        list static-lsp-next-hop {
          key "name";
          ordered-by user;
          description
            "Static LSP next hop";
          uses lsp_nh_obj;
        }
      }
      leaf protocol-instance-name {
        type string;
        description
          "Name of protocol instance under routing instance";
      }
      container static-route {
        description
          "Static route Status";
        leaf bfd-admin-down {
          type enumeration {
            enum "active" {
              description
                "Static route will be inactive on bfd-admin-down";
            }
            enum "passive" {
              description
                "Static route will remain active on bfd-admin-down";
            }
          }
          description
            "Static route State on BFD ADMIN DOWN";
        }
      }
      list route-target-filter {
        key "name";
        ordered-by user;
        description
          "Route-target-filter route";
        leaf name {
          type string {
            length "1 .. 47";
          }
        }
        uses apply-advanced;
        leaf-list neighbor {
          type jt:ipaddr-scoped;
          ordered-by user;
          description
            "BGP peers for filter";
        }
        leaf-list group {
          type string;
          ordered-by user;
          description
            "BGP groups for filter";
        }
        leaf local {
          type empty;
          description
            "Locally originated filter";
        }
      }
    }
    list martians {
      key "address choice-ident choice-value";
      ordered-by user;
      description
        "Invalid routes";
      uses martian_type;
    }
    container aggregate {
      description
        "Coalesced routes";
      uses rib_aggregate_type;
    }
    container generate {
      description
        "Route of last resort";
      uses rib_aggregate_type;
    }
    choice maximum-paths-type {
      case case_1 {
        container maximum-routes {
          status deprecated;
          description
            "Maximum number of routes";
          leaf limit {
            type union {
              type string {
                pattern "<.*>|$.*";
              }
              type uint32 {
                range "1 .. 4294967295";
              }
            }
            mandatory true;
            description
              "Maximum number of routes";
          }
          choice log_type {
            case case_1 {
              leaf threshold {
                type union {
                  type string {
                    pattern "<.*>|$.*";
                  }
                  type uint32 {
                    range "1 .. 100";
                  }
                }
                description
                  "Percentage of limit at which to start generating warnings";
              }
            }
            case case_2 {
              leaf log-only {
                type empty;
                description
                  "Generate warning messages only";
              }
            }
          }
          leaf log-interval {
            type union {
              type string {
                pattern "<.*>|$.*";
              }
              type uint32 {
                range "5 .. 86400";
              }
            }
            units "seconds";
            description
              "Minimum interval between log messages";
          }
        }
      }
      case case_2 {
        container maximum-paths {
          description
            "Maximum number of paths";
          leaf limit {
            type union {
              type string {
                pattern "<.*>|$.*";
              }
              type uint32 {
                range "1 .. 4294967295";
              }
            }
            mandatory true;
            description
              "Maximum number of paths";
          }
          choice log_type {
            case case_1 {
              leaf threshold {
                type union {
                  type string {
                    pattern "<.*>|$.*";
                  }
                  type uint32 {
                    range "1 .. 100";
                  }
                }
                description
                  "Percentage of limit at which to start generating warnings";
              }
            }
            case case_2 {
              leaf log-only {
                type empty;
                description
                  "Generate warning messages only";
              }
            }
          }
          leaf log-interval {
            type union {
              type string {
                pattern "<.*>|$.*";
              }
              type uint32 {
                range "5 .. 86400";
              }
            }
            units "seconds";
            description
              "Minimum interval between log messages";
          }
        }
      }
    }
    container maximum-prefixes {
      description
        "Maximum number of prefixes";
      leaf limit {
        type union {
          type string {
            pattern "<.*>|$.*";
          }
          type uint32 {
            range "1 .. 4294967295";
          }
        }
        description
          "Maximum number of prefixes";
      }
      choice log_type {
        case case_1 {
          leaf threshold {
            type union {
              type string {
                pattern "<.*>|$.*";
              }
              type uint32 {
                range "1 .. 100";
              }
            }
            description
              "Percentage of limit at which to start generating warnings";
          }
        }
        case case_2 {
          leaf log-only {
            type empty;
            description
              "Generate warning messages only";
          }
        }
      }
      leaf log-interval {
        type union {
          type string {
            pattern "<.*>|$.*";
          }
          type uint32 {
            range "5 .. 86400";
          }
        }
        units "seconds";
        description
          "Minimum interval between log messages";
      }
    }
    container multipath {
      presence "enable multipath";
      description
        "Protocol-independent load balancing";
      uses apply-advanced;
      container vpn-unequal-cost {
        presence "enable vpn-unequal-cost";
        description
          "Include VPN routes with unequal IGP metrics";
        leaf equal-external-internal {
          type empty;
          description
            "Include external and internal VPN routes";
        }
      }
      leaf as-path-compare {
        type empty;
        description
          "Compare AS path sequences in addition to AS path length";
      }
      leaf preserve-nexthop-hierarchy {
        type empty;
        description
          "Force multipath to create List nexthop";
      }
    }
    container policy-multipath {
      description
        "Policy based multipath";
      uses apply-advanced;
      leaf-list policy {
        type jt:policy-algebra;
        ordered-by user;
        description
          "Import policy to create policy based multipath";
      }
      container traceoptions {
        description
          "Trace options";
        uses apply-advanced;
        container file {
          description
            "Trace file options";
          leaf filename {
            type string {
              length "1 .. 1024";
            }
            description
              "Name of file in which to write trace information";
          }
          leaf replace {
            type empty;
            status deprecated;
            description
              "Replace trace file rather than appending to it";
          }
          leaf size {
            type string;
            description
              "Maximum trace file size";
          }
          leaf files {
            type union {
              type string {
                pattern "<.*>|$.*";
              }
              type uint32 {
                range "2 .. 1000";
              }
            }
            default "10";
            description
              "Maximum number of trace files";
          }
          leaf no-stamp {
            type empty;
            status deprecated;
            description
              "Do not timestamp trace file";
          }
          choice world-readable-choice {
            leaf world-readable {
              type empty;
              description
                "Allow any user to read the log file";
            }
            leaf no-world-readable {
              type empty;
              description
                "Don't allow any user to read the log file";
            }
          }
        }
        list flag {
          key "name";
          ordered-by user;
          description
            "Tracing parameters";
          leaf name {
            type enumeration {
              enum "route" {
                description
                  "Policy-multipath route tracing.";
              }
            }
          }
          leaf send {
            type empty;
            description
              "Trace transmitted packets";
          }
          leaf receive {
            type empty;
            description
              "Trace received packets";
          }
          leaf detail {
            type empty;
            description
              "Trace detailed information";
          }
          leaf disable {
            type empty;
            description
              "Disable this trace flag";
          }
        }
      }
      leaf preserve-nexthop-hierarchy {
        type empty;
        description
          "Enable preserved nexthop hierarchy";
      }
    }
    container access {
      description
        "Access routes";
      uses apply-advanced;
      list route {
        key "name";
        ordered-by user;
        description
          "Access route";
        leaf name {
          type jt:ipprefix;
          description
            "IP address of destination";
        }
        uses apply-advanced;
        leaf-list next-hop {
          type union {
            type jt:ipaddr-or-interface;
            type string {
              pattern "<.*>|$.*";
            }
          }
          ordered-by user;
          description
            "Next hop to destination";
        }
        list qualified-next-hop {
          key "name";
          ordered-by user;
          description
            "Next hop with qualifiers";
          uses qualified_nh_obj;
        }
        leaf metric {
          type union {
            type string {
              pattern "<.*>|$.*";
            }
            type uint32 {
              range "1 .. 255";
            }
          }
          description
            "Metric value";
        }
        leaf preference {
          type union {
            type uint32;
            type string {
              pattern "<.*>|$.*";
            }
          }
          description
            "Preference value";
        }
        leaf tag {
          type union {
            type uint32;
            type string {
              pattern "<.*>|$.*";
            }
          }
          description
            "Tag string";
        }
        leaf tag2 {
          type union {
            type uint32;
            type string {
              pattern "<.*>|$.*";
            }
          }
          description
            "Tag2 string";
        }
      }
    }
    container access-internal {
      description
        "Access-internal routes";
      uses apply-advanced;
      list route {
        key "name";
        ordered-by user;
        description
          "Access-internal route";
        leaf name {
          type jt:ipprefix;
          description
            "IP address and optional prefix length of destination";
        }
        uses apply-advanced;
        leaf-list next-hop {
          type union {
            type jt:ipaddr-or-interface;
            type string {
              pattern "<.*>|$.*";
            }
          }
          ordered-by user;
          description
            "Next hop to destination";
        }
        list qualified-next-hop {
          key "name";
          ordered-by user;
          description
            "Next hop with qualifiers";
          uses qualified_nh_obj;
        }
      }
    }
    container bgp-static {
      description
        "Routes for BGP static advertisements";
      uses apply-advanced;
      list route {
        key "name";
        ordered-by user;
        description
          "BGP-static route";
        leaf name {
          type jt:ipprefix;
          description
            "IP address and optional prefix length of destination";
        }
        uses apply-advanced;
        container metric {
          presence "enable metric";
          description
            "Metric value";
          uses rib_static_metric_type;
        }
        container metric2 {
          presence "enable metric2";
          description
            "Metric value 2";
          uses rib_static_metric_type;
        }
        container metric3 {
          presence "enable metric3";
          description
            "Metric value 3";
          uses rib_static_metric_type;
        }
        container metric4 {
          presence "enable metric4";
          description
            "Metric value 4";
          uses rib_static_metric_type;
        }
        container tag {
          presence "enable tag";
          description
            "Tag string";
          uses rib_static_metric_type;
        }
        container tag2 {
          presence "enable tag2";
          description
            "Tag string 2";
          uses rib_static_metric_type;
        }
        container preference {
          presence "enable preference";
          description
            "Preference value";
          uses rib_static_metric_type;
        }
        container preference2 {
          presence "enable preference2";
          description
            "Preference value 2";
          uses rib_static_metric_type;
        }
        container color {
          presence "enable color";
          description
            "Color (preference) value";
          uses rib_static_metric_type;
        }
        container color2 {
          presence "enable color2";
          description
            "Color (preference) value 2";
          uses rib_static_metric_type;
        }
        leaf-list community {
          type jt:community;
          ordered-by user;
          description
            "BGP community identifier";
        }
        container as-path {
          description
            "Autonomous system path";
          uses apply-advanced;
          leaf path {
            type string;
            description
              "Autonomous system path";
          }
          leaf origin {
            type enumeration {
              enum "igp" {
                description
                  "Path originated in the local IGP";
              }
              enum "egp" {
                description
                  "Path originated in another AS";
              }
              enum "incomplete" {
                description
                  "Path was learned by some other means";
              }
            }
          }
          leaf atomic-aggregate {
            type empty;
            description
              "Add ATOMIC_AGGREGATE path attribute to route";
          }
          container aggregator {
            presence "enable aggregator";
            description
              "Add AGGREGATOR path attribute to route";
          }
          leaf as-number {
            type string;
            description
              " Autonomous system number in plain number or 'higher 16bits'.'Lower 16 bits' (asdot notation) format";
          }
          leaf address {
            type jt:ipv4addr;
            description
              "Address of BGP system that formed the route";
          }
        }
      }
    }
    list rib-groups {
      key "name";
      ordered-by user;
      description
        "Group of routing tables";
      uses rpd_rib_group_type;
    }
    leaf-list instance-import {
      type jt:policy-algebra;
      ordered-by user;
      description
        "Import policy for instance RIBs";
    }
    leaf-list instance-export {
      type jt:policy-algebra;
      ordered-by user;
      description
        "Export policy for instance RIBs";
    }
    leaf-list pre-export-filter {
      type jt:policy-algebra;
      ordered-by user;
      description
        "Pre-export filter for protocol export-policy";
    }
    container auto-export {
      presence "enable auto-export";
      description
        "Export routes between routing instances";
      uses apply-advanced;
      choice enable-disable {
        case case_1 {
          leaf disable {
            type empty;
            description
              "Disable auto-export";
          }
        }
      }
      container traceoptions {
        description
          "Trace options";
        uses apply-advanced;
        container file {
          description
            "Trace file options";
          leaf filename {
            type string {
              length "1 .. 1024";
            }
            description
              "Name of file in which to write trace information";
          }
          leaf replace {
            type empty;
            status deprecated;
            description
              "Replace trace file rather than appending to it";
          }
          leaf size {
            type string;
            description
              "Maximum trace file size";
          }
          leaf files {
            type union {
              type string {
                pattern "<.*>|$.*";
              }
              type uint32 {
                range "2 .. 1000";
              }
            }
            default "10";
            description
              "Maximum number of trace files";
          }
          leaf no-stamp {
            type empty;
            status deprecated;
            description
              "Do not timestamp trace file";
          }
          choice world-readable-choice {
            leaf world-readable {
              type empty;
              description
                "Allow any user to read the log file";
            }
            leaf no-world-readable {
              type empty;
              description
                "Don't allow any user to read the log file";
            }
          }
        }
        list flag {
          key "name";
          ordered-by user;
          description
            "Tracing parameters";
          leaf name {
            type enumeration {
              enum "export" {
                description
                  "Export processing";
              }
              enum "route" {
                description
                  "Trace routing information";
              }
              enum "normal" {
                description
                  "Trace normal events";
              }
              enum "general" {
                description
                  "Trace general events";
              }
              enum "state" {
                description
                  "Trace state transitions";
              }
              enum "policy" {
                description
                  "Trace policy processing";
              }
              enum "task" {
                description
                  "Trace routing protocol task processing";
              }
              enum "timer" {
                description
                  "Trace routing protocol timer processing";
              }
              enum "all" {
                description
                  "Trace everything";
              }
            }
          }
          leaf send {
            type empty;
            description
              "Trace transmitted packets";
          }
          leaf receive {
            type empty;
            description
              "Trace received packets";
          }
          leaf detail {
            type empty;
            description
              "Trace detailed information";
          }
          leaf disable {
            type empty;
            description
              "Disable this trace flag";
          }
        }
      }
      container family {
        container inet {
          description
            "IPv4 parameters";
          uses export-af-obj;
        }
        container inet6 {
          description
            "IPv6 parameters";
          uses export-af-obj;
        }
        container iso {
          description
            "ISO parameters";
          uses export-af-obj;
        }
      }
    }
    container transport-class {
      presence "enable transport-class";
      description
        "Transport layer options";
      uses apply-advanced;
      leaf auto-create {
        type empty;
        description
          "Auto create on color discovery";
      }
      container fallback {
        description
          "Service routes resolution fallback";
        uses apply-advanced;
        leaf none {
          type empty;
          description
            "Resolve associated service-routes using this transport-class tunnels only";
        }
      }
      list name {
        key "name";
        ordered-by user;
        description
          "Transport layer collecting Tunnels with similar characteristics";
        leaf name {
          type string;
          description
            "Transport class name";
        }
        uses apply-advanced;
        leaf color {
          type union {
            type uint32;
            type string {
              pattern "<.*>|$.*";
            }
          }
          description
            "Color(0..4294967295). This auto derives the Mapping Community and Route Target";
        }
        container fallback {
          description
            "Service routes resolution fallback";
          uses apply-advanced;
          leaf none {
            type empty;
            description
              "Resolve associated service-routes using this transport-class tunnels only";
          }
        }
        container tunnel-egress {
          description
            "Tunnel-Egress endpoint origination";
          uses apply-advanced;
          list end-point {
            key "name";
            ordered-by user;
            description
              "Configure Tunnel-Egress endpoints";
            leaf name {
              type jt:ipaddr;
              description
                "Address of Tunnel egress endpoint";
            }
            uses apply-advanced;
            leaf-list import {
              type jt:policy-algebra;
              ordered-by user;
              description
                "Import policy to set attributes";
            }
          }
        }
      }
      container any-class {
        description
          "Predefined transport class collecting Tunnels of all transport classes";
        uses apply-advanced;
        leaf color {
          type union {
            type uint32;
            type string {
              pattern "<.*>|$.*";
            }
          }
          description
            "Color 32bit value. This auto derives the Mapping Community.";
        }
        container fallback {
          description
            "Service routes resolution fallback";
          uses apply-advanced;
          leaf none {
            type empty;
            description
              "Resolve associated service-routes using this transport-class tunnels only";
          }
        }
      }
      container best-effort {
        description
          "Best effort transport class";
        uses apply-advanced;
        leaf color {
          type union {
            type uint32;
            type string {
              pattern "<.*>|$.*";
            }
          }
          description
            "Color 32 bit value";
        }
        container fallback {
          description
            "Service routes resolution fallback";
          uses apply-advanced;
          leaf none {
            type empty;
            description
              "Resolve associated service-routes using this transport-class tunnels only";
          }
        }
      }
    }
    container dynamic-tunnels {
      description
        "Dynamic tunnel definitions";
      uses apply-advanced;
      list tunnel-attributes {
        key "name";
        ordered-by user;
        description
          "Dynamic tunnel attributes definition";
        leaf name {
          type string;
          description
            "Dynamic Tunnel attribute name";
        }
        uses apply-advanced;
        leaf dynamic-tunnel-source-prefix {
          type jt:ipaddr;
          description
            "Tunnel source address";
        }
        leaf dynamic-tunnel-type {
          type enumeration {
            enum "GRE" {
              description
                "Tunnel type GRE";
            }
            enum "V4oV6" {
              description
                "Tunnel type is IPV4oIPV6";
            }
            enum "UDP" {
              description
                "Tunnel type UDP";
            }
            enum "BGP-SIGNAL" {
              description
                "Tunnel type BGP-SIGNAL";
            }
            enum "IPIP" {
              description
                "Tunnel type IPIP";
            }
          }
          mandatory true;
        }
        leaf dynamic-tunnel-mtu {
          type union {
            type string {
              pattern "<.*>|$.*";
            }
            type uint32 {
              range "296 .. 9232";
            }
          }
          description
            "Dynamic Tunnel MTU value";
        }
        leaf dynamic-tunnel-gre-key {
          type union {
            type string {
              pattern "<.*>|$.*";
            }
            type uint32 {
              range "1 .. 4294967295";
            }
          }
          description
            "RFC 2890 Dynamic Tunnel GRE Key";
        }
        leaf dynamic-tunnel-anchor-pfe {
          type string;
          description
            "Dynamic Tunnel anchor PFE name of format pfe-x/y/z";
        }
        leaf dynamic-tunnel-anti-spoof {
          type enumeration {
            enum "on" {
              description
                "Enable antispoofing check. Default is enabled";
            }
            enum "off" {
              description
                "Disable antispoofing check";
            }
          }
        }
        leaf dynamic-tunnel-reassembly {
          type enumeration {
            enum "on" {
              description
                "Enable reassembly check. Default is disabled";
            }
            enum "off" {
              description
                "Disable reassembly check";
            }
          }
        }
        leaf dynamic-tunnel-ttl {
          type union {
            type string {
              pattern "<.*>|$.*";
            }
            type uint32 {
              range "1 .. 255";
            }
          }
          description
            "Dynamic Tunnel TTL value";
        }
        leaf dynamic-tunnel-forwarding-class {
          type string {
            length "1 .. 64";
          }
          description
            "Dynamic Tunnel forwarding class name";
        }
        leaf dynamic-tunnel-payload-port-profile {
          type string;
          description
            "Dynamic Tunnel UDP payload port profile";
        }
        leaf dynamic-tunnel-propagate-dscp {
          type empty;
          description
            "Dynamic Tunnel Propagate DSCP";
        }
        leaf dynamic-tunnel-propagate-ecn {
          type empty;
          description
            "Dynamic Tunnel Propagate ECN";
        }
      }
      container forwarding-rib {
        presence "enable forwarding-rib";
        description
          "Forwarding routing table for dynamic-tunnel";
        uses apply-advanced;
        container inet.0 {
          presence "enable inet.0";
          description
            "Rib table inet.0";
          uses apply-advanced;
          leaf-list inet-import {
            type jt:policy-algebra;
            ordered-by user;
            description
              "Import policy for V4 dynamic-tunnel";
          }
        }
        container inet6.0 {
          presence "enable inet6.0";
          description
            "Rib table inet6.0";
          uses apply-advanced;
          leaf-list inet6-import {
            type jt:policy-algebra;
            ordered-by user;
            description
              "Import policy for V6 dynamic-tunnel";
          }
        }
      }
      container statistics {
        description
          "Fetch traffic statistics for  dynamic tunnels";
        uses apply-advanced;
        leaf interval {
          type union {
            type string {
              pattern "<.*>|$.*";
            }
            type uint16 {
              range "1 .. 65535";
            }
          }
          units "seconds";
          description
            "Time after which statistics has to be fetched";
        }
      }
      container traceoptions {
        description
          "Trace options";
        uses apply-advanced;
        container file {
          description
            "Trace file options";
          leaf filename {
            type string {
              length "1 .. 1024";
            }
            description
              "Name of file in which to write trace information";
          }
          leaf replace {
            type empty;
            status deprecated;
            description
              "Replace trace file rather than appending to it";
          }
          leaf size {
            type string;
            description
              "Maximum trace file size";
          }
          leaf files {
            type union {
              type string {
                pattern "<.*>|$.*";
              }
              type uint32 {
                range "2 .. 1000";
              }
            }
            default "10";
            description
              "Maximum number of trace files";
          }
          leaf no-stamp {
            type empty;
            status deprecated;
            description
              "Do not timestamp trace file";
          }
          choice world-readable-choice {
            leaf world-readable {
              type empty;
              description
                "Allow any user to read the log file";
            }
            leaf no-world-readable {
              type empty;
              description
                "Don't allow any user to read the log file";
            }
          }
        }
        list flag {
          key "name";
          ordered-by user;
          description
            "Tracing parameters";
          leaf name {
            type enumeration {
              enum "kernel" {
                description
                  "Trace kernel communication";
              }
              enum "tunnel" {
                description
                  "Trace tunnel addition, change, or deletion";
              }
              enum "task" {
                description
                  "Trace task or job processing";
              }
              enum "tunnel-event" {
                description
                  "Trace create, delete, up, down event for nh based tunnel";
              }
              enum "flash-event" {
                description
                  "Trace flash event for tunnel forwarding route";
              }
              enum "stats-job" {
                description
                  "Trace taffic statistics job related stuff";
              }
              enum "all" {
                description
                  "Trace everything";
              }
            }
          }
          leaf send {
            type empty;
            description
              "Trace transmitted packets";
          }
          leaf receive {
            type empty;
            description
              "Trace received packets";
          }
          leaf detail {
            type empty;
            description
              "Trace detailed information";
          }
          leaf disable {
            type empty;
            description
              "Disable this trace flag";
          }
        }
      }
      leaf v4ov6 {
        type enumeration {
          enum "ipv6-anycast-source-duplication" {
            description
              "Enable full resolved nh base source-tunnel";
          }
        }
        description
          "Enable dynamic tunnel V4oV6 mode";
      }
      list gre {
        key "name";
        ordered-by user;
        description
          "Enable dynamic gre tunnel mode";
        leaf name {
          type enumeration {
            enum "next-hop-based-tunnel" {
              description
                "Enable nh base dynamic-tunnel";
            }
            enum "full-resolved-next-hop-based-tunnel" {
              description
                "Enable full resolved nh base dynamic-tunnel";
            }
            enum "chain-full-resolve-next-hop-based-tunnel" {
              description
                "Enable chain full resolved nh base dynamic-tunnel";
            }
          }
          description
            "Enable dynamic tunnel gre mode";
        }
        uses apply-advanced;
      }
      container signal-tunnel-preference {
        presence "enable signal-tunnel-preference";
        description
          "Set tunnel preference for signalled tunnels";
        uses apply-advanced;
        leaf gre {
          type union {
            type string {
              pattern "<.*>|$.*";
            }
            type uint32 {
              range "1 .. 10";
            }
          }
          description
            "Preference of GRE signalled tunnels";
        }
        leaf udp {
          type union {
            type string {
              pattern "<.*>|$.*";
            }
            type uint32 {
              range "1 .. 10";
            }
          }
          description
            "Preference of UDP signalled tunnels";
        }
        leaf ipip {
          type union {
            type string {
              pattern "<.*>|$.*";
            }
            type uint32 {
              range "1 .. 10";
            }
          }
          description
            "Preference of IPIP signalled tunnels";
        }
      }
      list dynamic-tunnel {
        key "name";
        ordered-by user;
        uses dynamic_tunnel_type;
      }
    }
    container forwarding-table {
      uses forwarding-table-type;
    }
    container fate-sharing {
      description
        "Fate-sharing links or nodes database";
      uses apply-advanced;
      list group {
        key "name";
        ordered-by user;
        description
          "Group of objects sharing common characteristics";
        leaf name {
          type string;
          description
            "Name of object groups sharing the same fate";
        }
        uses apply-advanced;
        leaf cost {
          type union {
            type string {
              pattern "<.*>|$.*";
            }
            type uint32 {
              range "1 .. 65535";
            }
          }
          description
            "Cost value";
        }
        leaf use-for-post-convergence-lfa {
          type empty;
          description
            "Use this fate-sharing group as a constraint for post-convergence-lfa";
        }
        list from {
          key "name";
          uses fate_sharing_links;
        }
      }
    }
    container programmable-rpd {
      description
        "RPD Server module management options";
      uses programmable-rpd-type;
    }
    container validation {
      description
        "Define Route validation";
      uses apply-advanced;
      container traceoptions {
        description
          "Trace options for route validation";
        uses apply-advanced;
        container file {
          description
            "Trace file options";
          leaf filename {
            type string {
              length "1 .. 1024";
            }
            description
              "Name of file in which to write trace information";
          }
          leaf replace {
            type empty;
            status deprecated;
            description
              "Replace trace file rather than appending to it";
          }
          leaf size {
            type string;
            description
              "Maximum trace file size";
          }
          leaf files {
            type union {
              type string {
                pattern "<.*>|$.*";
              }
              type uint32 {
                range "2 .. 1000";
              }
            }
            default "10";
            description
              "Maximum number of trace files";
          }
          leaf no-stamp {
            type empty;
            status deprecated;
            description
              "Do not timestamp trace file";
          }
          choice world-readable-choice {
            leaf world-readable {
              type empty;
              description
                "Allow any user to read the log file";
            }
            leaf no-world-readable {
              type empty;
              description
                "Don't allow any user to read the log file";
            }
          }
        }
        list flag {
          key "name";
          ordered-by user;
          description
            "Tracing parameters";
          leaf name {
            type enumeration {
              enum "error" {
                description
                  "Trace errored packets";
              }
              enum "packets" {
                description
                  "Trace all I/O packets";
              }
              enum "keepalive" {
                description
                  "Trace keepalive packets";
              }
              enum "update" {
                description
                  "Trace update packets";
              }
              enum "nsr-synchronization" {
                description
                  "Trace NSR synchronization events";
              }
              enum "state" {
                description
                  "Trace state transitions";
              }
              enum "policy" {
                description
                  "Trace policy processing";
              }
              enum "task" {
                description
                  "Trace routing protocol task processing";
              }
              enum "timer" {
                description
                  "Trace routing protocol timer processing";
              }
              enum "client" {
                description
                  "Trace route validation client events";
              }
              enum "all" {
                description
                  "Trace everything";
              }
            }
          }
          leaf send {
            type empty;
            description
              "Trace transmitted packets";
          }
          leaf receive {
            type empty;
            description
              "Trace received packets";
          }
          leaf detail {
            type empty;
            description
              "Trace detailed information";
          }
          leaf disable {
            type empty;
            description
              "Disable this trace flag";
          }
        }
      }
      leaf source-file {
        type string;
        description
          "Specify a local file to read data set";
      }
      leaf-list notification-rib {
        type string;
        ordered-by user;
        description
          "Define routing tables that get notified upon validation state change";
      }
      list group {
        key "name";
        description
          "Define a group of sessions";
        leaf name {
          type string;
          description
            "Group name";
        }
        uses apply-advanced;
        leaf authentication-algorithm {
          type enumeration {
            enum "ao" {
              description
                "TCP authentication option";
            }
          }
          description
            "Authentication algorithm name";
        }
        leaf tcpao-auth-mismatch {
          type enumeration {
            enum "allow-without-tcpao" {
              description
                "Allow the connection establishment without TCP-AO";
            }
          }
          description
            "Continue without TCP-AO if any one TCP endpoint does not have TCP-AO configured";
        }
        leaf authentication-key-chain {
          type string {
            length "1 .. 128";
          }
          description
            "Key chain name";
        }
        leaf max-sessions {
          type union {
            type string {
              pattern "<.*>|$.*";
            }
            type uint32 {
              range "1 .. 63";
            }
          }
          description
            "Maximum connected session in this group";
        }
        list session {
          key "name";
          description
            "Configure a session";
          leaf name {
            type jt:ipaddr;
          }
          uses apply-advanced;
          container traceoptions {
            description
              "Trace options for route validation";
            uses apply-advanced;
            container file {
              description
                "Trace file options";
              leaf filename {
                type string {
                  length "1 .. 1024";
                }
                description
                  "Name of file in which to write trace information";
              }
              leaf replace {
                type empty;
                status deprecated;
                description
                  "Replace trace file rather than appending to it";
              }
              leaf size {
                type string;
                description
                  "Maximum trace file size";
              }
              leaf files {
                type union {
                  type string {
                    pattern "<.*>|$.*";
                  }
                  type uint32 {
                    range "2 .. 1000";
                  }
                }
                default "10";
                description
                  "Maximum number of trace files";
              }
              leaf no-stamp {
                type empty;
                status deprecated;
                description
                  "Do not timestamp trace file";
              }
              choice world-readable-choice {
                leaf world-readable {
                  type empty;
                  description
                    "Allow any user to read the log file";
                }
                leaf no-world-readable {
                  type empty;
                  description
                    "Don't allow any user to read the log file";
                }
              }
            }
            list flag {
              key "name";
              ordered-by user;
              description
                "Tracing parameters";
              leaf name {
                type enumeration {
                  enum "error" {
                    description
                      "Trace errored packets";
                  }
                  enum "packets" {
                    description
                      "Trace all I/O packets";
                  }
                  enum "keepalive" {
                    description
                      "Trace keepalive packets";
                  }
                  enum "update" {
                    description
                      "Trace update packets";
                  }
                  enum "state" {
                    description
                      "Trace state transitions";
                  }
                  enum "task" {
                    description
                      "Trace routing protocol task processing";
                  }
                  enum "timer" {
                    description
                      "Trace routing protocol timer processing";
                  }
                  enum "all" {
                    description
                      "Trace everything";
                  }
                }
              }
              leaf send {
                type empty;
                description
                  "Trace transmitted packets";
              }
              leaf receive {
                type empty;
                description
                  "Trace received packets";
              }
              leaf detail {
                type empty;
                description
                  "Trace detailed information";
              }
              leaf disable {
                type empty;
                description
                  "Disable this trace flag";
              }
            }
          }
          leaf authentication-algorithm {
            type enumeration {
              enum "ao" {
                description
                  "TCP authentication option";
              }
            }
            description
              "Authentication algorithm name";
          }
          leaf tcpao-auth-mismatch {
            type enumeration {
              enum "allow-without-tcpao" {
                description
                  "Allow the connection establishment without TCP-AO";
              }
            }
            description
              "Continue without TCP-AO if any one TCP endpoint does not have TCP-AO configured";
          }
          leaf authentication-key-chain {
            type string {
              length "1 .. 128";
            }
            description
              "Key chain name";
          }
          leaf database {
            type string;
            description
              "Named database in this instance to install validation entries";
          }
          leaf refresh-time {
            type union {
              type string {
                pattern "<.*>|$.*";
              }
              type uint32 {
                range "1 .. 1800";
              }
            }
            units "seconds";
            description
              "Interval between keepalive packet transmissions";
          }
          leaf hold-time {
            type union {
              type string {
                pattern "<.*>|$.*";
              }
              type uint32 {
                range "10 .. 3600";
              }
            }
            units "seconds";
            description
              "Time after which the session is declared down.";
          }
          leaf record-lifetime {
            type union {
              type string {
                pattern "<.*>|$.*";
              }
              type uint32 {
                range "60 .. 604800";
              }
            }
            units "seconds";
            description
              "Lifetime of route validation records";
          }
          leaf preference {
            type union {
              type string {
                pattern "<.*>|$.*";
              }
              type uint32 {
                range "1 .. 255";
              }
            }
            description
              "Preference for session establishment";
          }
          leaf port {
            type union {
              type string {
                pattern "<.*>|$.*";
              }
              type uint16 {
                range "1 .. 65535";
              }
            }
            description
              "Portnumber to connect";
          }
          leaf local-address {
            type jt:ipaddr;
          }
        }
      }
      container static {
        description
          "Define static route validation record";
        uses apply-advanced;
        list record {
          key "name";
          description
            "Static route validation record";
          leaf name {
            type jt:ipprefix;
          }
          uses apply-advanced;
          list maximum-length {
            key "name";
            ordered-by user;
            leaf name {
              type union {
                type string {
                  pattern "<.*>|$.*";
                }
                type uint32 {
                  range "1 .. 128";
                }
              }
              description
                "Maximum prefix-length for route validation record";
            }
            uses apply-advanced;
            list origin-autonomous-system {
              key "name";
              ordered-by user;
              leaf name {
                type union {
                  type uint32;
                  type string {
                    pattern "<.*>|$.*";
                  }
                }
                description
                  "Legitimate Origin Autonomous System";
              }
              uses apply-advanced;
              leaf validation-state {
                type enumeration {
                  enum "invalid" {
                    description
                      "Invalid route validation state";
                  }
                  enum "valid" {
                    description
                      "Valid route validation state";
                  }
                }
                description
                  "Validation state for route validation record";
              }
            }
          }
        }
      }
      list database {
        key "name";
        description
          "Specify a named validation database";
        leaf name {
          type string;
          description
            "Name of validation database";
        }
        uses apply-advanced;
        container static {
          description
            "Define static route validation record";
          uses apply-advanced;
          list record {
            key "name";
            description
              "Static route validation record";
            leaf name {
              type jt:ipprefix;
            }
            uses apply-advanced;
            list maximum-length {
              key "name";
              ordered-by user;
              leaf name {
                type union {
                  type string {
                    pattern "<.*>|$.*";
                  }
                  type uint32 {
                    range "1 .. 128";
                  }
                }
                description
                  "Maximum prefix-length for route validation record";
              }
              uses apply-advanced;
              list origin-autonomous-system {
                key "name";
                ordered-by user;
                leaf name {
                  type union {
                    type uint32;
                    type string {
                      pattern "<.*>|$.*";
                    }
                  }
                  description
                    "Legitimate Origin Autonomous System";
                }
                uses apply-advanced;
                leaf validation-state {
                  type enumeration {
                    enum "invalid" {
                      description
                        "Invalid route validation state";
                    }
                    enum "valid" {
                      description
                        "Valid route validation state";
                    }
                  }
                  description
                    "Validation state for route validation record";
                }
              }
            }
          }
        }
      }
    }
  }

  grouping bmp-loc-rib-apath-options {
    description
      "Number of paths to advertise";
    uses apply-advanced;
    container path-selection-mode {
      description
        "Configure how to select add-path routes";
      uses apply-advanced;
      choice mode {
        case case_1 {
          leaf all-paths {
            type empty;
            description
              "Advertise all paths allowed by path count";
          }
        }
        case case_2 {
          leaf equal-cost-paths {
            type empty;
            description
              "Advertise equal cost paths";
          }
        }
      }
    }
    leaf path-count {
      type union {
        type string {
          pattern "<.*>|$.*";
        }
        type int32 {
          range "2 .. 64";
        }
      }
      mandatory true;
      description
        "Number of paths to advertise";
    }
    leaf multipath {
      type empty;
      description
        "Include multipath contributor routes";
    }
  }

  grouping domain-id-type {
    leaf name {
      type string;
      description
        "Domain id for type 5 evpn DCI";
    }
    uses apply-advanced;
  }

  grouping dynamic_tunnel_type {
    description
      "Dynamic tunnel definition";
    leaf name {
      type string;
      description
        "Tunnel name";
    }
    uses apply-advanced;
    leaf source-address {
      type jt:ipaddr;
      description
        "Tunnel source address";
    }
    choice tunnel-type {
      case case_1 {
        list rsvp-te {
          key "name";
          ordered-by user;
          description
            "RSVP-TE point-to-point LSP";
          leaf name {
            type string;
            description
              "Configure multiple entries for RSVP tunnel";
          }
          uses apply-advanced;
          container label-switched-path-template {
            description
              "Template for dynamic point-to-point LSP parameters";
            uses apply-advanced;
            choice dynamic-template {
              case case_1 {
                leaf template-name {
                  type string;
                  description
                    "Name of point-to-point LSP template";
                }
              }
              case case_2 {
                leaf default-template {
                  type empty;
                  description
                    "Use default parameters";
                }
              }
            }
          }
          list destination-networks {
            key "name";
            ordered-by user;
            description
              "Create tunnels for routes in these destination networks";
            uses app_network_type;
          }
        }
      }
      case case_2 {
        container spring-te {
          description
            "SPRING-TE LSP's";
          uses apply-advanced;
          leaf use-transport-class {
            type empty;
            description
              "Install dynamic-tunnel routes via transport class RIBs";
          }
          list source-routing-path-template {
            key "name";
            ordered-by user;
            description
              "Template color mapping for SPRING-TE dynamic LSP parameters";
            uses spring-te-template-map;
          }
          list destination-networks {
            key "name";
            ordered-by user;
            description
              "Create tunnels for routes in these destination networks";
            uses app_network_type;
          }
        }
      }
      case case_3 {
        leaf gre {
          type empty;
          description
            "Generic routing encapsulation type for IPv4";
        }
      }
      case case_4 {
        leaf udp {
          type empty;
          description
            "UDP encapsulation type for IPv4";
        }
      }
      case case_5 {
        leaf bgp-signal {
          type empty;
          description
            "BGP signals the encapsulation type for IPv4";
        }
      }
      case case_6 {
        leaf ipip {
          type empty;
          description
            "IPIP encapsulation type for IPv4";
        }
      }
      case case_7 {
        leaf srv6 {
          type empty;
          description
            "SRv6 encapsulation type for IPv6";
        }
      }
    }
    leaf use-transport-class {
      type empty;
      description
        "Install dynamic-tunnel routes via transport class RIBs";
    }
    list destination-networks {
      key "name";
      ordered-by user;
      description
        "Create tunnels for routes in these destination networks";
      uses network_type;
    }
  }

  grouping app_network_type {
    leaf name {
      type jt:ipprefix;
      description
        "Network prefix";
    }
    uses apply-advanced;
  }

  grouping export-af-obj {
    uses apply-advanced;
    choice enable-disable {
      case case_1 {
        leaf disable {
          type empty;
          description
            "Disable auto-export for address family";
        }
      }
    }
    container unicast {
      presence "enable unicast";
      description
        "Unicast routing information";
      uses export-subaf-obj;
    }
    container multicast {
      presence "enable multicast";
      description
        "Multicast routing information";
      uses export-subaf-obj;
    }
    container flow {
      presence "enable flow";
      description
        "Flow routing information";
      uses export-subaf-obj;
    }
  }

  grouping export-subaf-obj {
    uses apply-advanced;
    choice enable-disable {
      case case_1 {
        leaf disable {
          type empty;
          description
            "Disable instance export";
        }
      }
    }
    leaf rib-group {
      type string;
      description
        "Auxiliary rib-group of additional RIBs to consider";
    }
  }

  grouping fate_sharing_links {
    leaf name {
      type jt:ipv4addr;
      description
        "Router ID or LAN interface address";
    }
    leaf to {
      type jt:ipv4addr;
      description
        "Point-to-point links";
    }
  }

  grouping flow-interface-group {
    leaf group {
      type union {
        type string {
          pattern "<.*>|$.*";
        }
        type uint32 {
          range "1 .. 255";
        }
      }
      description
        "Interface group ID to match traffic";
    }
    leaf exclude {
      type empty;
      description
        "Don't apply flow-spec filter to traffic on this group";
    }
  }

  grouping flow-route-inet {
    leaf name {
      type string;
    }
    uses apply-advanced;
    leaf no-install {
      type empty;
      description
        "Don't install firewall filter in forwarding";
    }
    container match {
      description
        "Flow definition";
      uses flow-route-qualifier-inet;
    }
    container then {
      description
        "Actions to take for this flow";
      uses flow-route-op;
    }
  }

  grouping flow-route-inet6 {
    leaf name {
      type string;
    }
    uses apply-advanced;
    leaf no-install {
      type empty;
      description
        "Don't install firewall filter in forwarding";
    }
    container match {
      description
        "Flow definition";
      uses flow-route-qualifier-inet6;
    }
    container then {
      description
        "Actions to take for this flow";
      uses flow-route-op;
    }
  }

  grouping flow-route-op {
    uses apply-advanced;
    leaf community {
      type string;
      description
        "Name of BGP community";
    }
    choice flow_op_action {
      case case_1 {
        leaf accept {
          type empty;
          description
            "Allow traffic through";
        }
      }
      case case_2 {
        leaf discard {
          type empty;
          description
            "Discard all traffic for this flow";
        }
      }
      case case_3 {
        leaf rate-limit {
          type string;
          description
            "Rate in bits/sec to limit the flow traffic";
        }
      }
    }
    leaf routing-instance {
      type string;
      description
        "Redirect to instance identified via Route Target community";
    }
    leaf sample {
      type empty;
      description
        "Sample traffic that matches this flow";
    }
    leaf mark {
      type union {
        type string {
          pattern "<.*>|$.*";
        }
        type uint32 {
          range "0 .. 63";
        }
      }
      description
        "Set DSCP value for traffic that matches this flow";
    }
    leaf next-term {
      type empty;
      description
        "Continue the filter evaluation after matching this flow";
    }
    choice redirect_op_action {
      case case_1 {
        leaf-list redirect {
          type jt:ipaddr;
          ordered-by user;
          description
            "Redirect(Tunnel) this flow's traffic to given next-hop address";
        }
      }
    }
  }

  grouping flow-route-qualifier-inet {
    uses apply-advanced;
    leaf-list protocol {
      type string;
      ordered-by user;
      description
        "IP protocol value";
    }
    leaf-list port {
      type string;
      ordered-by user;
    }
    leaf-list destination-port {
      type string;
      ordered-by user;
    }
    leaf-list source-port {
      type string;
      ordered-by user;
    }
    leaf-list tcp-flags {
      type string;
      ordered-by user;
      description
        "TCP flags";
    }
    leaf-list packet-length {
      type jt:policy-algebra;
      ordered-by user;
      description
        "Packet length (0-65535)";
    }
    leaf-list dscp {
      type jt:policy-algebra;
      ordered-by user;
      description
        "Differentiated Services (DiffServ) code point (DSCP) (0-63)";
    }
    leaf-list fragment {
      type enumeration {
        enum "dont-fragment" {
          description
            "Don't Fragment flag is set";
        }
        enum "not-a-fragment" {
          description
            "Not a fragment";
        }
        enum "is-fragment" {
          description
            "Fragmented packet";
        }
        enum "first-fragment" {
          description
            "First fragment";
        }
        enum "last-fragment" {
          description
            "Last fragment";
        }
      }
      ordered-by user;
    }
    leaf destination {
      type jt:ipv4prefix;
      description
        "Destination prefix for this traffic flow";
    }
    leaf source {
      type jt:ipv4prefix;
      description
        "Source prefix for this traffic flow";
    }
    leaf-list icmp-code {
      type string;
      ordered-by user;
      description
        "ICMP message code";
    }
    leaf-list icmp-type {
      type string;
      ordered-by user;
      description
        "ICMP message type";
    }
  }

  grouping flow-route-qualifier-inet6 {
    uses apply-advanced;
    leaf-list protocol {
      type string;
      ordered-by user;
      description
        "IP protocol value";
    }
    leaf-list port {
      type string;
      ordered-by user;
    }
    leaf-list destination-port {
      type string;
      ordered-by user;
    }
    leaf-list source-port {
      type string;
      ordered-by user;
    }
    leaf-list tcp-flags {
      type string;
      ordered-by user;
      description
        "TCP flags";
    }
    leaf-list packet-length {
      type jt:policy-algebra;
      ordered-by user;
      description
        "Packet length (0-65535)";
    }
    leaf-list dscp {
      type jt:policy-algebra;
      ordered-by user;
      description
        "Differentiated Services (DiffServ) code point (DSCP) (0-63)";
    }
    leaf-list fragment {
      type enumeration {
        enum "dont-fragment" {
          description
            "Don't Fragment flag is set";
        }
        enum "not-a-fragment" {
          description
            "Not a fragment";
        }
        enum "is-fragment" {
          description
            "Fragmented packet";
        }
        enum "first-fragment" {
          description
            "First fragment";
        }
        enum "last-fragment" {
          description
            "Last fragment";
        }
      }
      ordered-by user;
    }
    container destination {
      presence "enable destination";
      description
        "Destination prefix for this traffic flow";
      uses flow-prefix-with-offset;
    }
    container source {
      presence "enable source";
      description
        "Source prefix for this traffic flow";
      uses flow-prefix-with-offset;
    }
    leaf-list icmp6-type {
      type string;
      ordered-by user;
      description
        "ICMP message type";
    }
    leaf-list icmp6-code {
      type string;
      ordered-by user;
      description
        "ICMP message code";
    }
    leaf-list flow-label {
      type jt:policy-algebra;
      ordered-by user;
      description
        "Flow-label (0-1048575)";
    }
  }

  grouping flow-prefix-with-offset {
    leaf prefix {
      type jt:ipv6prefix;
      mandatory true;
    }
    leaf prefix-offset {
      type union {
        type uint32;
        type string {
          pattern "<.*>|$.*";
        }
      }
      description
        "Offset from where prefix match will start";
    }
  }

  grouping flow-rule-inet {
    leaf name {
      type string;
    }
    uses apply-advanced;
    leaf no-install {
      type empty;
      description
        "Don't install firewall filter in forwarding";
    }
    container match {
      description
        "Flow definition";
      uses flow-rule-qualifier-inet;
    }
    container then {
      description
        "Actions to take for this flow";
      uses flow-rule-op;
    }
  }

  grouping flow-rule-inet6 {
    leaf name {
      type string;
    }
    uses apply-advanced;
    leaf no-install {
      type empty;
      description
        "Don't install firewall filter in forwarding";
    }
    container match {
      description
        "Flow definition";
      uses flow-rule-qualifier-inet6;
    }
    container then {
      description
        "Actions to take for this flow";
      uses flow-rule-op;
    }
  }

  grouping flow-rule-op {
    uses apply-advanced;
    choice flow_op_action {
      case case_1 {
        leaf accept {
          type empty;
          description
            "Allow traffic through";
        }
      }
      case case_2 {
        leaf discard {
          type empty;
          description
            "Discard all traffic for this flow";
        }
      }
      case case_3 {
        leaf rate-limit {
          type string;
          description
            "Rate in bits/sec to limit the flow traffic";
        }
      }
    }
  }

  grouping flow-rule-qualifier-inet {
    uses apply-advanced;
    leaf-list protocol {
      type string;
      ordered-by user;
      description
        "IP protocol value";
    }
    leaf-list port {
      type string;
      ordered-by user;
    }
    leaf-list destination-port {
      type string;
      ordered-by user;
    }
    leaf-list source-port {
      type string;
      ordered-by user;
    }
    leaf destination {
      type jt:ipv4prefix;
      description
        "Destination prefix for this traffic flow";
    }
    leaf source {
      type jt:ipv4prefix;
      description
        "Source prefix for this traffic flow";
    }
  }

  grouping flow-rule-qualifier-inet6 {
    uses apply-advanced;
    leaf-list protocol {
      type string;
      ordered-by user;
      description
        "IP protocol value";
    }
    leaf-list port {
      type string;
      ordered-by user;
    }
    leaf-list destination-port {
      type string;
      ordered-by user;
    }
    leaf-list source-port {
      type string;
      ordered-by user;
    }
    container destination {
      presence "enable destination";
      description
        "Destination prefix for this traffic flow";
      uses flow-prefix-with-offset;
    }
    container source {
      presence "enable source";
      description
        "Source prefix for this traffic flow";
      uses flow-prefix-with-offset;
    }
  }

  grouping flow-validation {
    uses apply-advanced;
    container traceoptions {
      description
        "Trace options";
      uses flow-dep-traceoptions;
    }
  }

  grouping flow-dep-traceoptions {
    uses apply-advanced;
    container file {
      description
        "Trace file options";
      leaf filename {
        type string {
          length "1 .. 1024";
        }
        description
          "Name of file in which to write trace information";
      }
      leaf replace {
        type empty;
        status deprecated;
        description
          "Replace trace file rather than appending to it";
      }
      leaf size {
        type string;
        description
          "Maximum trace file size";
      }
      leaf files {
        type union {
          type string {
            pattern "<.*>|$.*";
          }
          type uint32 {
            range "2 .. 1000";
          }
        }
        default "10";
        description
          "Maximum number of trace files";
      }
      leaf no-stamp {
        type empty;
        status deprecated;
        description
          "Do not timestamp trace file";
      }
      choice world-readable-choice {
        leaf world-readable {
          type empty;
          description
            "Allow any user to read the log file";
        }
        leaf no-world-readable {
          type empty;
          description
            "Don't allow any user to read the log file";
        }
      }
    }
    list flag {
      key "name";
      ordered-by user;
      description
        "Tracing parameters";
      leaf name {
        type enumeration {
          enum "resolution" {
            description
              "Trace flow to unicast route resolution";
          }
          enum "flash" {
            description
              "Trace flash processing";
          }
          enum "route" {
            description
              "Trace routing information";
          }
          enum "normal" {
            description
              "Trace normal events";
          }
          enum "general" {
            description
              "Trace general events";
          }
          enum "state" {
            description
              "Trace state transitions";
          }
          enum "policy" {
            description
              "Trace policy processing";
          }
          enum "task" {
            description
              "Trace routing protocol task processing";
          }
          enum "timer" {
            description
              "Trace routing protocol timer processing";
          }
          enum "all" {
            description
              "Trace everything";
          }
        }
      }
      leaf send {
        type empty;
        description
          "Trace transmitted packets";
      }
      leaf receive {
        type empty;
        description
          "Trace received packets";
      }
      leaf detail {
        type empty;
        description
          "Trace detailed information";
      }
      leaf disable {
        type empty;
        description
          "Disable this trace flag";
      }
      container filter {
        presence "enable filter";
        description
          "Filter to apply to tracing";
        leaf match-on {
          type enumeration {
            enum "prefix" {
              description
                "Filter based on prefix";
            }
            enum "route-attribute" {
              description
                "Filter based on route attributes";
            }
          }
          mandatory true;
          description
            "Argument on which to match";
        }
        leaf-list policy {
          type jt:policy-algebra;
          ordered-by user;
          description
            "Filter policy";
        }
      }
    }
  }

  grouping forwarding-table-type {
    description
      "Forwarding table management options";
    uses apply-advanced;
    leaf oc-tlv-support {
      type empty;
      description
        "Send origin protocol and network-instance for route and stream next-hop origin protocol";
    }
    leaf remnant-holdtime {
      type union {
        type string {
          pattern "<.*>|$.*";
        }
        type uint32 {
          range "0 .. 10000";
        }
      }
      description
        "Time to hold inherited routes from FIB";
    }
    leaf send-gr-issu-message {
      type union {
        type string {
          pattern "<.*>|$.*";
        }
        type uint32 {
          range "1 .. 65535";
        }
      }
      description
        "Simulate gr-issu message reception from rpd-agent";
    }
    leaf chain-composite-max-label-count {
      type union {
        type string {
          pattern "<.*>|$.*";
        }
        type uint32 {
          range "1 .. 16";
        }
      }
      description
        "Maximum labels inside chain composite for the platform.";
    }
    leaf krt-nexthop-ack {
      type empty;
      description
        "Enable kernel nexthop ack";
    }
    leaf krt-nexthop-ack-timeout {
      type union {
        type string {
          pattern "<.*>|$.*";
        }
        type uint32 {
          range "1 .. 400";
        }
      }
      description
        "Kernel nexthop ack timeout interval";
    }
    leaf srv6-chain-merge {
      type empty;
      description
        "Enable merging of srv6 chain nexthops";
    }
    choice session-id-change-limiter-indirect-choice {
      leaf session-id-change-limiter-indirect {
        type empty;
        description
          "Enable indirect nexthop to limit session-id change propagation";
      }
      leaf no-session-id-change-limiter-indirect {
        type empty;
        description
          "Don't enable indirect nexthop to limit session-id change propagation";
      }
    }
    container consistency-checking {
      status deprecated;
      description
        "RIB/FIB consistency checking";
      uses apply-advanced;
      choice enable-disable {
        case case_1 {
          leaf enable {
            type empty;
            description
              "Enable consistency checking";
          }
        }
        case case_2 {
          leaf disable {
            type empty;
            description
              "Disable consistency checking";
          }
        }
      }
      leaf period {
        type union {
          type string {
            pattern "<.*>|$.*";
          }
          type uint32 {
            range "30 .. 4294967295";
          }
        }
        description
          "Periodicity of scan in seconds";
      }
      leaf threshold {
        type union {
          type uint32;
          type string {
            pattern "<.*>|$.*";
          }
        }
        description
          "Mismatch threshold until complaint";
      }
    }
    leaf-list export {
      type jt:policy-algebra;
      ordered-by user;
      description
        "Export policy";
    }
    leaf dynamic-list-next-hop {
      type empty;
      description
        "Dynamic next-hop mode for EVPN";
    }
    container evpn-egress-link-protection {
      presence "enable evpn-egress-link-protection";
      description
        "EVPN PE-CE egress link failure protection";
      uses apply-advanced;
    }
    leaf vpls-hotstandby-convergence {
      type empty;
      description
        "Enable convergence improvements for VPLS hot-standby";
    }
    container egress-chaining {
      description
        "Enable egress-chaining";
      uses apply-advanced;
      leaf spring-te {
        type empty;
        description
          "Enable egress-chaining for SPRING-TE routes";
      }
    }
    leaf evpn-aliasing-optimize {
      type empty;
      description
        "EVPN Aliasing convergence improvement";
    }
    choice indirect-next-hop-choice {
      leaf indirect-next-hop {
        type empty;
        description
          "Install indirect next hops in Packet Forwarding Engine";
      }
      leaf no-indirect-next-hop {
        type empty;
        description
          "Don't install indirect next hops in Packet Forwarding Engine";
      }
    }
    choice route-ack-converge-choice {
      leaf route-ack-converge {
        type empty;
        description
          "Enable the route ack convergence feature";
      }
      leaf no-route-ack-converge {
        type empty;
        description
          "Don't enable the route ack convergence feature";
      }
    }
    leaf long-live-ack-timer-val {
      type union {
        type string {
          pattern "<.*>|$.*";
        }
        type uint32 {
          range "1 .. 65535";
        }
      }
      description
        "Set default long live acknowledgement timer value";
    }
    choice pfe-install-error-choice {
      leaf pfe-install-error {
        type empty;
        description
          "Enable processing error from PFE for objects installed";
      }
      leaf no-pfe-install-error {
        type empty;
        description
          "Don't enable processing error from PFE for objects installed";
      }
    }
    list rib {
      key "name";
      ordered-by user;
      status deprecated;
      leaf name {
        type string;
      }
    }
    leaf unicast-reverse-path {
      type enumeration {
        enum "active-paths" {
          description
            "Consider active paths when performing RP verification";
        }
        enum "feasible-paths" {
          description
            "Consider all feasible paths for RP verification";
        }
      }
      description
        "Unicast reverse path (RP) verification";
    }
    container ip-tunnel-rpf-check {
      presence "enable ip-tunnel-rpf-check";
      description
        "IP tunnel Reverse Path Forwarding Check";
      uses apply-advanced;
      leaf mode {
        type enumeration {
          enum "strict" {
            description
              "Strict mode for rpf-check(Default)";
          }
          enum "loose" {
            description
              "Loose mode for rpf-check";
          }
        }
        default "strict";
      }
      leaf fail-filter {
        type string;
        description
          "Fail filter name for RPF check(family inet|inet6|any)";
      }
    }
    container fib-next-hop-split {
      description
        "Split nexthop to chain nexthop when installing fom rib to fib";
      uses apply-advanced;
      leaf labeled-isis {
        type empty;
        description
          "Create composite-chained nexthops for labeled ISIS routes";
      }
    }
    container fib-agent {
      presence "enable fib-agent";
      description
        "Configure fib-agent parameters";
      uses apply-advanced;
      leaf address {
        type jt:ipaddr;
        default "127.0.0.1";
        description
          "IP address of the FIB agent";
      }
      leaf port {
        type union {
          type string {
            pattern "<.*>|$.*";
          }
          type uint32 {
            range "1 .. 65535";
          }
        }
        default "2620";
        description
          "TCP port of the FIB agent";
      }
      leaf protocol-id {
        type union {
          type string {
            pattern "<.*>|$.*";
          }
          type uint32 {
            range "0 .. 255";
          }
        }
        default "22";
        description
          "Protocol ID to be used for programming routes";
      }
    }
    list channel {
      key "name";
      ordered-by user;
      description
        "Configure fib-channel parameters";
      leaf name {
        type string;
        description
          "FIB Channel Name";
      }
      uses apply-advanced;
      container protocol {
        presence "enable protocol";
        description
          "Configure fib-channel protocol";
        uses apply-advanced;
        leaf protocol-type {
          type enumeration {
            enum "netlink-fpm" {
              description
                "Configure SONiC FIB Channel";
            }
            enum "gRPC" {
              description
                "Configure vRouter FIB channel.";
            }
          }
          mandatory true;
        }
        leaf destination {
          type string;
          description
            "Destination of the FIB";
        }
        leaf source-id {
          type union {
            type string {
              pattern "<.*>|$.*";
            }
            type uint32 {
              range "0 .. 255";
            }
          }
          default "22";
          description
            "Source ID to be used for programming routes";
        }
      }
      leaf-list export {
        type jt:policy-algebra;
        ordered-by user;
        description
          "Export policy";
      }
    }
    leaf multicast-composite-delete-defer-timeout {
      type union {
        type string {
          pattern "<.*>|$.*";
        }
        type uint32 {
          range "1 .. 3600";
        }
      }
      description
        "Time to defer multicast composite NH delete operation into FIB";
    }
  }

  grouping juniper-system {
    uses apply-advanced;
    leaf host-name {
      type string {
        length "1 .. 255";
      }
      description
        "Hostname for this router";
    }
    container root-authentication {
      description
        "Authentication information for the root login";
      uses authentication-object;
    }
    container scripts {
      description
        "Scripting mechanisms";
      uses scripts_type;
    }
    container login {
      description
        "Names, login classes, and passwords for users";
      uses apply-advanced;
      container retry-options {
        description
          "Configure password retry options";
        uses apply-advanced;
        leaf tries-before-disconnect {
          type union {
            type string {
              pattern "<.*>|$.*";
            }
            type uint32 {
              range "2 .. 10";
            }
          }
          default "3";
          description
            "Number of times user is allowed to try password";
        }
        leaf backoff-threshold {
          type union {
            type string {
              pattern "<.*>|$.*";
            }
            type uint32 {
              range "1 .. 3";
            }
          }
          default "2";
          description
            "Number of password failures before delay is introduced";
        }
        leaf backoff-factor {
          type union {
            type string {
              pattern "<.*>|$.*";
            }
            type uint32 {
              range "5 .. 10";
            }
          }
          default "5";
          description
            "Delay factor after 'backoff-threshold' password failures";
        }
        leaf minimum-time {
          type union {
            type string {
              pattern "<.*>|$.*";
            }
            type uint32 {
              range "20 .. 60";
            }
          }
          default "20";
          description
            "Minimum total connection time if all attempts fail";
        }
        leaf maximum-time {
          type union {
            type string {
              pattern "<.*>|$.*";
            }
            type uint32 {
              range "20 .. 300";
            }
          }
          default "120";
          description
            "Maximum time the connection will remain for user to enter username and password";
        }
        leaf lockout-period {
          type union {
            type string {
              pattern "<.*>|$.*";
            }
            type uint32 {
              range "1 .. 43200";
            }
          }
          units "minutes";
          description
            "Amount of time user account is locked after 'tries-before-disconnect' failures";
        }
      }
      leaf idle-timeout {
        type union {
          type string {
            pattern "<.*>|$.*";
          }
          type uint32 {
            range "1 .. 60";
          }
        }
        units "minutes";
        description
          "Maximum idle time before logout";
      }
      list class {
        key "name";
        description
          "Login class";
        uses login-class-object;
      }
      list user {
        key "name";
        description
          "Username";
        uses login-user-object;
      }
      container password {
        description
          "Password configuration";
        uses apply-advanced;
        leaf minimum-character-changes {
          type union {
            type string {
              pattern "<.*>|$.*";
            }
            type int32 {
              range "4 .. 15";
            }
          }
          description
            "Minimum number of character changes between old and new passwords";
        }
        leaf minimum-reuse {
          type union {
            type string {
              pattern "<.*>|$.*";
            }
            type int32 {
              range "1 .. 20";
            }
          }
          description
            "Minimum number of old passwords which should not be same as the new password";
        }
        leaf maximum-lifetime {
          type union {
            type string {
              pattern "<.*>|$.*";
            }
            type int32 {
              range "30 .. 365";
            }
          }
          description
            "Maximum password lifetime in days";
        }
        leaf minimum-lifetime {
          type union {
            type string {
              pattern "<.*>|$.*";
            }
            type int32 {
              range "1 .. 30";
            }
          }
          description
            "Minimum password lifetime in days";
        }
        leaf minimum-length {
          type union {
            type string {
              pattern "<.*>|$.*";
            }
            type int32 {
              range "6 .. 20";
            }
          }
          description
            "Minimum password length for all users";
        }
        leaf maximum-length {
          type union {
            type string {
              pattern "<.*>|$.*";
            }
            type int32 {
              range "20 .. 128";
            }
          }
          description
            "Maximum password length for all users";
        }
        leaf change-type {
          type enumeration {
            enum "character-sets" {
              description
                "Count number of character type";
            }
            enum "set-transitions" {
              description
                "Count changes in character type";
            }
          }
          description
            "Password change type";
        }
        leaf minimum-changes {
          type union {
            type int32;
            type string {
              pattern "<.*>|$.*";
            }
          }
          description
            "Minimum number of changes in password";
        }
        leaf minimum-numerics {
          type union {
            type string {
              pattern "<.*>|$.*";
            }
            type int32 {
              range "1 .. 128";
            }
          }
          description
            "Minimum number of numeric class characters in password";
        }
        leaf minimum-upper-cases {
          type union {
            type string {
              pattern "<.*>|$.*";
            }
            type int32 {
              range "1 .. 128";
            }
          }
          description
            "Minimum number of upper-case class characters in password";
        }
        leaf minimum-lower-cases {
          type union {
            type string {
              pattern "<.*>|$.*";
            }
            type int32 {
              range "1 .. 128";
            }
          }
          description
            "Minimum number of lower-case class characters in password";
        }
        leaf minimum-punctuations {
          type union {
            type string {
              pattern "<.*>|$.*";
            }
            type int32 {
              range "1 .. 128";
            }
          }
          description
            "Minimum number of punctuation class characters in password";
        }
        leaf format {
          type enumeration {
            enum "sha256" {
              description
                "Secure Hash Algorithm 256 ($5$)";
            }
            enum "sha512" {
              description
                "Secure Hash Algorithm 512 ($6$)";
            }
            enum "md5" {
              description
                "Message Digest 5";
            }
            enum "des" {
              description
                "Digital Encryption Standard";
            }
          }
          description
            "Encryption method to use for password";
        }
      }
      container deny-sources {
        description
          "Sources from which logins are denied";
        uses apply-advanced;
        leaf-list address {
          type jt:ipprefix-optional;
          ordered-by user;
          description
            "IPv4/IPv6 addresses, prefix length optional, or hostnames";
        }
      }
      leaf announcement {
        type string {
          length "1 .. 2048";
        }
        description
          "System announcement message (displayed after login)";
      }
      leaf message {
        type string {
          length "1 .. 2048";
        }
        description
          "System login message";
      }
    }
    container configuration {
      description
        "Set the configuration processing related parameters";
      uses apply-advanced;
      container input {
        description
          "Set the input configuration processing related parameters";
        uses apply-advanced;
        container format {
          description
            "Specify the format";
          uses apply-advanced;
          container json {
            description
              "JSON format related parameters";
            uses apply-advanced;
            leaf reorder-list-keys {
              type empty;
              description
                "Reorder list keys as per JUNOS style";
            }
          }
        }
      }
    }
    leaf max-cli-sessions {
      type union {
        type uint32;
        type string {
          pattern "<.*>|$.*";
        }
      }
      description
        "Maximum number of cli sessions";
    }
    container services {
      presence "enable services";
      description
        "System services";
      uses apply-advanced;
      container netconf {
        description
          "Allow NETCONF connections";
        uses apply-advanced;
        container yang-modules {
          description
            "Tweak settings for YANG modules served on this device";
          uses apply-advanced;
          leaf emit-family-ns-and-module-name {
            type empty;
            description
              "Emit family specific namespace and module name in Yang modules";
          }
          leaf device-specific {
            type empty;
            description
              "Serve YANG modules specific to this device";
          }
          leaf emit-extensions {
            type empty;
            description
              "Enable serving of Junos YANG extension modules";
          }
          leaf rpc-output-verbose {
            type empty;
            status deprecated;
            description
              "Emit verbose rpc output";
          }
          leaf emit-anyxml-in-rpc-output {
            type empty;
            description
              "Emit anyxml stanza in RPC output/response block";
          }
        }
        container ssh {
          presence "enable ssh";
          description
            "Allow NETCONF over SSH";
          uses apply-advanced;
          leaf client-alive-count-max {
            type union {
              type string {
                pattern "<.*>|$.*";
              }
              type uint32 {
                range "0 .. 255";
              }
            }
            default "3";
            description
              "Threshold of missing client-alive responses that triggers a disconnect";
          }
          leaf client-alive-interval {
            type union {
              type string {
                pattern "<.*>|$.*";
              }
              type uint32 {
                range "0 .. 65535";
              }
            }
            units "seconds";
            default "0";
            description
              "Frequency of client-alive requests";
          }
          leaf port {
            type union {
              type string {
                pattern "<.*>|$.*";
              }
              type int32 {
                range "1 .. 65535";
              }
            }
            default "830";
            description
              "Service port number";
          }
        }
        container tls {
          description
            "Allow NETCONF over TLS";
          uses apply-advanced;
          leaf local-certificate {
            type string;
            description
              "Local Certificate ID";
          }
          list client-identity {
            key "name";
            ordered-by user;
            description
              "Individual TLS/NETCONF client information";
            leaf name {
              type string {
                length "1 .. 31";
              }
              description
                "Client ID";
            }
            uses apply-advanced;
            leaf fingerprint {
              type string;
              mandatory true;
              description
                "Client certificate fingerprint in x509c2n:tls-fingerprint format";
            }
            leaf map-type {
              type enumeration {
                enum "specified" {
                  description
                    "Use the specified username as NETCONF username";
                }
                enum "san-dirname-cn" {
                  description
                    "Use the common name (CN) field of SAN DirName as NETCONF username";
                }
              }
              mandatory true;
              description
                "Map Type";
            }
            leaf username {
              type string;
              description
                "NETCONF username if the map-type is specified";
            }
          }
          container default-client-identity {
            description
              "Default TLS/NETCONF client information";
            uses apply-advanced;
            leaf map-type {
              type enumeration {
                enum "specified" {
                  description
                    "Use the specified username as NETCONF username";
                }
                enum "san-dirname-cn" {
                  description
                    "Use the common name (CN) field of SAN DirName as NETCONF username";
                }
              }
              description
                "Map Type";
            }
            leaf username {
              type string;
              description
                "NETCONF username if the map-type is specified";
            }
          }
          container traceoptions {
            description
              "NETCONF over TLS trace options";
            uses apply-advanced;
            leaf no-remote-trace {
              type empty;
              description
                "Disable remote tracing";
            }
            container file {
              description
                "Trace file information";
              leaf filename {
                type string {
                  length "1 .. 1024";
                }
                description
                  "Name of file in which to write trace information";
              }
              leaf size {
                type string;
                description
                  "Maximum trace file size";
              }
              leaf files {
                type union {
                  type string {
                    pattern "<.*>|$.*";
                  }
                  type uint32 {
                    range "2 .. 1000";
                  }
                }
                default "3";
                description
                  "Maximum number of trace files";
              }
              choice world-readable-choice {
                leaf world-readable {
                  type empty;
                  description
                    "Allow any user to read the log file";
                }
                leaf no-world-readable {
                  type empty;
                  description
                    "Don't allow any user to read the log file";
                }
              }
              leaf match {
                type jt:regular-expression;
                description
                  "Regular expression for lines to be logged";
              }
            }
            leaf level {
              type enumeration {
                enum "error" {
                  description
                    "Match error conditions";
                }
                enum "warning" {
                  description
                    "Match warning messages";
                }
                enum "notice" {
                  description
                    "Match conditions that should be handled specially";
                }
                enum "info" {
                  description
                    "Match informational messages";
                }
                enum "verbose" {
                  description
                    "Match verbose messages";
                }
                enum "all" {
                  description
                    "Match all levels";
                }
              }
              default "error";
              description
                "Level of debugging output";
            }
            list flag {
              key "name";
              ordered-by user;
              description
                "Tracing parameters";
              leaf name {
                type enumeration {
                  enum "general" {
                    description
                      "Log the tls-proxyd infra related messages";
                  }
                  enum "pki" {
                    description
                      "Log the PKI related messages";
                  }
                  enum "plugin" {
                    description
                      "Log the plugin messages";
                  }
                  enum "app" {
                    description
                      "Log the application data in plain text";
                  }
                  enum "all" {
                    description
                      "Log the entire communication";
                  }
                }
              }
            }
          }
        }
        container unified {
          description
            "Schema options for unified netconf";
          uses apply-advanced;
          leaf unhide {
            type empty;
            description
              "Unhide unified netconf get from CLI";
          }
        }
        container hello-message {
          description
            "Configuration for NETCONF 'hello' message";
          uses apply-advanced;
          container yang-module-capabilities {
            description
              "Advertise YANG module capabilities of the device";
            uses apply-advanced;
            leaf advertise-native-yang-modules {
              type empty;
              description
                "Advertise Junos native YANG modules";
            }
            leaf advertise-custom-yang-modules {
              type empty;
              description
                "Advertise custom YANG modules installed on the device";
            }
            leaf advertise-standard-yang-modules {
              type empty;
              description
                "Advertise standard YANG modules supported by the device";
            }
          }
        }
        container netconf-monitoring {
          description
            "NETCONF monitoring feature (RFC 6022) related configuration";
          uses apply-advanced;
          container netconf-state-schemas {
            description
              "Configuration to retrieve the schemas supported by the NETCONF server";
            uses apply-advanced;
            leaf retrieve-custom-yang-modules {
              type empty;
              description
                "Retrieve the custom YANG modules installed on the device";
            }
            leaf retrieve-standard-yang-modules {
              type empty;
              description
                "Retrieve the standard YANG modules supported by the device";
            }
          }
        }
        leaf rfc-compliant {
          type empty;
          description
            "Make the NETCONF sessions compliant to RFC 4741";
        }
        leaf yang-compliant {
          type empty;
          description
            "Make the NETCONF sessions compliant to yang schemas";
        }
        leaf flatten-commit-results {
          type empty;
          description
            "Suppress the 'commit-results' XML subtree in 'commit' rpc response";
        }
        container traceoptions {
          description
            "NETCONF trace options";
          uses apply-advanced;
          leaf no-remote-trace {
            type empty;
            description
              "Disable remote tracing";
          }
          container file {
            description
              "Trace file information";
            leaf filename {
              type string {
                length "1 .. 1024";
              }
              description
                "Name of file in which to write trace information";
            }
            leaf size {
              type string;
              description
                "Maximum trace file size";
            }
            leaf files {
              type union {
                type string {
                  pattern "<.*>|$.*";
                }
                type uint32 {
                  range "2 .. 1000";
                }
              }
              default "3";
              description
                "Maximum number of trace files";
            }
            choice world-readable-choice {
              leaf world-readable {
                type empty;
                description
                  "Allow any user to read the log file";
              }
              leaf no-world-readable {
                type empty;
                description
                  "Don't allow any user to read the log file";
              }
            }
            leaf match {
              type jt:regular-expression;
              description
                "Regular expression for lines to be logged";
            }
          }
          list flag {
            key "name";
            ordered-by user;
            description
              "Tracing parameters";
            leaf name {
              type enumeration {
                enum "all" {
                  description
                    "Log the entire communication";
                }
                enum "incoming" {
                  description
                    "Log all incoming data";
                }
                enum "outgoing" {
                  description
                    "Log all outgoing data";
                }
                enum "debug" {
                  description
                    "Log debug level information";
                }
              }
            }
          }
          leaf on-demand {
            type empty;
            description
              "Enable on-demand tracing";
          }
        }
        container notification {
          presence "enable notification";
          description
            "Enable Netconf notification service";
          uses apply-advanced;
          leaf interleave {
            type empty;
            description
              "Enable interleaving";
          }
        }
        container version-1.1 {
          presence "enable version-1.1";
          description
            "Make the NETCONF sessions compliant to RFC 6242";
        }
      }
      container ssh {
        presence "enable ssh";
        description
          "Allow ssh access";
        uses apply-advanced;
        leaf-list authentication-order {
          type enumeration {
            enum "radius" {
              description
                "Remote Authentication Dial-In User Service";
            }
            enum "tacplus" {
              description
                "TACACS+ authentication services";
            }
            enum "password" {
              description
                "Traditional password authentication";
            }
          }
          ordered-by user;
        }
        container cert-based-auth {
          description
            "Certificates for user authentication";
          uses apply-advanced;
          list trusted-user-ca-keys {
            key "name";
            ordered-by user;
            description
              "Trusted User CA Keys";
            leaf name {
              type string {
                length "1 .. 4096";
              }
              description
                "SSH public key for validating user certificates";
            }
            uses apply-advanced;
          }
          leaf host-certificate {
            type string {
              length "1 .. 8000";
            }
            description
              "SSH host certificate";
          }
        }
        leaf host-certificate-file {
          type string;
          description
            "File containing the host certificate";
        }
        leaf trusted-user-ca-key-file {
          type string;
          description
            "File containing public keys for validating user certificates";
        }
        leaf-list authorized-principals {
          type string;
          ordered-by user;
          description
            "List of authorized principals";
        }
        leaf authorized-principals-file {
          type string;
          description
            "File containing list of authorized principals";
        }
        leaf authorized-principals-command {
          type string;
          description
            "Command to generate AuthorizedPrincipals file";
        }
        leaf root-login {
          type enumeration {
            enum "allow" {
              description
                "Allow root access via ssh";
            }
            enum "deny" {
              description
                "Do not allow root access via ssh";
            }
            enum "deny-password" {
              description
                "Allow for non-password-based authentication methods only";
            }
          }
          description
            "Configure root access via ssh";
        }
        leaf no-challenge-response {
          type empty;
          description
            "Disables ssh challenge-response based authentication methods";
        }
        leaf no-password-authentication {
          type empty;
          description
            "Disables ssh password based authentication methods";
        }
        leaf no-passwords {
          type empty;
          description
            "Disables ssh password and challenge-response based authentication";
        }
        leaf no-public-keys {
          type empty;
          description
            "Disables ssh public key based authentication";
        }
        leaf allow-tcp-forwarding {
          type empty;
          description
            "Allow forwarding TCP connections via SSH";
        }
        leaf-list protocol-version {
          type enumeration {
            enum "v2" {
              description
                "Version 2 ssh protocol";
            }
          }
          ordered-by user;
          description
            "Specify ssh protocol versions supported";
        }
        leaf max-sessions-per-connection {
          type union {
            type string {
              pattern "<.*>|$.*";
            }
            type int32 {
              range "1 .. 65535";
            }
          }
          description
            "Maximum number of sessions per single SSH connection";
        }
        leaf max-pre-authentication-packets {
          type union {
            type string {
              pattern "<.*>|$.*";
            }
            type int32 {
              range "20 .. 2147483647";
            }
          }
          description
            "Maximum number of pre-authentication SSH packets per single SSH connection";
        }
        leaf sftp-server {
          type empty;
          description
            "Globally enable incoming SFTP connections";
        }
        leaf-list ciphers {
          type enumeration {
            enum "3des-cbc" {
              description
                "Triple DES in CBC mode";
            }
            enum "aes128-cbc" {
              description
                "128-bit AES with Cipher Block Chaining";
            }
            enum "aes192-cbc" {
              description
                "192-bit AES with Cipher Block Chaining";
            }
            enum "aes256-cbc" {
              description
                "256-bit AES with Cipher Block Chaining";
            }
            enum "aes128-ctr" {
              description
                "128-bit AES with Counter Mode";
            }
            enum "aes192-ctr" {
              description
                "192-bit AES with Counter Mode";
            }
            enum "aes256-ctr" {
              description
                "256-bit AES with Counter Mode";
            }
            enum "aes128-gcm@openssh.com" {
              description
                "128-bit AES with Galois/Counter Mode";
            }
            enum "aes256-gcm@openssh.com" {
              description
                "256-bit AES with Galois/Counter Mode";
            }
            enum "chacha20-poly1305@openssh.com" {
              description
                "ChaCha20 stream cipher and Poly1305 MAC";
            }
          }
          ordered-by user;
          description
            "Specify the ciphers allowed for protocol version 2";
        }
        leaf-list macs {
          type enumeration {
            enum "hmac-md5" {
              description
                "Hash-based MAC using Message-Digest 5 (MD5)";
            }
            enum "hmac-md5-etm@openssh.com" {
              description
                "Hash-based Encrypt-then-MAC using Message-Digest 5 (MD5)";
            }
            enum "hmac-sha1" {
              description
                "Hash-based MAC using Secure Hash Algorithm (SHA1)";
            }
            enum "hmac-sha1-etm@openssh.com" {
              description
                "Hash-based Encrypt-then-MAC using Secure Hash Algorithm (SHA1)";
            }
            enum "umac-64@openssh.com" {
              description
                "UMAC-64 algorithm specified in RFC4418";
            }
            enum "umac-128@openssh.com" {
              description
                "UMAC-128 algorithm specified in RFC4418";
            }
            enum "umac-64-etm@openssh.com" {
              description
                "Encrypt-then-MAC using UMAC-64 algorithm specified in RFC4418";
            }
            enum "umac-128-etm@openssh.com" {
              description
                "Encrypt-then-MAC using UMAC-128 algorithm specified in RFC4418";
            }
            enum "hmac-sha2-256" {
              description
                "Hash-based MAC using Secure Hash Algorithm (SHA2)";
            }
            enum "hmac-sha2-256-etm@openssh.com" {
              description
                "Hash-based Encrypt-then-Mac using Secure Hash Algorithm (SHA2)";
            }
            enum "hmac-sha2-512" {
              description
                "Hash-based MAC using Secure Hash Algorithm (SHA2)";
            }
            enum "hmac-sha2-512-etm@openssh.com" {
              description
                "Hash-based Encrypt-then-Mac using Secure Hash Algorithm (SHA2)";
            }
            enum "hmac-sha1-96" {
              description
                "96-bits of Hash-based MAC using SHA1";
            }
            enum "hmac-sha1-96-etm@openssh.com" {
              description
                "96-bits of Hash-based Encrypt-then-MAC using SHA1";
            }
            enum "hmac-md5-96" {
              description
                "96-bits of Hash-based MAC using MD5";
            }
            enum "hmac-md5-96-etm@openssh.com" {
              description
                "96-bits of Hash-based Encrypt-then-MAC using MD5";
            }
          }
          ordered-by user;
          description
            "Message Authentication Code algorithms allowed (SSHv2)";
        }
        leaf-list key-exchange {
          type enumeration {
            enum "curve25519-sha256" {
              description
                "The EC Diffie-Hellman on Curve25519 with SHA2-256 hash";
            }
            enum "ecdh-sha2-nistp256" {
              description
                "The EC Diffie-Hellman on nistp256 with SHA2-256";
            }
            enum "ecdh-sha2-nistp384" {
              description
                "The EC Diffie-Hellman on nistp384 with SHA2-384";
            }
            enum "ecdh-sha2-nistp521" {
              description
                "The EC Diffie-Hellman on nistp521 with SHA2-512";
            }
            enum "group-exchange-sha2" {
              description
                "The RFC 4419 group exchange with SHA2-256 hash";
            }
            enum "group-exchange-sha1" {
              description
                "The RFC 4419 group exchange with SHA1 hash";
            }
            enum "dh-group14-sha1" {
              description
                "The RFC 4253 mandated group14 with SHA1 hash";
            }
            enum "dh-group1-sha1" {
              description
                "The RFC 4253 mandated group1 with SHA1 hash";
            }
          }
          ordered-by user;
          description
            "Specify ssh key-exchange for Diffie-Hellman keys";
        }
        leaf client-alive-count-max {
          type union {
            type string {
              pattern "<.*>|$.*";
            }
            type uint32 {
              range "0 .. 255";
            }
          }
          default "3";
          description
            "Threshold of missing client-alive responses that triggers a disconnect";
        }
        leaf client-alive-interval {
          type union {
            type string {
              pattern "<.*>|$.*";
            }
            type uint32 {
              range "0 .. 65535";
            }
          }
          units "seconds";
          default "0";
          description
            "Frequency of client-alive requests";
        }
        container hostkey-algorithm-list {
          presence "enable hostkey-algorithm-list";
          description
            "Specify permissible SSH host-key algorithms";
          uses apply-advanced;
          leaf rsa {
            type empty;
            description
              "Allow generation of RSA host-key";
          }
          leaf ecdsa-sha2-nistp256 {
            type empty;
            description
              "Allow generation of ECDSA host-key with NIST P-256 curve";
          }
          leaf ecdsa-sha2-nistp384 {
            type empty;
            description
              "Allow generation of ECDSA host-key with NIST P-384 curve";
          }
          leaf ecdsa-sha2-nistp521 {
            type empty;
            description
              "Allow generation of ECDSA host-key with NIST P-521 curve";
          }
          leaf ed25519 {
            type empty;
            description
              "Allow generation of EdDSA host-key with curve25519";
          }
        }
        leaf fingerprint-hash {
          type enumeration {
            enum "sha2-256" {
              description
                "Enable use of SHA2-256";
            }
            enum "md5" {
              description
                "Enable use of MD5";
            }
          }
          description
            "Configure hash algorithm used when displaying key fingerprints";
        }
        leaf authorized-keys-command {
          type string {
            length "1 .. 1024";
          }
          description
            "Specifies a command string to be used to look up the user's public keys";
        }
        leaf authorized-keys-command-user {
          type string {
            length "1 .. 256";
          }
          description
            "Specifies the user under whose account the authorized-keys-command is run";
        }
        container rekey {
          description
            "Limits before session keys are renegotiated";
          uses apply-advanced;
          leaf data-limit {
            type string;
            units "bytes";
            description
              "Data limit before renegotiating session keys";
          }
          leaf time-limit {
            type union {
              type string {
                pattern "<.*>|$.*";
              }
              type uint32 {
                range "1 .. 1440";
              }
            }
            units "minutes";
            description
              "Time limit before renegotiating session keys";
          }
        }
        leaf port {
          type union {
            type string {
              pattern "<.*>|$.*";
            }
            type uint32 {
              range "1 .. 65535";
            }
          }
          default "22";
          description
            "Port number to accept incoming connections";
        }
        leaf log-key-changes {
          type empty;
          description
            "Log changes to authorized keys to syslog";
        }
      }
      container xnm-clear-text {
        presence "enable xnm-clear-text";
        description
          "Allow clear text-based JUNOScript connections";
        uses apply-advanced;
      }
      container xnm-ssl {
        presence "enable xnm-ssl";
        description
          "Allow SSL-based JUNOScript connections";
        uses apply-advanced;
        leaf local-certificate {
          type string;
          mandatory true;
          description
            "Name of local X.509 certificate to use";
        }
        choice ssl-renegotiation-choice {
          leaf ssl-renegotiation {
            type empty;
            description
              "Allow SSL renegotiation";
          }
          leaf no-ssl-renegotiation {
            type empty;
            description
              "Don't allow SSL renegotiation";
          }
        }
      }
      container jeb {
        presence "enable jeb";
        description
          "Configure the Juniper Juniper Entropy Beacon service";
        uses apply-advanced;
        leaf port {
          type union {
            type string {
              pattern "<.*>|$.*";
            }
            type uint32 {
              range "1025 .. 65535";
            }
          }
          default "57005";
          description
            "JEB Service port";
        }
        leaf rbg {
          type enumeration {
            enum "default-rng" {
              description
                "Default CSPRNG";
            }
            enum "hmac-drbg" {
              description
                "HMAC DRBG, NIST SP800-90A";
            }
            enum "jrbc" {
              description
                "Juniper Random Bit Conditioner";
            }
          }
          mandatory true;
          description
            "Random Bit Generator";
        }
        leaf max-seed-size {
          type union {
            type string {
              pattern "<.*>|$.*";
            }
            type uint32 {
              range "1 .. 65536";
            }
          }
          default "4096";
          description
            "Maximum allowed size for a requested seed";
        }
        container tls {
          presence "enable tls";
          description
            "Configure TLS Attributes for JEB Service";
          uses apply-advanced;
          leaf cert-bundle {
            type string;
            mandatory true;
            description
              "Certificate Bundle File";
          }
          leaf certificate {
            type string;
            mandatory true;
            description
              "TLS Server Certificate";
          }
          leaf key {
            type string;
            mandatory true;
            description
              "Private Key File";
          }
        }
      }
      container extension-service {
        description
          "Enable JUNOS extension services";
        uses apply-advanced;
        container request-response {
          description
            "Allow request-response API execution";
          uses apply-advanced;
          container grpc {
            description
              "Grpc server configuration";
            uses apply-advanced;
            choice request-response-type {
              case case_1 {
                container ssl {
                  description
                    "SSL based API connection settings";
                  uses apply-advanced;
                  leaf address {
                    type jt:ipaddr;
                    default "::";
                    description
                      "Address to listen for incoming connections";
                  }
                  leaf port {
                    type union {
                      type string {
                        pattern "<.*>|$.*";
                      }
                      type uint32 {
                        range "1 .. 65535";
                      }
                    }
                    default "32767";
                    description
                      "Port number to accept incoming connections";
                  }
                  leaf-list local-certificate {
                    type string;
                    ordered-by user;
                    description
                      "Name of local X.509 certificate to use";
                  }
                  container mutual-authentication {
                    description
                      "Enable TLS mutual authentication";
                    uses apply-advanced;
                    leaf certificate-authority {
                      type string;
                      mandatory true;
                      description
                        "Certificate authority profile";
                    }
                    leaf client-certificate-request {
                      type enumeration {
                        enum "no-certificate" {
                          description
                            "Client certificate is not requested";
                        }
                        enum "request-certificate" {
                          description
                            "Request certificate from client, do not verify";
                        }
                        enum "request-certificate-and-verify" {
                          description
                            "Request certificate from client, verify if provided";
                        }
                        enum "require-certificate" {
                          description
                            "Client certificate is mandatory, do not verify";
                        }
                        enum "require-certificate-and-verify" {
                          description
                            "Client certificate is mandatory, certificate is verified";
                        }
                      }
                      default "require-certificate-and-verify";
                      description
                        "Specify requirements for client certificate";
                    }
                  }
                  leaf hot-reloading {
                    type empty;
                    description
                      "Enable certificate reload without terminating existing gRPC sessions";
                  }
                  leaf use-pki {
                    type empty;
                    description
                      "Use local-certificate loaded via pki hierarchy";
                  }
                }
              }
            }
            leaf max-connections {
              type union {
                type string {
                  pattern "<.*>|$.*";
                }
                type uint32 {
                  range "1 .. 30";
                }
              }
              default "5";
              description
                "Maximum number of connections";
            }
            leaf routing-instance {
              type string;
              description
                "Routing instance for grpc";
            }
            leaf grpc-keep-alive {
              type union {
                type string {
                  pattern "<.*>|$.*";
                }
                type uint32 {
                  range "0 .. 4294967295";
                }
              }
              units "seconds";
              default "300";
              description
                "GRPC keep alive duration in seconds";
            }
          }
        }
        container traceoptions {
          description
            "Trace options for JSD";
          uses apply-advanced;
          leaf no-remote-trace {
            type empty;
            description
              "Disable remote tracing";
          }
          container file {
            description
              "Trace file information";
            leaf filename {
              type string {
                length "1 .. 1024";
              }
              description
                "Name of file in which to write trace information";
            }
            leaf size {
              type string;
              description
                "Maximum trace file size";
            }
            leaf files {
              type union {
                type string {
                  pattern "<.*>|$.*";
                }
                type uint32 {
                  range "2 .. 1000";
                }
              }
              default "10";
              description
                "Maximum number of trace files";
            }
            choice world-readable-choice {
              leaf world-readable {
                type empty;
                description
                  "Allow any user to read the log file";
              }
              leaf no-world-readable {
                type empty;
                description
                  "Don't allow any user to read the log file";
              }
            }
            leaf match {
              type jt:regular-expression;
              description
                "Regular expression for lines to be logged";
            }
          }
          container level {
            description
              "Trace verbosity level";
            choice level-name {
              case case_1 {
                leaf error {
                  type empty;
                  description
                    "Only trace error events";
                }
              }
            }
          }
          list flag {
            key "name";
            ordered-by user;
            description
              "Tracing parameters";
            leaf name {
              type enumeration {
                enum "timer" {
                  description
                    "Trace internal timer events";
                }
                enum "timeouts" {
                  description
                    "Trace timeouts ";
                }
                enum "routing-socket" {
                  description
                    "Trace routing socket calls";
                }
                enum "general" {
                  description
                    "Trace general events";
                }
                enum "config" {
                  description
                    "Trace config events";
                }
                enum "grpc" {
                  description
                    "Trace grpc related events";
                }
                enum "libgrpc-debug" {
                  description
                    "Trace all lib grpc related events";
                }
                enum "libgrpc-errors" {
                  description
                    "Trace lib grpc errors";
                }
                enum "libgrpc-info" {
                  description
                    "Trace lib grpc info and errors";
                }
                enum "notification" {
                  description
                    "Trace notification events";
                }
                enum "all" {
                  description
                    "Trace everything";
                }
              }
            }
          }
        }
      }
      container grpc-tunnel {
        description
          "GRPC tunnel configuration for outbound TCP over gRPC";
        uses apply-advanced;
        container servers {
          description
            "GRPC tunnel servers configuration";
          uses apply-advanced;
          leaf retry-interval {
            type union {
              type string {
                pattern "<.*>|$.*";
              }
              type uint32 {
                range "10 .. 300";
              }
            }
            units "seconds";
            default "30";
            description
              "Retry interval for unreachable targets";
          }
          list server {
            key "name";
            max-elements 10;
            ordered-by user;
            description
              "List of tunnel servers to be dialled";
            leaf name {
              type string {
                length "1 .. 31";
              }
              description
                "Name of the tunnel server";
            }
            uses apply-advanced;
            leaf address {
              type jt:hostname;
              mandatory true;
              description
                "IP address or hostname of the tunnel server";
            }
            leaf port {
              type union {
                type string {
                  pattern "<.*>|$.*";
                }
                type uint32 {
                  range "1 .. 65535";
                }
              }
              mandatory true;
              description
                "Port number where gRPC tunnel server is listening";
            }
            leaf-list targets {
              type enumeration {
                enum "ssh" {
                  description
                    "Configure SSH to be registered";
                }
                enum "netconf-ssh" {
                  description
                    "Configure NETCONF over SSH to be registered";
                }
                enum "gnmi-gnoi" {
                  description
                    "Configure gNMI and gNOI to be registered";
                }
              }
              ordered-by user;
              description
                "Targets to be registered with the tunnel server";
            }
            leaf routing-instance {
              type string;
              description
                "Routing instance to be used for tunnel server dial-out";
            }
            leaf source-address {
              type jt:ipaddr;
              description
                "Source address to be used for tunnel server dial-out";
            }
            container credentials {
              description
                "Credentials to use for gRPC connection";
              uses apply-advanced;
              choice credential-type {
                case case_1 {
                  container tls {
                    presence "enable tls";
                    description
                      "Configure secure TLS credentials";
                    uses apply-advanced;
                    leaf certificate-id {
                      type string;
                      description
                        "Local certificate ID to be used for gRPC tunnel target";
                    }
                    leaf-list ca-profiles {
                      type string;
                      ordered-by user;
                      description
                        "List of CA profiles to be used to verify tunnel server";
                    }
                  }
                }
              }
            }
          }
        }
        container target-string-option {
          description
            "Option to configure target string for this device";
          uses apply-advanced;
          leaf-list pattern {
            type enumeration {
              enum "hostname" {
                description
                  "Hostname of this device";
              }
              enum "vendor" {
                description
                  "Vendor name";
              }
              enum "model" {
                description
                  "Hardware model";
              }
              enum "version" {
                description
                  "Software version";
              }
              enum "custom" {
                description
                  "Custom string to be used as target string";
              }
            }
            ordered-by user;
            description
              "Ordered list to build customised target string";
          }
          leaf custom-string {
            type string {
              length "1 .. 31";
            }
            description
              "Custom string to be used when 'custom' option is chosen";
          }
          leaf delimiter {
            type string {
              length "1 .. 3";
            }
            description
              "Delimiter to separate the options under pattern";
          }
        }
        container traceoptions {
          description
            "GRPC tunnel trace options";
          uses apply-advanced;
          leaf no-remote-trace {
            type empty;
            description
              "Disable remote tracing";
          }
          container file {
            description
              "Trace file information";
            leaf filename {
              type string {
                length "1 .. 1024";
              }
              description
                "Name of file in which to write trace information";
            }
            leaf size {
              type string;
              description
                "Maximum trace file size";
            }
            leaf files {
              type union {
                type string {
                  pattern "<.*>|$.*";
                }
                type uint32 {
                  range "2 .. 1000";
                }
              }
              default "3";
              description
                "Maximum number of trace files";
            }
            choice world-readable-choice {
              leaf world-readable {
                type empty;
                description
                  "Allow any user to read the log file";
              }
              leaf no-world-readable {
                type empty;
                description
                  "Don't allow any user to read the log file";
              }
            }
            leaf match {
              type jt:regular-expression;
              description
                "Regular expression for lines to be logged";
            }
          }
          leaf level {
            type enumeration {
              enum "error" {
                description
                  "Match error conditions";
              }
              enum "warning" {
                description
                  "Match warning messages";
              }
              enum "notice" {
                description
                  "Match conditions that should be handled specially";
              }
              enum "info" {
                description
                  "Match informational messages";
              }
              enum "verbose" {
                description
                  "Match verbose messages";
              }
              enum "all" {
                description
                  "Match all levels";
              }
            }
            default "error";
            description
              "Level of debugging output";
          }
          list flag {
            key "name";
            ordered-by user;
            description
              "Tracing parameters";
            leaf name {
              type enumeration {
                enum "general" {
                  description
                    "Log general messages";
                }
                enum "grpc-events" {
                  description
                    "Log grpc events with tunnel server";
                }
                enum "timer" {
                  description
                    "Log timer events";
                }
                enum "config" {
                  description
                    "Log configuration messages";
                }
                enum "all" {
                  description
                    "Log all the messages";
                }
              }
            }
          }
        }
      }
      container service-deployment {
        description
          "Configuration for Service Deployment (SDXD) management application";
        uses apply-advanced;
        leaf local-certificate {
          type string {
            length "1 .. 1024";
          }
          description
            "Name of local X.509 certificate to use";
        }
        leaf source-address {
          type jt:ipv4addr;
          description
            "Local IPv4 address to be used as source address for traffic to SDX";
        }
        list servers {
          key "name";
          max-elements 3;
          ordered-by user;
          description
            "Service deployment system configuration";
          leaf name {
            type jt:ipv4addr;
            description
              "IPv4 address of SDX server";
          }
          uses apply-advanced;
          leaf port {
            type union {
              type uint16;
              type string {
                pattern "<.*>|$.*";
              }
            }
            description
              "TCP port of SDX server";
          }
          leaf user {
            type string;
            description
              "Username used by SDX when logging into the router";
          }
          container security-options {
            description
              "Specify mechanism to secure the connection";
            uses apply-advanced;
            choice protocol {
              case case_1 {
                leaf tls {
                  type empty;
                  description
                    "Use TLS for transport layer security";
                }
              }
              case case_2 {
                leaf ssl3 {
                  type empty;
                  description
                    "Use SSLv3 for transport layer security";
                }
              }
            }
          }
        }
        container traceoptions {
          description
            "Service deployment daemon trace options";
          uses apply-advanced;
          leaf no-remote-trace {
            type empty;
            description
              "Disable remote tracing";
          }
          container file {
            description
              "Trace file information";
            leaf filename {
              type string {
                length "1 .. 1024";
              }
              description
                "Name of file in which to write trace information";
            }
            leaf size {
              type string;
              description
                "Maximum trace file size";
            }
            leaf files {
              type union {
                type string {
                  pattern "<.*>|$.*";
                }
                type uint32 {
                  range "2 .. 1000";
                }
              }
              default "3";
              description
                "Maximum number of trace files";
            }
            choice world-readable-choice {
              leaf world-readable {
                type empty;
                description
                  "Allow any user to read the log file";
              }
              leaf no-world-readable {
                type empty;
                description
                  "Don't allow any user to read the log file";
              }
            }
            leaf match {
              type jt:regular-expression;
              description
                "Regular expression for lines to be logged";
            }
          }
          list flag {
            key "name";
            ordered-by user;
            description
              "Tracing options";
            leaf name {
              type enumeration {
                enum "beep" {
                  description
                    "Trace BEEP protocol events";
                }
                enum "profile" {
                  description
                    "Trace BEEP profile events";
                }
                enum "application" {
                  description
                    "Trace application events";
                }
                enum "io" {
                  description
                    "Trace I/O activities";
                }
                enum "all" {
                  description
                    "Trace everything";
                }
              }
            }
          }
        }
      }
      container outbound-ssh {
        description
          "Initiate outbound SSH connection";
        uses apply-advanced;
        leaf routing-instance {
          type string;
          description
            "Routing instance through which client is reachable";
        }
        container traceoptions {
          description
            "Outbound SSH trace options";
          uses apply-advanced;
          leaf no-remote-trace {
            type empty;
            description
              "Disable remote tracing";
          }
          container file {
            description
              "Trace file information";
            leaf filename {
              type string {
                length "1 .. 1024";
              }
              description
                "Name of file in which to write trace information";
            }
            leaf size {
              type string;
              description
                "Maximum trace file size";
            }
            leaf files {
              type union {
                type string {
                  pattern "<.*>|$.*";
                }
                type uint32 {
                  range "2 .. 1000";
                }
              }
              default "3";
              description
                "Maximum number of trace files";
            }
            choice world-readable-choice {
              leaf world-readable {
                type empty;
                description
                  "Allow any user to read the log file";
              }
              leaf no-world-readable {
                type empty;
                description
                  "Don't allow any user to read the log file";
              }
            }
            leaf match {
              type jt:regular-expression;
              description
                "Regular expression for lines to be logged";
            }
          }
          list flag {
            key "name";
            ordered-by user;
            description
              "Tracing parameters";
            leaf name {
              type enumeration {
                enum "configuration" {
                  description
                    "Trace configuration events";
                }
                enum "connectivity" {
                  description
                    "Trace TCP connection handling";
                }
                enum "all" {
                  description
                    "Trace everything";
                }
              }
            }
          }
        }
        list client {
          key "name";
          ordered-by user;
          description
            "Define a device initiated SSH connection";
          leaf name {
            type string;
            description
              "Client application identifier";
          }
          uses apply-advanced;
          leaf disable-ssh-security-settings {
            type empty;
            status deprecated;
            description
              "Disable ssh security parameter defined under [system services ssh]";
          }
          leaf device-id {
            type string;
            mandatory true;
            description
              "Unique ID used by client to identify this device";
          }
          leaf secret {
            type jt:unreadable;
            description
              "Shared secret between client and this device";
          }
          container keep-alive {
            presence "enable keep-alive";
            uses apply-advanced;
            leaf retry {
              type union {
                type uint32;
                type string {
                  pattern "<.*>|$.*";
                }
              }
              default "3";
              description
                "Maximum number of connection attempts";
            }
            leaf timeout {
              type union {
                type uint32;
                type string {
                  pattern "<.*>|$.*";
                }
              }
              default "15";
              description
                "Timeout value for conection attempts";
            }
          }
          leaf reconnect-strategy {
            type enumeration {
              enum "sticky" {
                description
                  "Attempt to reconnect to the server last connected to";
              }
              enum "in-order" {
                description
                  "Attempt to reconnect to the first server configured";
              }
            }
            default "in-order";
            description
              "Strategy used to reconnect to a server";
          }
          leaf services {
            type enumeration {
              enum "netconf" {
                description
                  "Enable invoking NETCONF sub-system";
              }
            }
            description
              "The subsystem(s) that can be invoked";
          }
          list servers {
            key "name";
            ordered-by user;
            description
              "Client application servers";
            leaf name {
              type string;
              description
                "Client address to connect to";
            }
            uses apply-advanced;
            leaf port {
              type union {
                type uint16;
                type string {
                  pattern "<.*>|$.*";
                }
              }
              description
                "Client port to connect to";
            }
            leaf retry {
              type union {
                type uint32;
                type string {
                  pattern "<.*>|$.*";
                }
              }
              default "3";
              description
                "Maximum number of connection attempts";
            }
            leaf timeout {
              type union {
                type uint32;
                type string {
                  pattern "<.*>|$.*";
                }
              }
              default "15";
              description
                "Timeout value for conection attempts";
            }
          }
          container proxy-server {
            description
              "Proxy server to reach the application server";
            uses apply-advanced;
            choice proxy-type {
              case case_1 {
                leaf dhcp {
                  type empty;
                  description
                    "Read proxy server information from DHCP generated file";
                }
              }
              case case_2 {
                container static {
                  description
                    "Proxy server details";
                  uses apply-advanced;
                  leaf host {
                    type string;
                    mandatory true;
                    description
                      "Host name or address";
                  }
                  leaf port {
                    type union {
                      type uint16;
                      type string {
                        pattern "<.*>|$.*";
                      }
                    }
                    default "8080";
                    description
                      "Port number";
                  }
                  container proxy-authorization {
                    description
                      "Credentials for proxy authorization with basic authentication type";
                    uses apply-advanced;
                    leaf user {
                      type string {
                        length "1 .. 255";
                      }
                      mandatory true;
                      description
                        "User name";
                    }
                    leaf password {
                      type string {
                        length "1 .. 255";
                      }
                      mandatory true;
                      description
                        "Password";
                    }
                  }
                }
              }
            }
          }
        }
      }
    }
    container schema {
      description
        "System schema";
      uses apply-advanced;
      container openconfig {
        description
          "Openconfig schema options";
        uses apply-advanced;
        leaf unhide {
          type empty;
          description
            "Unhide openconfig from CLI";
        }
      }
    }
    container statistics-timeout {
      description
        "Statistics - Configurable Timeout";
      uses apply-advanced;
      leaf statistics-timeout-value {
        type union {
          type string {
            pattern "<.*>|$.*";
          }
          type int32 {
            range "1000 .. 60000";
          }
        }
        description
          "Statistics - Configurable Timeout value in milliseconds(1000 to 60000)";
      }
    }
    container icmp {
      presence "enable icmp";
      description
        " ICMP ";
      uses apply-advanced;
      leaf ttl-expired-source-address {
        type jt:ipv4addr;
        description
          "IPv4 address for ttl-expiry";
      }
    }
    leaf time-zone {
      type string;
      units "<continent>/<major-city> or <time-zone>";
      default "UTC";
      description
        "Time zone name or POSIX-compliant time zone string";
    }
    leaf use-imported-time-zones {
      type empty;
      description
        "Use locally generated time-zone database";
    }
    leaf regex-additive-logic {
      type empty;
      description
        "Set regex-additive-logic";
    }
    leaf extended-echo {
      type empty;
      description
        "Enable ICMP extended echo processing";
    }
    leaf dump-device {
      type string;
      description
        "Device to record memory snapshots on operating system failure";
    }
    leaf mirror-flash-on-disk {
      type empty;
      status deprecated;
      description
        "Mirror contents of the flash drive onto hard drive";
    }
    container icmp-rate-limit {
      status deprecated;
      description
        "Rate-limiting parameters for ICMP messages";
      leaf packet-rate {
        type union {
          type uint32;
          type string {
            pattern "<.*>|$.*";
          }
        }
        default "1000";
        description
          "ICMP rate-limiting packets earned per second";
      }
      leaf bucket-size {
        type union {
          type uint32;
          type string {
            pattern "<.*>|$.*";
          }
        }
        units "seconds";
        default "5";
        description
          "ICMP rate-limiting maximum bucket size";
      }
    }
    leaf tcp-ack-rst-syn {
      type empty;
      status deprecated;
      description
        "Send ACKs for in-window RSTs and SYN packets on TCP connections";
    }
    leaf-list authentication-order {
      type enumeration {
        enum "radius" {
          description
            "Remote Authentication Dial-In User Service";
        }
        enum "tacplus" {
          description
            "TACACS+ authentication services";
        }
        enum "password" {
          description
            "Traditional password authentication";
        }
      }
      ordered-by user;
    }
    container name-resolution {
      description
        "Configure hostname resolution behaviour";
      uses apply-advanced;
      container no-resolve-host-on-input {
        presence "enable no-resolve-host-on-input";
        description
          "Do not resolve hostnames at the time of input";
      }
    }
    list radius-server {
      key "name";
      ordered-by user;
      description
        "RADIUS server configuration";
      uses radius-server-object;
    }
    list tacplus-server {
      key "name";
      ordered-by user;
      description
        "TACACS+ server configuration";
      uses tacplus-server-object;
    }
    container password-options {
      description
        "Local password options, password should be configured at [system authentication-order]";
      uses apply-advanced;
      leaf tacplus-authorization {
        type empty;
        description
          "TACACS+ authorization for locally authenticated users";
      }
    }
    container ldap-server {
      presence "enable ldap-server";
      description
        "LDAP server configuration";
      uses apply-advanced;
      leaf-list address {
        type jt:hostname;
        max-elements 2;
        ordered-by user;
        description
          "LDAP authentication server address";
      }
      leaf-list port {
        type union {
          type uint32;
          type string {
            pattern "<.*>|$.*";
          }
        }
        max-elements 2;
        ordered-by user;
        description
          "LDAP authentication server port number";
      }
      leaf base {
        type string;
        mandatory true;
        description
          "LDAP base";
      }
      leaf binddn {
        type string;
        mandatory true;
        description
          "LDAP binddn";
      }
      leaf bindpw {
        type string;
        mandatory true;
        description
          "LDAP bindpw";
      }
      leaf routing-instance {
        type string;
        description
          "LDAP routing instance";
      }
      leaf ldaps-cert {
        type string;
        mandatory true;
        description
          "LDAPS client certificate id";
      }
    }
    container accounting {
      description
        "System accounting configuration";
      uses apply-advanced;
      leaf-list events {
        type enumeration {
          enum "login" {
            description
              "Login session";
          }
          enum "change-log" {
            description
              "Configuration changes";
          }
          enum "interactive-commands" {
            description
              "Commands";
          }
        }
        description
          "Events to be logged";
      }
      leaf enhanced-avs-max {
        type union {
          type string {
            pattern "<.*>|$.*";
          }
          type int32 {
            range "7 .. 15";
          }
        }
        default "7";
        description
          "No. of AV pairs each of which can store a max of 250 Bytes";
      }
      container traceoptions {
        description
          "Trace options for system accounting";
        uses apply-advanced;
        leaf no-remote-trace {
          type empty;
          description
            "Disable remote tracing";
        }
        container file {
          description
            "Trace file information";
          leaf filename {
            type string {
              length "1 .. 1024";
            }
            description
              "Name of file in which to write trace information";
          }
          leaf size {
            type string;
            description
              "Maximum trace file size";
          }
          leaf files {
            type union {
              type string {
                pattern "<.*>|$.*";
              }
              type uint32 {
                range "2 .. 1000";
              }
            }
            default "3";
            description
              "Maximum number of trace files";
          }
          choice world-readable-choice {
            leaf world-readable {
              type empty;
              description
                "Allow any user to read the log file";
            }
            leaf no-world-readable {
              type empty;
              description
                "Don't allow any user to read the log file";
            }
          }
        }
        list flag {
          key "name";
          ordered-by user;
          description
            "Tracing parameters";
          leaf name {
            type enumeration {
              enum "all" {
                description
                  "Trace all operations";
              }
              enum "events" {
                description
                  "Trace accounting events and their processing";
              }
              enum "config" {
                description
                  "Trace configuration processing";
              }
              enum "radius" {
                description
                  "Trace RADIUS processing";
              }
              enum "tacplus" {
                description
                  "Trace TACPLUS processing";
              }
            }
          }
        }
      }
      container destination {
        description
          "Destination for system accounting records";
        uses apply-advanced;
        container radius {
          presence "enable radius";
          description
            "Configure RADIUS accounting";
          uses apply-advanced;
          list server {
            key "name";
            ordered-by user;
            description
              "RADIUS accounting server configuration";
            uses radius-server-object;
          }
        }
        container tacplus {
          presence "enable tacplus";
          description
            "Send TACACS+ accounting records";
          uses apply-advanced;
          list server {
            key "name";
            ordered-by user;
            description
              "TACACS+ server configuration";
            uses tacplus-server-object;
          }
        }
      }
    }
    leaf allow-icmp4-extension {
      type empty;
      description
        "Allow icmp4 to add additional data structures in the extension";
    }
    leaf allow-icmp6-extension {
      type empty;
      description
        "Allow icmp6 to add additional data structures in the extension";
    }
    container syslog {
      description
        "System logging facility";
      uses apply-advanced;
      container archive {
        presence "enable archive";
        description
          "Archive file information";
        uses archive-object;
      }
      list user {
        key "name";
        ordered-by user;
        description
          "Notify a user of the event";
        leaf name {
          type string;
          description
            "Name of user to notify";
        }
        uses apply-advanced;
        list contents {
          key "name";
          uses syslog-object;
        }
        leaf match {
          type jt:regular-expression;
          description
            "Regular expression for lines to be logged";
        }
        leaf allow-duplicates {
          type empty;
          description
            "Do not suppress the repeated message";
        }
        leaf-list match-strings {
          type string;
          max-elements 50;
          ordered-by user;
          description
            "Matching string(s) for lines to be logged";
        }
      }
      list host {
        key "name";
        ordered-by user;
        description
          "Host to be notified";
        leaf name {
          type string;
          description
            "Name of host to notify";
        }
        uses apply-advanced;
        list contents {
          key "name";
          uses syslog-object;
        }
        leaf match {
          type jt:regular-expression;
          description
            "Regular expression for lines to be logged";
        }
        leaf allow-duplicates {
          type empty;
          description
            "Do not suppress the repeated message";
        }
        leaf port {
          type union {
            type uint16;
            type string {
              pattern "<.*>|$.*";
            }
          }
          description
            "Port number";
        }
        leaf facility-override {
          type enumeration {
            enum "authorization" {
              description
                "Authorization system";
            }
            enum "daemon" {
              description
                "Various system processes";
            }
            enum "ftp" {
              description
                "FTP process";
            }
            enum "kernel" {
              description
                "Kernel";
            }
            enum "user" {
              description
                "User processes";
            }
            enum "local0" {
              description
                "Local logging option number 0";
            }
            enum "local1" {
              description
                "Local logging option number 1";
            }
            enum "local2" {
              description
                "Local logging option number 2";
            }
            enum "local3" {
              description
                "Local logging option number 3";
            }
            enum "local4" {
              description
                "Local logging option number 4";
            }
            enum "local5" {
              description
                "Local logging option number 5";
            }
            enum "local6" {
              description
                "Local logging option number 6";
            }
            enum "local7" {
              description
                "Local logging option number 7";
            }
          }
          description
            "Alternate facility for logging to remote host";
        }
        leaf log-prefix {
          type string;
          description
            "Prefix for all logging to this host";
        }
        leaf source-address {
          type jt:ipaddr;
          description
            "Use specified address as source address";
        }
        leaf explicit-priority {
          type empty;
          description
            "Include priority and facility in messages";
        }
        leaf exclude-hostname {
          type empty;
          description
            "Exclude hostname field in messages";
        }
        leaf transport {
          type enumeration {
            enum "tcp" {
              description
                "TCP as transport for syslog";
            }
            enum "udp" {
              description
                "UDP as transport for syslog";
            }
            enum "tls" {
              description
                "TLS as transport for syslog";
            }
          }
          default "udp";
          description
            "Transport type";
        }
        leaf-list match-strings {
          type string;
          max-elements 50;
          ordered-by user;
          description
            "Matching string(s) for lines to be logged";
        }
        container structured-data {
          presence "enable structured-data";
          description
            "Log system message in structured format";
          uses apply-advanced;
          choice format {
            case case_1 {
              leaf brief {
                type empty;
                description
                  "Omit English-language text from end of logged message";
              }
            }
          }
        }
      }
      leaf allow-duplicates {
        type empty;
        description
          "Do not suppress the repeated message for all targets";
      }
      list file {
        key "name";
        description
          "File in which to log data";
        leaf name {
          type string {
            length "1 .. 1024";
          }
          description
            "Name of file in which to log data";
        }
        uses apply-advanced;
        list contents {
          key "name";
          uses syslog-object;
        }
        leaf match {
          type jt:regular-expression;
          description
            "Regular expression for lines to be logged";
        }
        leaf allow-duplicates {
          type empty;
          description
            "Do not suppress the repeated message";
        }
        container archive {
          presence "enable archive";
          description
            "Archive file information";
          uses archive-object;
        }
        leaf explicit-priority {
          type empty;
          description
            "Include priority and facility in messages";
        }
        leaf-list match-strings {
          type string;
          max-elements 50;
          ordered-by user;
          description
            "Matching string(s) for lines to be logged";
        }
        container structured-data {
          presence "enable structured-data";
          description
            "Log system message in structured format";
          uses apply-advanced;
          choice format {
            case case_1 {
              leaf brief {
                type empty;
                description
                  "Omit English-language text from end of logged message";
              }
            }
          }
        }
      }
      list console {
        key "name";
        description
          "Console logging";
        leaf name {
          type enumeration {
            enum "any" {
              description
                "All facilities";
            }
            enum "authorization" {
              description
                "Authorization system";
            }
            enum "daemon" {
              description
                "Various system processes";
            }
            enum "ftp" {
              description
                "FTP process";
            }
            enum "ntp" {
              description
                "NTP process";
            }
            enum "security" {
              description
                "Security related";
            }
            enum "kernel" {
              description
                "Kernel";
            }
            enum "user" {
              description
                "User processes";
            }
            enum "dfc" {
              description
                "Dynamic flow capture";
            }
            enum "external" {
              description
                "Local external applications";
            }
            enum "firewall" {
              description
                "Firewall filtering system";
            }
            enum "pfe" {
              description
                "Packet Forwarding Engine";
            }
            enum "conflict-log" {
              description
                "Configuration conflict log";
            }
            enum "change-log" {
              description
                "Configuration change log";
            }
            enum "interactive-commands" {
              description
                "Commands executed by the UI";
            }
            enum "application-status" {
              description
                "Application stop / start status";
            }
          }
          description
            "Facility type";
        }
        choice level {
          case case_1 {
            leaf any {
              type empty;
              description
                "All levels";
            }
          }
          case case_2 {
            leaf emergency {
              type empty;
              description
                "Panic conditions";
            }
          }
          case case_3 {
            leaf alert {
              type empty;
              description
                "Conditions that should be corrected immediately";
            }
          }
          case case_4 {
            leaf critical {
              type empty;
              description
                "Critical conditions";
            }
          }
          case case_5 {
            leaf error {
              type empty;
              description
                "Error conditions";
            }
          }
          case case_6 {
            leaf warning {
              type empty;
              description
                "Warning messages";
            }
          }
          case case_7 {
            leaf notice {
              type empty;
              description
                "Conditions that should be handled specially";
            }
          }
          case case_8 {
            leaf info {
              type empty;
              description
                "Informational messages";
            }
          }
          case case_9 {
            leaf none {
              type empty;
              description
                "No messages";
            }
          }
        }
      }
      container time-format {
        presence "enable time-format";
        description
          "Additional information to include in system log timestamp";
        leaf year {
          type empty;
          description
            "Include year in timestamp";
        }
        leaf millisecond {
          type empty;
          description
            "Include milliseconds in timestamp";
        }
      }
      leaf source-address {
        type jt:ipaddr;
        description
          "Use specified address as source address";
      }
      leaf log-rotate-frequency {
        type union {
          type string {
            pattern "<.*>|$.*";
          }
          type uint32 {
            range "1 .. 59";
          }
        }
        units "minutes";
        default "15";
        description
          "Rotate log frequency";
      }
      container server {
        presence "enable server";
        description
          "Enable syslog server";
        uses apply-advanced;
        list routing-instances {
          key "name";
          ordered-by user;
          description
            "Enable/disable syslog server in routing-instances";
          leaf name {
            type string;
            description
              "Routing instance name";
          }
          uses apply-advanced;
          container disable {
            presence "enable disable";
            description
              "Disable syslog server in this routing instance";
          }
        }
      }
      leaf alternate-format {
        type empty;
        description
          "Append node name with daemon name instead of hostname(default) in the log entries";
      }
    }
    choice compress-configuration-files-choice {
      leaf compress-configuration-files {
        type empty;
        description
          "Compress the router configuration files";
      }
      leaf no-compress-configuration-files {
        type empty;
        description
          "Don't compress the router configuration files";
      }
    }
    container license {
      description
        "License information for the router";
      uses license-object;
    }
    container kernel-options {
      description
        "Kernel options: selectively enable few knobs";
      uses apply-advanced;
      leaf select-active-unilist-member {
        type empty;
        status deprecated;
        description
          "Select active unilist member for host path forwarding";
      }
    }
    leaf netlink-async-mode {
      type empty;
      description
        "Enable async mode in nlsd";
    }
    container snapshot {
      description
        "System snapshot";
      uses apply-advanced;
      container recovery {
        description
          "System snapshot recovery management";
        uses apply-advanced;
        leaf on-upgrade {
          type empty;
          description
            "Update the recovery snapshot when the JUNOS release changes";
        }
        leaf configuration-only {
          type empty;
          description
            "Save configuration only, snapshot updated when out-of-date";
        }
        choice automatic-choice {
          leaf automatic {
            type empty;
            description
              "Automatically recover junos volume when necessary";
          }
          leaf no-automatic {
            type empty;
            description
              "Don't automatically recover junos volume when necessary";
          }
        }
        leaf-list configuration-preference {
          type enumeration {
            enum "config" {
              description
                "Use '/config/juniper.conf.gz' if available";
            }
            enum "snapshot" {
              description
                "Use configuration saved in snapshot";
            }
          }
          ordered-by user;
          description
            "Configuration to use when booting a snapshot from OAM";
        }
      }
      choice configuration-choice {
        leaf configuration {
          type empty;
          description
            "Save configuration in snapshot";
        }
        leaf no-configuration {
          type empty;
          description
            "Don't save configuration in snapshot";
        }
      }
    }
    container processes {
      description
        "Process control";
      uses apply-advanced;
      container routing {
        description
          "Routing process";
        uses apply-advanced;
        container bgp {
          description
            "BGP protocol control";
          uses apply-advanced;
          container rib-sharding {
            presence "enable rib-sharding";
            description
              "Enable BGP RIB sharding";
            uses apply-advanced;
            leaf number-of-shards {
              type union {
                type string {
                  pattern "<.*>|$.*";
                }
                type uint32 {
                  range "1 .. 31";
                }
              }
              description
                "Set number of sharding threads";
            }
          }
          container update-threading {
            presence "enable update-threading";
            description
              "Enable BGP update threading";
            uses apply-advanced;
            leaf number-of-threads {
              type union {
                type string {
                  pattern "<.*>|$.*";
                }
                type uint32 {
                  range "1 .. 128";
                }
              }
              description
                "Set number of update threads";
            }
            leaf group-split-size {
              type union {
                type string {
                  pattern "<.*>|$.*";
                }
                type uint32 {
                  range "0 .. 2000";
                }
              }
              description
                "Threshold value to assign a new update thread for group";
            }
          }
          leaf tcp-listen-port {
            type union {
              type string {
                pattern "<.*>|$.*";
              }
              type uint16 {
                range "1 .. 65535";
              }
            }
            description
              "TCP port number to accept incoming BGP connections";
          }
        }
      }
    }
  }

  grouping archive-object {
    uses apply-advanced;
    leaf size {
      type string;
      units "bytes";
      description
        "Size of files to be archived";
    }
    leaf files {
      type string;
      description
        "Number of files to be archived";
    }
    choice world-readable-choice {
      leaf world-readable {
        type empty;
        description
          "Allow any user to read the log file";
      }
      leaf no-world-readable {
        type empty;
        description
          "Don't allow any user to read the log file";
      }
    }
    choice binary-data-choice {
      leaf binary-data {
        type empty;
        description
          "Mark file as if it contains binary data";
      }
      leaf no-binary-data {
        type empty;
        description
          "Don't mark file as if it contains binary data";
      }
    }
    leaf transfer-interval {
      type union {
        type string {
          pattern "<.*>|$.*";
        }
        type uint32 {
          range "5 .. 2880";
        }
      }
      units "minutes";
      description
        "Frequency at which to transfer files to archive sites";
    }
    leaf start-time {
      type jt:time;
      description
        "Start time for file transmission (yyyy-mm-dd.hh:mm)";
    }
    list archive-sites {
      key "name";
      ordered-by user;
      leaf name {
        type string;
        description
          "Primary and failover URLs to receive archive files";
      }
      leaf password {
        type jt:unreadable;
        description
          "Password for login into the archive site";
      }
      leaf routing-instance {
        type string;
        description
          "Routing instance";
      }
    }
  }

  grouping authentication-object {
    description
      "Authentication method";
    uses apply-advanced;
    leaf plain-text-password-value {
      type string;
      description
        "Plain text password";
    }
    leaf encrypted-password {
      type string {
        length "1 .. 128";
      }
      description
        "Encrypted password string";
    }
    leaf no-public-keys {
      type empty;
      description
        "Disables SSH public key based authentication";
    }
    list ssh-rsa {
      key "name";
      ordered-by user;
      description
        "Secure shell (SSH) RSA public key string";
      leaf name {
        type string;
        description
          "Secure shell (SSH) RSA public key string";
      }
      uses apply-advanced;
      leaf key-options {
        type string;
        description
          "SSH key options";
      }
      leaf from {
        type string;
        description
          "Pattern-list of allowed hosts";
      }
    }
    list ssh-dsa {
      key "name";
      ordered-by user;
      status deprecated;
      description
        "Secure shell (SSH) DSA public key string";
      leaf name {
        type string;
        description
          "Secure shell (SSH) DSA public key string";
      }
      uses apply-advanced;
      leaf key-options {
        type string;
        description
          "SSH key options";
      }
      leaf from {
        type string;
        description
          "Pattern-list of allowed hosts";
      }
    }
    list ssh-ecdsa {
      key "name";
      ordered-by user;
      description
        "Secure shell (SSH) ECDSA public key string";
      leaf name {
        type string;
        description
          "Secure shell (SSH) ECDSA public key string";
      }
      uses apply-advanced;
      leaf key-options {
        type string;
        description
          "SSH key options";
      }
      leaf from {
        type string;
        description
          "Pattern-list of allowed hosts";
      }
    }
    list ssh-ed25519 {
      key "name";
      ordered-by user;
      description
        "Secure shell (SSH) ED25519 public key string";
      leaf name {
        type string;
        description
          "Secure shell (SSH) EC25519 public key string";
      }
      uses apply-advanced;
      leaf key-options {
        type string;
        description
          "SSH key options";
      }
      leaf from {
        type string;
        description
          "Pattern-list of allowed hosts";
      }
    }
  }

  grouping ldp-sync-obj {
    uses apply-advanced;
    choice enable-disable {
      case case_1 {
        leaf disable {
          type empty;
          description
            "Disable LDP synchronization";
        }
      }
    }
    leaf hold-time {
      type union {
        type string {
          pattern "<.*>|$.*";
        }
        type uint32 {
          range "1 .. 65535";
        }
      }
      description
        "Time during which maximum metric is advertised";
    }
  }

  grouping ldp_filter_obj {
    description
      "Filter to apply to tracing";
    leaf match-on {
      type enumeration {
        enum "fec" {
          description
            "Filter based on FEC associated to the traced object.";
        }
        enum "address" {
          description
            "Filter based on packet source and destination addresses.";
        }
      }
      mandatory true;
      description
        "Argument on which to match";
    }
    leaf-list policy {
      type jt:policy-algebra;
      ordered-by user;
      description
        "Filter policy";
    }
  }

  grouping license-object {
    description
      "License configuration for this router";
    uses apply-advanced;
    container autoupdate {
      presence "enable autoupdate";
      description
        "Autoupdate license keys from license servers";
      uses apply-advanced;
      list url {
        key "name";
        max-elements 10;
        ordered-by user;
        description
          "URL of a license server";
        leaf name {
          type string;
          description
            "URL of a license server for license keys";
        }
        leaf password {
          type jt:unreadable;
          description
            "Password of URL for a license server";
        }
      }
    }
    container log-frequency {
      description
        "Generate a syslog message for nagging";
      choice time_choice {
        case case_1 {
          leaf time-of-day {
            type jt:time-of-day;
            description
              "Time of day at which to log nag message (hh:mm)";
          }
        }
        case case_2 {
          leaf time-interval {
            type union {
              type string {
                pattern "<.*>|$.*";
              }
              type uint32 {
                range "60 .. 86400";
              }
            }
            units "seconds";
            description
              "Frequency for logging nag message (multiples of 60)";
          }
        }
      }
    }
    container renew {
      presence "enable renew";
      description
        "License renew lead time and checking interval";
      leaf before-expiration {
        type union {
          type string {
            pattern "<.*>|$.*";
          }
          type uint32 {
            range "0 .. 60";
          }
        }
        mandatory true;
        description
          "License renew lead time before expiration in days";
      }
      leaf interval {
        type union {
          type string {
            pattern "<.*>|$.*";
          }
          type uint32 {
            range "1 .. 336";
          }
        }
        mandatory true;
        description
          "License checking interval in hours";
      }
    }
    container traceoptions {
      description
        "Trace options for licenses";
      uses apply-advanced;
      leaf no-remote-trace {
        type empty;
        description
          "Disable remote tracing";
      }
      container file {
        description
          "Trace file information";
        leaf filename {
          type string {
            length "1 .. 1024";
          }
          description
            "Name of file in which to write trace information";
        }
        leaf size {
          type string;
          description
            "Maximum trace file size";
        }
        leaf files {
          type union {
            type string {
              pattern "<.*>|$.*";
            }
            type uint32 {
              range "2 .. 1000";
            }
          }
          default "3";
          description
            "Maximum number of trace files";
        }
        choice world-readable-choice {
          leaf world-readable {
            type empty;
            description
              "Allow any user to read the log file";
          }
          leaf no-world-readable {
            type empty;
            description
              "Don't allow any user to read the log file";
          }
        }
        leaf match {
          type jt:regular-expression;
          description
            "Regular expression for lines to be logged";
        }
      }
      list flag {
        key "name";
        ordered-by user;
        description
          "Tracing parameters";
        leaf name {
          type enumeration {
            enum "all" {
              description
                "Trace all operations";
            }
            enum "events" {
              description
                "Trace licensing events and their processing";
            }
            enum "config" {
              description
                "Trace license configuration processing";
            }
          }
        }
      }
    }
    container keys {
      presence "enable keys";
      description
        "License keys";
      uses apply-advanced;
      list key {
        key "name";
        ordered-by user;
        description
          "License key";
        leaf name {
          type string;
          description
            "License key";
        }
        uses apply-advanced;
      }
    }
    choice mode-selection {
      case case_1 {
        leaf standalone-mode {
          type empty;
          description
            "Forcing the node to standalone licensing";
        }
      }
    }
  }

  grouping log-object {
    description
      "Configure auditable security logs";
    uses apply-advanced;
    list exclude {
      key "name";
      ordered-by user;
      status deprecated;
      description
        "List of security log criteria to exclude from the audit log";
      leaf name {
        type string;
        description
          "Exclude criteria name";
      }
      uses apply-advanced;
      leaf destination-address {
        type jt:ipaddr;
        description
          "Destination address";
      }
      leaf destination-port {
        type union {
          type uint32;
          type string {
            pattern "<.*>|$.*";
          }
        }
        description
          "Destination port";
      }
      leaf event-id {
        type string;
        description
          "Event ID filter";
      }
      leaf failure {
        type empty;
        description
          "Event was a failure";
      }
      leaf interface-name {
        type string;
        description
          "Name of interface";
      }
      leaf policy-name {
        type string;
        description
          "Policy name filter";
      }
      leaf process {
        type string;
        description
          "Process that generated the event";
      }
      leaf protocol {
        type string;
        description
          "Protocol filter";
      }
      leaf source-address {
        type jt:ipaddr;
        description
          "Source address";
      }
      leaf source-port {
        type union {
          type uint32;
          type string {
            pattern "<.*>|$.*";
          }
        }
        description
          "Source port";
      }
      leaf success {
        type empty;
        description
          "Event was successful";
      }
      leaf username {
        type string;
        description
          "Username filter";
      }
    }
    leaf limit {
      type union {
        type uint32;
        type string {
          pattern "<.*>|$.*";
        }
      }
      default "10000";
      status deprecated;
      description
        "Limit number of security log entries to keep in memory";
    }
    container cache {
      presence "enable cache";
      description
        "Cache security log events in the audit log buffer";
      uses apply-advanced;
      list exclude {
        key "name";
        ordered-by user;
        description
          "List of security log criteria to exclude from the audit log";
        leaf name {
          type string;
          description
            "Exclude criteria name";
        }
        uses apply-advanced;
        leaf destination-address {
          type jt:ipaddr;
          description
            "Destination address";
        }
        leaf destination-port {
          type union {
            type uint32;
            type string {
              pattern "<.*>|$.*";
            }
          }
          description
            "Destination port";
        }
        leaf event-id {
          type string;
          description
            "Event ID filter";
        }
        leaf failure {
          type empty;
          description
            "Event was a failure";
        }
        leaf interface-name {
          type string;
          description
            "Name of interface";
        }
        leaf policy-name {
          type string;
          description
            "Policy name filter";
        }
        leaf process {
          type string;
          description
            "Process that generated the event";
        }
        leaf protocol {
          type string;
          description
            "Protocol filter";
        }
        leaf source-address {
          type jt:ipaddr;
          description
            "Source address";
        }
        leaf source-port {
          type union {
            type uint32;
            type string {
              pattern "<.*>|$.*";
            }
          }
          description
            "Source port";
        }
        leaf success {
          type empty;
          description
            "Event was successful";
        }
        leaf username {
          type string;
          description
            "Username filter";
        }
      }
      leaf limit {
        type union {
          type uint32;
          type string {
            pattern "<.*>|$.*";
          }
        }
        default "10000";
        description
          "Limit number of security log entries to keep in memory";
      }
    }
  }

  grouping login-class-object {
    leaf name {
      type string;
      description
        "Login class name";
    }
    uses apply-advanced;
    leaf-list allowed-days {
      type enumeration {
        enum "sunday" {
          description
            "Sunday";
        }
        enum "monday" {
          description
            "Monday";
        }
        enum "tuesday" {
          description
            "Tuesday";
        }
        enum "wednesday" {
          description
            "Wednesday";
        }
        enum "thursday" {
          description
            "Thursday";
        }
        enum "friday" {
          description
            "Friday";
        }
        enum "saturday" {
          description
            "Saturday";
        }
      }
      ordered-by user;
      description
        "Day(s) of week when access is allowed.";
    }
    leaf access-start {
      type jt:time-of-day;
      description
        "Start time for remote access (hh:mm)";
    }
    leaf access-end {
      type jt:time-of-day;
      description
        "End time for remote access (hh:mm)";
    }
    leaf idle-timeout {
      type union {
        type uint32;
        type string {
          pattern "<.*>|$.*";
        }
      }
      units "minutes";
      description
        "Maximum idle time before logout";
    }
    leaf logical-system {
      type string;
      description
        "Logical system associated with login";
    }
    leaf tenant {
      type string;
      description
        "Tenant associated with this login";
    }
    leaf login-alarms {
      type empty;
      description
        "Display system alarms when logging in";
    }
    leaf login-script {
      type string;
      description
        "Execute this login-script when logging in";
    }
    leaf login-tip {
      type empty;
      description
        "Display tip when logging in";
    }
    leaf no-sftp-server {
      type empty;
      description
        "Disable incoming SFTP connections";
    }
    leaf-list permissions {
      type string;
      ordered-by user;
    }
    leaf allow-commands {
      type jt:regular-expression;
      description
        "Regular expression for commands to allow explicitly";
    }
    leaf deny-commands {
      type jt:regular-expression;
      description
        "Regular expression for commands to deny explicitly";
    }
    leaf allow-configuration {
      type jt:regular-expression;
      description
        "Regular expression for configure to allow explicitly";
    }
    leaf deny-configuration {
      type jt:regular-expression;
      description
        "Regular expression for configure to deny explicitly";
    }
    leaf-list allow-commands-regexps {
      type string;
      ordered-by user;
      description
        "Object path regular expressions to allow commands";
    }
    leaf-list deny-commands-regexps {
      type string;
      ordered-by user;
      description
        "Object path regular expressions to deny commands";
    }
    leaf-list allow-configuration-regexps {
      type string;
      ordered-by user;
      description
        "Object path regular expressions to allow";
    }
    leaf-list deny-configuration-regexps {
      type string;
      ordered-by user;
      description
        "Object path regular expressions to deny";
    }
    leaf allow-configuration-exact-match {
      type jt:regular-expression;
      description
        "Regular expression for configure to allow exact match explicitly";
    }
    leaf deny-configuration-exact-match {
      type jt:regular-expression;
      description
        "Regular expression for configure to deny exact match explicitly";
    }
    leaf-list allow-grpc-rpc-regexps {
      type string;
      ordered-by user;
      description
        "Regular expressions of gRPC rpcs to be allowed";
    }
    leaf-list deny-grpc-rpc-regexps {
      type string;
      ordered-by user;
      description
        "Regular expressions of gRPC rpcs to be denied";
    }
    leaf configuration-breadcrumbs {
      type empty;
      description
        "Enable breadcrumbs during display of configuration";
    }
    list confirm-commands {
      key "name";
      ordered-by user;
      description
        "List of commands to be confirmed explicitly";
      leaf name {
        type jt:regular-expression;
        description
          "Regular expression for confirm commands";
      }
      uses apply-advanced;
      leaf message {
        type string;
        description
          "Message to be displayed during confirmation";
      }
    }
    choice hidden-commands {
      case case_1 {
        leaf allow-hidden-commands {
          type empty;
          description
            "Allow all hidden commands to be executed";
        }
      }
      case case_2 {
        container no-hidden-commands {
          description
            "Deny all hidden commands with exemptions";
          uses apply-advanced;
          list except {
            key "name";
            ordered-by user;
            description
              "Specify the list of hidden command to be exempted";
            leaf name {
              type string;
              description
                "Exempted hidden command(s)";
            }
            uses apply-advanced;
          }
        }
      }
    }
    container cli {
      uses apply-advanced;
      leaf prompt {
        type string {
          length "1 .. 255";
        }
        description
          "Cli prompt name for this class";
      }
      container timestamp {
        presence "enable timestamp";
        description
          "Cli Timestamp for this class (default format is '%b %d %T')";
        uses apply-advanced;
        leaf format {
          type string;
          default "%b %d %T";
          description
            "Timestamp format (default is '%b %d %T')";
        }
      }
    }
    leaf web-ui-hidden-menus {
      type string;
      description
        "Hidden menus in web user interface";
    }
    leaf web-ui-read-only-menus {
      type string;
      description
        "Read only menus in web user interface";
    }
    leaf security-role {
      type enumeration {
        enum "audit-administrator" {
          description
            "Audit administrator";
        }
        enum "crypto-administrator" {
          description
            "Cryptographic administrator";
        }
        enum "ids-administrator" {
          description
            "IDS administrator";
        }
        enum "security-administrator" {
          description
            "Security administrator";
        }
      }
      description
        "Common Criteria security role";
    }
  }

  grouping login-user-object {
    leaf name {
      type string;
      description
        "User name (login)";
    }
    uses apply-advanced;
    leaf full-name {
      type string {
        length "1 .. 255";
      }
      description
        "Full name";
    }
    container cli {
      uses apply-advanced;
      leaf prompt {
        type string {
          length "1 .. 255";
        }
        description
          "Cli prompt name for this user";
      }
      container timestamp {
        presence "enable timestamp";
        description
          "Cli Timestamp for this class (default format is '%b %d %T')";
        uses apply-advanced;
        leaf format {
          type string;
          default "%b %d %T";
          description
            "Timestamp format (default is '%b %d %T')";
        }
      }
      choice allow-syslog-output-choice {
        leaf allow-syslog-output {
          type empty;
          description
            "Enable monitor and syslog output";
        }
        leaf no-allow-syslog-output {
          type empty;
          description
            "Don't enable monitor and syslog output";
        }
      }
    }
    leaf uid {
      type union {
        type string {
          pattern "<.*>|$.*";
        }
        type uint32 {
          range "100 .. 64000";
        }
      }
      description
        "User identifier (uid)";
    }
    leaf class {
      type string;
      mandatory true;
      description
        "Login class";
    }
    container authentication {
      description
        "Authentication method";
      uses authentication-object;
    }
    leaf-list authorized-principals {
      type string;
      ordered-by user;
      description
        "List of authorized principals";
    }
    leaf authorized-principals-file {
      type string;
      description
        "File containing list of authorized principals";
    }
  }

  grouping lsp_nh_obj {
    leaf name {
      type string;
      mandatory true;
      description
        "LSP to use to reach destination";
    }
    uses apply-advanced;
    leaf preference {
      type union {
        type uint32;
        type string {
          pattern "<.*>|$.*";
        }
      }
      description
        "Preference of LSP next hop";
    }
    leaf metric {
      type union {
        type uint32;
        type string {
          pattern "<.*>|$.*";
        }
      }
      description
        "Metric of LSP next hop";
    }
  }

  grouping macro-data-type {
    leaf name {
      type string;
      description
        "Keyword part of the keyword-value pair";
    }
    leaf value {
      type string;
      description
        "Value part of the keyword-value pair";
    }
  }

  grouping martian_type {
    description
      "Invalid routes";
    leaf address {
      type jt:ipprefix;
      description
        "IP address or hostname";
    }
    leaf choice-ident {
      type enumeration {
        enum "exact";
        enum "longer";
        enum "orlonger";
        enum "upto";
        enum "through";
        enum "prefix-length-range";
      }
    }
    leaf choice-value {
      type string;
    }
    leaf allow {
      type empty;
    }
  }

  grouping metric_expression_type {
    uses apply-advanced;
    container metric {
      description
        "Parameters for metric attribute";
      leaf multiplier {
        type decimal64 {
          fraction-digits 9;
        }
        description
          "Coefficient for metric attribute";
      }
      leaf offset {
        type union {
          type int32;
          type string {
            pattern "<.*>|$.*";
          }
        }
        description
          "Offset for metric attribute";
      }
    }
    container metric2 {
      description
        "Parameters for metric2 attribute";
      leaf multiplier {
        type decimal64 {
          fraction-digits 9;
        }
        default "1.0";
        description
          "Coefficient for metric2 attribute";
      }
      leaf offset {
        type union {
          type int32;
          type string {
            pattern "<.*>|$.*";
          }
        }
        description
          "Offset for metric2 attribute";
      }
    }
  }

  grouping mpls_filter {
    description
      "Define a MPLS firewall filter";
    leaf name {
      type string {
        length "1 .. 127";
      }
      description
        "Filter name";
    }
    uses apply-advanced;
    list term {
      key "name";
      max-elements 16;
      ordered-by user;
      description
        "Define a firewall term";
      leaf name {
        type string {
          length "1 .. 127";
        }
        description
          "Term name";
      }
      uses apply-advanced;
      container from {
        description
          "Define match criteria";
        uses apply-advanced;
        leaf exp {
          type string;
          description
            "Match MPLS EXP bits - Range of values between 0 and 7 in decimal, hex or binary";
        }
        leaf label {
          type string;
          description
            "Match MPLS label value - Range of values between 0 and 1048575 in decimal or hex";
        }
      }
      container then {
        description
          "Action to take if the 'from' condition is matched";
        uses apply-advanced;
        choice designation {
          case case_1 {
            leaf accept {
              type empty;
              description
                "Accept the packet";
            }
          }
          case case_2 {
            leaf discard {
              type empty;
              description
                "Discard the packet";
            }
          }
        }
        leaf count {
          type string {
            length "1 .. 127";
          }
          description
            "Count the packet in the named counter";
        }
        leaf log {
          type empty;
          description
            "Log the packet";
        }
        leaf syslog {
          type empty;
          description
            "System log (syslog) information about the packet";
        }
      }
    }
  }

  grouping mrp-trace-options {
    description
      "Trace options for MMRP Protocol";
    uses apply-advanced;
    container file {
      description
        "Trace file options";
      leaf filename {
        type string {
          length "1 .. 1024";
        }
        description
          "Name of file in which to write trace information";
      }
      leaf replace {
        type empty;
        status deprecated;
        description
          "Replace trace file rather than appending to it";
      }
      leaf size {
        type string;
        description
          "Maximum trace file size";
      }
      leaf files {
        type union {
          type string {
            pattern "<.*>|$.*";
          }
          type uint32 {
            range "2 .. 1000";
          }
        }
        default "10";
        description
          "Maximum number of trace files";
      }
      leaf no-stamp {
        type empty;
        status deprecated;
        description
          "Do not timestamp trace file";
      }
      choice world-readable-choice {
        leaf world-readable {
          type empty;
          description
            "Allow any user to read the log file";
        }
        leaf no-world-readable {
          type empty;
          description
            "Don't allow any user to read the log file";
        }
      }
    }
    list flag {
      key "name";
      ordered-by user;
      description
        "Tracing parameters";
      leaf name {
        type enumeration {
          enum "events" {
            description
              "Trace events to the protocol state machine";
          }
          enum "pdu" {
            description
              "Trace RAPS PDU reception and transmission";
          }
          enum "timers" {
            description
              "Trace protocol timers";
          }
          enum "state-machine" {
            description
              "Trace information of the state machine";
          }
          enum "socket" {
            description
              "Trace soccket activity";
          }
          enum "error" {
            description
              "Trace all failure conditions";
          }
          enum "all" {
            description
              "Trace all";
          }
        }
      }
      leaf disable {
        type empty;
        description
          "Disable this trace flag";
      }
    }
  }

  grouping network_type {
    leaf name {
      type jt:ipprefix;
      description
        "Network prefix";
    }
    uses apply-advanced;
    leaf-list dyn-tunnel-attribute-policy {
      type jt:policy-algebra;
      ordered-by user;
      description
        "Import policy for dynamic-tunnel under this destination network";
    }
    leaf preference {
      type union {
        type uint32;
        type string {
          pattern "<.*>|$.*";
        }
      }
      description
        "Preference of tunnel route under this destination network";
    }
    leaf-list colors {
      type union {
        type uint32;
        type string {
          pattern "<.*>|$.*";
        }
      }
      ordered-by user;
      description
        "Set of color list that will be supported for tunnel creation";
    }
    leaf best-effort {
      type empty;
      description
        "Best-effort transport class";
    }
  }

  grouping output-plugin {
    leaf name {
      type string;
      description
        "Plugin name";
    }
    uses apply-advanced;
    list parameters {
      key "name";
      ordered-by user;
      description
        "List of key:value parameters for plugin";
      uses parameter-pair;
    }
  }

  grouping p2mp_ldp_lsp_nh_obj {
    uses apply-advanced;
    list root-address {
      key "name";
      description
        "Configure the root address of P2MP LSP";
      leaf name {
        type jt:ipaddr;
        description
          "Root address of the P2MP LSP";
      }
      uses apply-advanced;
      leaf lsp-id {
        type union {
          type string {
            pattern "<.*>|$.*";
          }
          type uint32 {
            range "1 .. 65535";
          }
        }
        description
          "Configure the generic LSP identifier";
      }
      list group-address {
        key "name";
        description
          "IPv4/Ipv6 group address for mLDP LSP";
        leaf name {
          type jt:ipaddr;
          description
            "IPv4/Ipv6 group address";
        }
        uses apply-advanced;
        list source-address {
          key "name";
          description
            "IPv4/Ipv6 source address";
          leaf name {
            type jt:ipaddr;
            description
              "IPv4/Ipv6 source address for mLDP LSP";
          }
          uses apply-advanced;
        }
      }
    }
  }

  grouping parameter-pair {
    leaf name {
      type string;
      description
        "Parameter key";
    }
    uses apply-advanced;
    leaf value {
      type string;
      description
        "Parameter value";
    }
  }

  grouping periodic_oam {
    uses apply-advanced;
    container mpls-tp-mode {
      presence "enable mpls-tp-mode";
      description
        "MPLS-TP Mode, Do not use IP addressing for OAM";
      uses apply-advanced;
      container lsping-channel-type {
        description
          "Supported Control-channel types for MPLS-TP mode....";
        uses apply-advanced;
        choice action-choice {
          case case_1 {
            leaf ipv4 {
              type empty;
              description
                "Use channel-type IPv4(0x0021), With IP-UDP encapsulation";
            }
          }
          case case_2 {
            leaf on-demand-cv {
              type empty;
              description
                "Use channel-type On-Demand-CV(0x0025), Without IP-UDP encapsulation";
            }
          }
        }
      }
    }
    container bfd-port {
      description
        "Egress knob to select MHOP-BFD port for MPLS BFD";
      uses apply-advanced;
      leaf-list import {
        type jt:policy-algebra;
        ordered-by user;
        description
          "Import policy";
      }
    }
    container bfd-liveness-detection {
      description
        "Bidirectional Forwarding Detection options";
      uses apply-advanced;
      leaf version {
        type enumeration {
          enum "0" {
            description
              "BFD version 0 (deprecated)";
          }
          enum "1" {
            description
              "BFD version 1";
          }
          enum "automatic" {
            description
              "Choose BFD version automatically";
          }
        }
        default "automatic";
        description
          "BFD protocol version number";
      }
      leaf minimum-interval {
        type union {
          type string {
            pattern "<.*>|$.*";
          }
          type uint32 {
            range "1 .. 255000";
          }
        }
        units "milliseconds";
        description
          "Minimum transmit and receive interval";
      }
      leaf minimum-transmit-interval {
        type union {
          type string {
            pattern "<.*>|$.*";
          }
          type uint32 {
            range "1 .. 255000";
          }
        }
        units "milliseconds";
        status deprecated;
        description
          "Minimum transmit interval";
      }
      leaf minimum-receive-interval {
        type union {
          type string {
            pattern "<.*>|$.*";
          }
          type uint32 {
            range "1 .. 255000";
          }
        }
        units "milliseconds";
        description
          "Minimum receive interval";
      }
      leaf multiplier {
        type union {
          type string {
            pattern "<.*>|$.*";
          }
          type uint32 {
            range "1 .. 255";
          }
        }
        default "3";
        description
          "Detection time multiplier";
      }
      leaf inline-disable {
        type empty;
        description
          "Disable inline mode for this BFD session";
      }
      leaf pdu-size {
        type union {
          type string {
            pattern "<.*>|$.*";
          }
          type uint32 {
            range "24 .. 16000";
          }
        }
        default "24";
        description
          "BFD transport protocol payload size";
      }
      choice adaptation-choice {
        case case_1 {
          leaf no-adaptation {
            type empty;
            description
              "Disable adaptation";
          }
        }
      }
      container transmit-interval {
        description
          "Transmit-interval options";
        uses apply-advanced;
        leaf minimum-interval {
          type union {
            type string {
              pattern "<.*>|$.*";
            }
            type uint32 {
              range "1 .. 255000";
            }
          }
          units "milliseconds";
          description
            "Minimum transmit interval";
        }
        leaf threshold {
          type union {
            type uint32;
            type string {
              pattern "<.*>|$.*";
            }
          }
          units "milliseconds";
          description
            "High transmit interval triggering a trap";
        }
      }
      container detection-time {
        description
          "Detection-time options";
        uses apply-advanced;
        leaf threshold {
          type union {
            type uint32;
            type string {
              pattern "<.*>|$.*";
            }
          }
          units "milliseconds";
          description
            "High detection-time triggering a trap";
        }
      }
      container failure-action {
        description
          "Action to take when BFD session goes down";
        choice action-choice {
          case case_1 {
            leaf teardown {
              type empty;
              description
                "Teardown label switched path and resignal";
            }
          }
          case case_2 {
            container make-before-break {
              presence "enable make-before-break";
              description
                "Resignal the label switched path before teardown";
              uses apply-advanced;
              leaf teardown-timeout {
                type union {
                  type string {
                    pattern "<.*>|$.*";
                  }
                  type uint32 {
                    range "0 .. 65535";
                  }
                }
                units "seconds";
                description
                  "Time to wait before teardown";
              }
            }
          }
        }
      }
      leaf no-router-alert-option {
        type empty;
        description
          "Do not set Router-Alert options in IP header for MPLS-BFD";
      }
      leaf use-ip-ttl-1 {
        type empty;
        description
          "Set TTL value to 1 in IP header for MPLS-BFD";
      }
    }
    container performance-monitoring {
      description
        "Performance monitoring options";
      uses apply-advanced;
      container traceoptions {
        description
          "Trace options for PM";
        uses apply-advanced;
        container file {
          description
            "Trace file options";
          leaf filename {
            type string {
              length "1 .. 1024";
            }
            description
              "Name of file in which to write trace information";
          }
          leaf replace {
            type empty;
            status deprecated;
            description
              "Replace trace file rather than appending to it";
          }
          leaf size {
            type string;
            description
              "Maximum trace file size";
          }
          leaf files {
            type union {
              type string {
                pattern "<.*>|$.*";
              }
              type uint32 {
                range "2 .. 1000";
              }
            }
            default "10";
            description
              "Maximum number of trace files";
          }
          leaf no-stamp {
            type empty;
            status deprecated;
            description
              "Do not timestamp trace file";
          }
          choice world-readable-choice {
            leaf world-readable {
              type empty;
              description
                "Allow any user to read the log file";
            }
            leaf no-world-readable {
              type empty;
              description
                "Don't allow any user to read the log file";
            }
          }
        }
        list flag {
          key "name";
          ordered-by user;
          description
            "Tracing parameters";
          leaf name {
            type enumeration {
              enum "init" {
                description
                  "Trace init commnad";
              }
              enum "error" {
                description
                  "Trace error conditions";
              }
              enum "event" {
                description
                  "Trace state machine events";
              }
              enum "general" {
                description
                  "Trace general events";
              }
              enum "packet" {
                description
                  "Trace various packets ";
              }
              enum "timer" {
                description
                  "Trace timer processing";
              }
              enum "all" {
                description
                  "Trace everything";
              }
            }
          }
        }
      }
      container querier {
        description
          "Querier options";
        uses apply-advanced;
        container loss {
          description
            "Loss measurement options";
          uses apply-advanced;
          list traffic-class {
            key "name";
            description
              "Traffic class specific options";
            leaf name {
              type enumeration {
                enum "tc-0" {
                  description
                    "Traffic class 0";
                }
                enum "tc-1" {
                  description
                    "Traffic class 1";
                }
                enum "tc-2" {
                  description
                    "Traffic class 2";
                }
                enum "tc-3" {
                  description
                    "Traffic class 3";
                }
                enum "tc-4" {
                  description
                    "Traffic class 4";
                }
                enum "tc-5" {
                  description
                    "Traffic class 5";
                }
                enum "tc-6" {
                  description
                    "Traffic class 6";
                }
                enum "tc-7" {
                  description
                    "Traffic class 7";
                }
                enum "all" {
                  description
                    "All Traffic class";
                }
                enum "none" {
                  description
                    "No Traffic class";
                }
              }
              description
                "Traffic class value";
            }
            uses apply-advanced;
            leaf query-interval {
              type union {
                type string {
                  pattern "<.*>|$.*";
                }
                type uint32 {
                  range "1000 .. 4294967295";
                }
              }
              units "milliseconds";
              description
                "Minimum transmit interval";
            }
            leaf measurement-quantity {
              type enumeration {
                enum "bytes" {
                  description
                    "Byte loss measurement";
                }
                enum "packets" {
                  description
                    "Packet loss measurement";
                }
              }
              default "packets";
              description
                "Loss measurement quantity";
            }
            leaf average-sample-size {
              type union {
                type string {
                  pattern "<.*>|$.*";
                }
                type uint16 {
                  range "1 .. 30";
                }
              }
              description
                "Number of samples used in average calculation";
            }
            leaf loss-threshold {
              type union {
                type string {
                  pattern "<.*>|$.*";
                }
                type uint32 {
                  range "1 .. 4294967295";
                }
              }
              description
                "Loss threshold value";
            }
            leaf loss-threshold-window {
              type union {
                type string {
                  pattern "<.*>|$.*";
                }
                type uint32 {
                  range "1 .. 30";
                }
              }
              description
                "Number of samples for loss threshold calculation";
            }
          }
        }
        container delay {
          description
            "Delay measurement options";
          uses apply-advanced;
          list traffic-class {
            key "name";
            description
              "Traffic class specific options";
            leaf name {
              type enumeration {
                enum "tc-0" {
                  description
                    "Traffic class 0";
                }
                enum "tc-1" {
                  description
                    "Traffic class 1";
                }
                enum "tc-2" {
                  description
                    "Traffic class 2";
                }
                enum "tc-3" {
                  description
                    "Traffic class 3";
                }
                enum "tc-4" {
                  description
                    "Traffic class 4";
                }
                enum "tc-5" {
                  description
                    "Traffic class 5";
                }
                enum "tc-6" {
                  description
                    "Traffic class 6";
                }
                enum "tc-7" {
                  description
                    "Traffic class 7";
                }
                enum "all" {
                  description
                    "All Traffic classes";
                }
              }
              description
                "Traffic class value";
            }
            uses apply-advanced;
            leaf query-interval {
              type union {
                type string {
                  pattern "<.*>|$.*";
                }
                type uint32 {
                  range "1000 .. 4294967295";
                }
              }
              units "milliseconds";
              description
                "Minimum transmit interval";
            }
            leaf padding-size {
              type union {
                type string {
                  pattern "<.*>|$.*";
                }
                type uint16 {
                  range "1 .. 1500";
                }
              }
              description
                "Size of padding";
            }
            leaf average-sample-size {
              type union {
                type string {
                  pattern "<.*>|$.*";
                }
                type uint16 {
                  range "1 .. 30";
                }
              }
              description
                "Number of samples used in average calculation";
            }
            leaf twcd-delay-threshold {
              type union {
                type string {
                  pattern "<.*>|$.*";
                }
                type uint32 {
                  range "1 .. 4294967295";
                }
              }
              units "microseconds";
              description
                "Two way channel delay threshold value";
            }
            leaf rtt-delay-threshold {
              type union {
                type string {
                  pattern "<.*>|$.*";
                }
                type uint32 {
                  range "1 .. 4294967295";
                }
              }
              units "microseconds";
              description
                "Round trip delay threshold value";
            }
          }
        }
        container loss-delay {
          description
            "Combined loss-delay measurement options";
          uses apply-advanced;
          list traffic-class {
            key "name";
            description
              "Traffic class specific options";
            leaf name {
              type enumeration {
                enum "tc-0" {
                  description
                    "Traffic class 0";
                }
                enum "tc-1" {
                  description
                    "Traffic class 1";
                }
                enum "tc-2" {
                  description
                    "Traffic class 2";
                }
                enum "tc-3" {
                  description
                    "Traffic class 3";
                }
                enum "tc-4" {
                  description
                    "Traffic class 4";
                }
                enum "tc-5" {
                  description
                    "Traffic class 5";
                }
                enum "tc-6" {
                  description
                    "Traffic class 6";
                }
                enum "tc-7" {
                  description
                    "Traffic class 7";
                }
                enum "all" {
                  description
                    "All Traffic classes";
                }
                enum "none" {
                  description
                    "No Traffic class";
                }
              }
              description
                "Traffic class value";
            }
            uses apply-advanced;
            leaf query-interval {
              type union {
                type string {
                  pattern "<.*>|$.*";
                }
                type uint32 {
                  range "1000 .. 4294967295";
                }
              }
              units "milliseconds";
              description
                "Minimum transmit interval";
            }
            leaf measurement-quantity {
              type enumeration {
                enum "bytes" {
                  description
                    "Byte loss measurement";
                }
                enum "packets" {
                  description
                    "Packet loss measurement";
                }
              }
              default "packets";
              description
                "Loss measurement quantity";
            }
            leaf padding-size {
              type union {
                type string {
                  pattern "<.*>|$.*";
                }
                type uint16 {
                  range "1 .. 1500";
                }
              }
              description
                "Size of padding";
            }
            leaf average-sample-size {
              type union {
                type string {
                  pattern "<.*>|$.*";
                }
                type uint16 {
                  range "1 .. 30";
                }
              }
              description
                "Number of samples used in average calculation";
            }
            leaf loss-threshold {
              type union {
                type string {
                  pattern "<.*>|$.*";
                }
                type uint32 {
                  range "1 .. 4294967295";
                }
              }
              description
                "Loss threshold value";
            }
            leaf loss-threshold-window {
              type union {
                type string {
                  pattern "<.*>|$.*";
                }
                type uint32 {
                  range "1 .. 30";
                }
              }
              description
                "Number of samples for loss threshold calculation";
            }
            leaf twcd-delay-threshold {
              type union {
                type string {
                  pattern "<.*>|$.*";
                }
                type uint32 {
                  range "1 .. 4294967295";
                }
              }
              units "microseconds";
              description
                "Two way channel delay threshold value";
            }
            leaf rtt-delay-threshold {
              type union {
                type string {
                  pattern "<.*>|$.*";
                }
                type uint32 {
                  range "1 .. 4294967295";
                }
              }
              units "microseconds";
              description
                "Round trip delay threshold value";
            }
          }
        }
      }
      container responder {
        description
          "Responder options";
        uses apply-advanced;
        container loss {
          description
            "Loss measurement options";
          uses apply-advanced;
          leaf min-query-interval {
            type union {
              type string {
                pattern "<.*>|$.*";
              }
              type uint32 {
                range "1000 .. 4294967295";
              }
            }
            units "milliseconds";
            description
              "Minimum query interval";
          }
        }
        container delay {
          description
            "Delay measurement options";
          uses apply-advanced;
          leaf min-query-interval {
            type union {
              type string {
                pattern "<.*>|$.*";
              }
              type uint32 {
                range "1000 .. 4294967295";
              }
            }
            units "milliseconds";
            description
              "Minimum query interval";
          }
        }
      }
    }
  }

  grouping prefix_list_items {
    leaf name {
      type jt:ipprefix-only;
      description
        "Address prefix";
    }
    uses apply-advanced;
  }

  grouping programmable-rpd-type {
    uses apply-advanced;
    container traceoptions {
      description
        "Trace options";
      uses apply-advanced;
      container file {
        description
          "Trace file options";
        leaf filename {
          type string {
            length "1 .. 1024";
          }
          description
            "Name of file in which to write trace information";
        }
        leaf replace {
          type empty;
          status deprecated;
          description
            "Replace trace file rather than appending to it";
        }
        leaf size {
          type string;
          description
            "Maximum trace file size";
        }
        leaf files {
          type union {
            type string {
              pattern "<.*>|$.*";
            }
            type uint32 {
              range "2 .. 1000";
            }
          }
          default "10";
          description
            "Maximum number of trace files";
        }
        leaf no-stamp {
          type empty;
          status deprecated;
          description
            "Do not timestamp trace file";
        }
        choice world-readable-choice {
          leaf world-readable {
            type empty;
            description
              "Allow any user to read the log file";
          }
          leaf no-world-readable {
            type empty;
            description
              "Don't allow any user to read the log file";
          }
        }
      }
      list flag {
        key "name";
        ordered-by user;
        description
          "Tracing parameters";
        leaf name {
          type enumeration {
            enum "client" {
              description
                "Client events";
            }
            enum "japi" {
              description
                "JAPI related traces";
            }
            enum "routing-interface" {
              description
                "Routing interface traces";
            }
            enum "te-path-compute" {
              description
                "TE Path Computation traces";
            }
            enum "statistics" {
              description
                "Statistics related traces";
            }
            enum "route" {
              description
                "Trace routing information";
            }
            enum "normal" {
              description
                "Trace normal events";
            }
            enum "general" {
              description
                "Trace general events";
            }
            enum "state" {
              description
                "Trace state transitions";
            }
            enum "policy" {
              description
                "Trace policy processing";
            }
            enum "task" {
              description
                "Trace routing protocol task processing";
            }
            enum "timer" {
              description
                "Trace routing protocol timer processing";
            }
            enum "all" {
              description
                "Trace everything";
            }
          }
        }
      }
    }
    container purge-timeout {
      presence "enable purge-timeout";
      description
        "Purge timeout for all programmable-rpd clients in seconds";
      choice purge-parm {
        case case_1 {
          leaf never {
            type empty;
            description
              "Client programmed objects are never purged";
          }
        }
        case case_2 {
          leaf timeout {
            type union {
              type string {
                pattern "<.*>|$.*";
              }
              type uint32 {
                range "1 .. 604800";
              }
            }
            units "seconds";
            description
              "Timeout value, in seconds, for purging client programmed objects";
          }
        }
      }
    }
    list client {
      key "name";
      ordered-by user;
      description
        "Programmable-rpd client options";
      leaf name {
        type string {
          length "1 .. 255";
        }
        description
          "Client ID";
      }
      uses apply-advanced;
      list interface-notification {
        key "name";
        ordered-by user;
        description
          "Interfaces for notification";
        leaf name {
          type string {
            length "1 .. 32";
          }
          description
            "Interface";
        }
        uses apply-advanced;
      }
    }
    container rib-service {
      presence "enable rib-service";
      description
        "RIB service API options";
      uses apply-advanced;
      container dynamic-next-hop-interface {
        presence "enable dynamic-next-hop-interface";
        description
          "Update routes for next-hop interface changes";
        uses apply-advanced;
        choice enable-disable {
          case case_1 {
            leaf disable {
              type empty;
              description
                "Disable dynamic next-hop interface handling";
            }
          }
        }
      }
    }
    leaf stats-sampling-interval {
      type union {
        type string {
          pattern "<.*>|$.*";
        }
        type uint32 {
          range "30 .. 3600";
        }
      }
      units "seconds";
      default "30";
      description
        "Sampling interval for programmable rpd statisitics";
    }
    leaf stats-aggregation-interval {
      type union {
        type string {
          pattern "<.*>|$.*";
        }
        type uint32 {
          range "60 .. 3600";
        }
      }
      units "seconds";
      default "60";
      description
        "Aggregation interval for programmable rpd statistics";
    }
  }

  grouping qualified_nh_obj {
    leaf name {
      type union {
        type jt:ipaddr-or-interface;
        type string {
          pattern "<.*>|$.*";
        }
      }
      mandatory true;
      description
        "Next hop to destination";
    }
    uses apply-advanced;
    leaf preference {
      type union {
        type uint32;
        type string {
          pattern "<.*>|$.*";
        }
      }
      description
        "Preference of qualified next hop";
    }
    leaf metric {
      type union {
        type uint32;
        type string {
          pattern "<.*>|$.*";
        }
      }
      description
        "Metric of qualified next hop";
    }
    leaf interface {
      type union {
        type jt:interface-name;
        type string {
          pattern "<.*>|$.*";
        }
      }
      description
        "Interface of qualified next hop";
    }
    leaf mac-address {
      type jt:mac-unicast;
      description
        "Next-hop Mac Address";
    }
    leaf order {
      type union {
        type string {
          pattern "<.*>|$.*";
        }
        type uint16 {
          range "1 .. 65535";
        }
      }
      description
        "Order of qualified next hop";
    }
    leaf tag {
      type union {
        type uint32;
        type string {
          pattern "<.*>|$.*";
        }
      }
      description
        "Tag string";
    }
    container bfd-liveness-detection {
      description
        "Bidirectional Forwarding Detection (BFD) options";
      uses apply-advanced;
      leaf version {
        type enumeration {
          enum "0" {
            description
              "BFD version 0 (deprecated)";
          }
          enum "1" {
            description
              "BFD version 1";
          }
          enum "automatic" {
            description
              "Choose BFD version automatically";
          }
        }
        default "automatic";
        description
          "BFD protocol version number";
      }
      leaf minimum-interval {
        type union {
          type string {
            pattern "<.*>|$.*";
          }
          type uint32 {
            range "1 .. 255000";
          }
        }
        units "milliseconds";
        description
          "Minimum transmit and receive interval";
      }
      leaf minimum-transmit-interval {
        type union {
          type string {
            pattern "<.*>|$.*";
          }
          type uint32 {
            range "1 .. 255000";
          }
        }
        units "milliseconds";
        status deprecated;
        description
          "Minimum transmit interval";
      }
      leaf minimum-receive-interval {
        type union {
          type string {
            pattern "<.*>|$.*";
          }
          type uint32 {
            range "1 .. 255000";
          }
        }
        units "milliseconds";
        description
          "Minimum receive interval";
      }
      leaf multiplier {
        type union {
          type string {
            pattern "<.*>|$.*";
          }
          type uint32 {
            range "1 .. 255";
          }
        }
        default "3";
        description
          "Detection time multiplier";
      }
      leaf inline-disable {
        type empty;
        description
          "Disable inline mode for this BFD session";
      }
      leaf pdu-size {
        type union {
          type string {
            pattern "<.*>|$.*";
          }
          type uint32 {
            range "24 .. 16000";
          }
        }
        default "24";
        description
          "BFD transport protocol payload size";
      }
      choice adaptation-choice {
        case case_1 {
          leaf no-adaptation {
            type empty;
            description
              "Disable adaptation";
          }
        }
      }
      container transmit-interval {
        description
          "Transmit-interval options";
        uses apply-advanced;
        leaf minimum-interval {
          type union {
            type string {
              pattern "<.*>|$.*";
            }
            type uint32 {
              range "1 .. 255000";
            }
          }
          units "milliseconds";
          description
            "Minimum transmit interval";
        }
        leaf threshold {
          type union {
            type uint32;
            type string {
              pattern "<.*>|$.*";
            }
          }
          units "milliseconds";
          description
            "High transmit interval triggering a trap";
        }
      }
      container detection-time {
        description
          "Detection-time options";
        uses apply-advanced;
        leaf threshold {
          type union {
            type uint32;
            type string {
              pattern "<.*>|$.*";
            }
          }
          units "milliseconds";
          description
            "High detection-time triggering a trap";
        }
      }
      container authentication {
        description
          "Authentication options";
        uses apply-advanced;
        leaf key-chain {
          type string;
          description
            "Key chain name";
        }
        leaf algorithm {
          type enumeration {
            enum "simple-password" {
              description
                "Simple password";
            }
            enum "keyed-md5" {
              description
                "Keyed message Digest 5";
            }
            enum "meticulous-keyed-md5" {
              description
                "Meticulous keyed message Digest 5";
            }
            enum "keyed-sha-1" {
              description
                "Keyed secure hash algorithm (SHA1) ";
            }
            enum "meticulous-keyed-sha-1" {
              description
                "Meticulous keyed secure hash algorithm (SHA1) ";
            }
          }
          description
            "Algorithm name";
        }
        leaf loose-check {
          type empty;
          description
            "Verify authentication only if authentication is negotiated";
        }
      }
      container echo {
        description
          "Echo mode parameters";
        uses apply-advanced;
        leaf minimum-interval {
          type union {
            type string {
              pattern "<.*>|$.*";
            }
            type uint32 {
              range "100 .. 255000";
            }
          }
          units "milliseconds";
          description
            "Minimum transmit and receive interval";
        }
      }
      container echo-lite {
        description
          "Echo-lite more parameters";
        uses apply-advanced;
        leaf minimum-interval {
          type union {
            type string {
              pattern "<.*>|$.*";
            }
            type uint32 {
              range "100 .. 255000";
            }
          }
          units "milliseconds";
          description
            "Minimum transmit and receive interval";
        }
      }
      leaf neighbor {
        type jt:ipaddr;
        description
          "BFD neighbor address";
      }
      leaf local-address {
        type jt:ipaddr;
        description
          "BFD local address (for multihop only)";
      }
      leaf holddown-interval {
        type union {
          type string {
            pattern "<.*>|$.*";
          }
          type uint32 {
            range "0 .. 255000";
          }
        }
        units "milliseconds";
        description
          "Time to hold the session-UP notification to the client";
      }
      leaf minimum-receive-ttl {
        type union {
          type string {
            pattern "<.*>|$.*";
          }
          type uint8 {
            range "1 .. 255";
          }
        }
        description
          "Minimum receive TTL below which to drop";
      }
    }
  }

  grouping radius-server-object {
    leaf name {
      type jt:hostname;
      description
        "RADIUS server address";
    }
    uses apply-advanced;
    leaf routing-instance {
      type string;
      description
        "Routing instance";
    }
    leaf port {
      type union {
        type string {
          pattern "<.*>|$.*";
        }
        type uint16 {
          range "1 .. 65535";
        }
      }
      default "1812";
      description
        "RADIUS server authentication port number";
    }
    leaf preauthentication-port {
      type union {
        type string {
          pattern "<.*>|$.*";
        }
        type uint16 {
          range "1 .. 65535";
        }
      }
      description
        "RADIUS server preauthentication port number";
    }
    leaf accounting-port {
      type union {
        type string {
          pattern "<.*>|$.*";
        }
        type uint16 {
          range "1 .. 65535";
        }
      }
      default "1813";
      description
        "RADIUS server accounting port number";
    }
    leaf dynamic-request-port {
      type union {
        type string {
          pattern "<.*>|$.*";
        }
        type uint16 {
          range "1 .. 65535";
        }
      }
      default "3799";
      description
        "RADIUS client dynamic request port number";
    }
    leaf secret {
      type jt:unreadable;
      mandatory true;
      description
        "Shared secret with the RADIUS server";
    }
    leaf preauthentication-secret {
      type jt:unreadable;
      description
        "Shared secret with the RADIUS server";
    }
    leaf timeout {
      type union {
        type string {
          pattern "<.*>|$.*";
        }
        type uint32 {
          range "1 .. 1000";
        }
      }
      units "seconds";
      default "3";
      description
        "Request timeout period";
    }
    leaf retry {
      type union {
        type string {
          pattern "<.*>|$.*";
        }
        type uint32 {
          range "1 .. 100";
        }
      }
      default "3";
      description
        "Retry attempts";
    }
    leaf accounting-timeout {
      type union {
        type string {
          pattern "<.*>|$.*";
        }
        type uint32 {
          range "0 .. 1000";
        }
      }
      units "seconds";
      default "0";
      description
        "Accounting request timeout period";
    }
    leaf accounting-retry {
      type union {
        type string {
          pattern "<.*>|$.*";
        }
        type uint32 {
          range "0 .. 100";
        }
      }
      default "0";
      description
        "Accounting retry attempts";
    }
    leaf max-outstanding-requests {
      type union {
        type string {
          pattern "<.*>|$.*";
        }
        type uint32 {
          range "0 .. 2000";
        }
      }
      default "1000";
      description
        "Maximum requests in flight to server";
    }
    leaf no-message-authenticator {
      type empty;
      description
        "Do not deny login if Message-Authenticator is not present";
    }
    leaf source-address {
      type jt:ipaddr;
      description
        "Use specified address as source address";
    }
    container tls {
      description
        "Radius over TLS";
      uses apply-advanced;
      leaf-list trusted-ca-group {
        type string {
          length "1 .. 63";
        }
        max-elements 20;
        ordered-by user;
        description
          "Name of the trusted CA groups (maximum 20)";
      }
      container mutual-authentication {
        description
          "Enable TLS mutual authentication";
        uses apply-advanced;
        leaf certificate-id {
          type string;
          mandatory true;
          description
            "Local Certificate ID";
        }
      }
    }
  }

  grouping rib-inet3 {
    uses apply-advanced;
    container inet.3 {
      presence "enable inet.3";
      description
        "Use inet.3 to exchange labeled unicast routes";
      uses apply-advanced;
    }
  }

  grouping rib_aggregate_type {
    uses apply-advanced;
    container defaults {
      description
        "Global route options";
      uses apply-advanced;
      container metric {
        presence "enable metric";
        description
          "Metric value";
        uses rib_static_metric_type;
      }
      container metric2 {
        presence "enable metric2";
        description
          "Metric value 2";
        uses rib_static_metric_type;
      }
      container metric3 {
        presence "enable metric3";
        description
          "Metric value 3";
        uses rib_static_metric_type;
      }
      container metric4 {
        presence "enable metric4";
        description
          "Metric value 4";
        uses rib_static_metric_type;
      }
      container tag {
        presence "enable tag";
        description
          "Tag string";
        uses rib_static_metric_type;
      }
      container tag2 {
        presence "enable tag2";
        description
          "Tag string 2";
        uses rib_static_metric_type;
      }
      container preference {
        presence "enable preference";
        description
          "Preference value";
        uses rib_static_metric_type;
      }
      container preference2 {
        presence "enable preference2";
        description
          "Preference value 2";
        uses rib_static_metric_type;
      }
      container color {
        presence "enable color";
        description
          "Color (preference) value";
        uses rib_static_metric_type;
      }
      container color2 {
        presence "enable color2";
        description
          "Color (preference) value 2";
        uses rib_static_metric_type;
      }
      leaf-list community {
        type jt:community;
        ordered-by user;
        description
          "BGP community identifier";
      }
      container as-path {
        description
          "Autonomous system path";
        uses apply-advanced;
        leaf path {
          type string;
          description
            "Autonomous system path";
        }
        leaf origin {
          type enumeration {
            enum "igp" {
              description
                "Path originated in the local IGP";
            }
            enum "egp" {
              description
                "Path originated in another AS";
            }
            enum "incomplete" {
              description
                "Path was learned by some other means";
            }
          }
        }
        leaf atomic-aggregate {
          type empty;
          description
            "Add ATOMIC_AGGREGATE path attribute to route";
        }
        container aggregator {
          presence "enable aggregator";
          description
            "Add AGGREGATOR path attribute to route";
        }
        leaf as-number {
          type string;
          description
            " Autonomous system number in plain number or 'higher 16bits'.'Lower 16 bits' (asdot notation) format";
        }
        leaf address {
          type jt:ipv4addr;
          description
            "Address of BGP system that formed the route";
        }
      }
      leaf discard {
        type empty;
        description
          "Drop packets to destination; send no ICMP unreachables";
      }
      leaf next-table {
        type string;
        description
          "Next hop to another table";
      }
      choice brief_flag {
        case case_1 {
          leaf brief {
            type empty;
            description
              "Include longest common sequences from contributing paths";
          }
        }
        case case_2 {
          leaf full {
            type empty;
            description
              "Include all AS numbers from all contributing paths";
          }
        }
      }
      choice passive_flag {
        case case_1 {
          leaf active {
            type empty;
            description
              "Remove inactive route from forwarding table";
          }
        }
        case case_2 {
          leaf passive {
            type empty;
            description
              "Retain inactive route in forwarding table";
          }
        }
      }
      container algorithm {
        description
          "Algorithm number";
        leaf number {
          type union {
            type string {
              pattern "<.*>|$.*";
            }
            type uint32 {
              range "0 .. 255";
            }
          }
          description
            "Algorithm number";
        }
      }
    }
    leaf protocol-instance-name {
      type string;
      description
        "Name of protocol instance under routing instance";
    }
    list route {
      key "name";
      description
        "Individual route options";
      leaf name {
        type jt:ipprefix;
        description
          "Destination prefix";
      }
      uses apply-advanced;
      leaf description {
        type string;
        description
          "Description for aggregate routes";
      }
      leaf-list policy {
        type jt:policy-algebra;
        ordered-by user;
        description
          "Policy filter";
      }
      container metric {
        presence "enable metric";
        description
          "Metric value";
        uses rib_static_metric_type;
      }
      container metric2 {
        presence "enable metric2";
        description
          "Metric value 2";
        uses rib_static_metric_type;
      }
      container metric3 {
        presence "enable metric3";
        description
          "Metric value 3";
        uses rib_static_metric_type;
      }
      container metric4 {
        presence "enable metric4";
        description
          "Metric value 4";
        uses rib_static_metric_type;
      }
      container tag {
        presence "enable tag";
        description
          "Tag string";
        uses rib_static_metric_type;
      }
      container tag2 {
        presence "enable tag2";
        description
          "Tag string 2";
        uses rib_static_metric_type;
      }
      container preference {
        presence "enable preference";
        description
          "Preference value";
        uses rib_static_metric_type;
      }
      container preference2 {
        presence "enable preference2";
        description
          "Preference value 2";
        uses rib_static_metric_type;
      }
      container color {
        presence "enable color";
        description
          "Color (preference) value";
        uses rib_static_metric_type;
      }
      container color2 {
        presence "enable color2";
        description
          "Color (preference) value 2";
        uses rib_static_metric_type;
      }
      leaf-list community {
        type jt:community;
        ordered-by user;
        description
          "BGP community identifier";
      }
      container as-path {
        description
          "Autonomous system path";
        uses apply-advanced;
        leaf path {
          type string;
          description
            "Autonomous system path";
        }
        leaf origin {
          type enumeration {
            enum "igp" {
              description
                "Path originated in the local IGP";
            }
            enum "egp" {
              description
                "Path originated in another AS";
            }
            enum "incomplete" {
              description
                "Path was learned by some other means";
            }
          }
        }
        leaf atomic-aggregate {
          type empty;
          description
            "Add ATOMIC_AGGREGATE path attribute to route";
        }
        container aggregator {
          presence "enable aggregator";
          description
            "Add AGGREGATOR path attribute to route";
        }
        leaf as-number {
          type string;
          description
            " Autonomous system number in plain number or 'higher 16bits'.'Lower 16 bits' (asdot notation) format";
        }
        leaf address {
          type jt:ipv4addr;
          description
            "Address of BGP system that formed the route";
        }
      }
      leaf discard {
        type empty;
        description
          "Drop packets to destination; send no ICMP unreachables";
      }
      leaf next-table {
        type string;
        description
          "Next hop to another table";
      }
      choice brief_flag {
        case case_1 {
          leaf brief {
            type empty;
            description
              "Include longest common sequences from contributing paths";
          }
        }
        case case_2 {
          leaf full {
            type empty;
            description
              "Include all AS numbers from all contributing paths";
          }
        }
      }
      choice passive_flag {
        case case_1 {
          leaf active {
            type empty;
            description
              "Remove inactive route from forwarding table";
          }
        }
        case case_2 {
          leaf passive {
            type empty;
            description
              "Retain inactive route in forwarding table";
          }
        }
      }
      container algorithm {
        description
          "Algorithm number";
        leaf number {
          type union {
            type string {
              pattern "<.*>|$.*";
            }
            type uint32 {
              range "0 .. 255";
            }
          }
          description
            "Algorithm number";
        }
      }
    }
  }

  grouping rib_group_inet_type {
    description
      "Routing table group";
    leaf ribgroup-name {
      type string;
      description
        "Name of the routing table group";
    }
  }

  grouping rib_group_type {
    uses apply-advanced;
    leaf inet-old-style {
      type string;
      status deprecated;
      description
        "Name of the IPv4 routing table group";
    }
    leaf inet {
      type string;
      description
        "Name of the IPv4 routing table group";
    }
    leaf inet3 {
      type string;
      description
        "Name of the IPv4 inet.3 routing table group";
    }
    leaf inet6 {
      type string;
      description
        "Name of the IPv6 routing table group";
    }
    leaf inet63 {
      type string;
      description
        "Name of the IPv6 inet6.3 routing table group";
    }
  }

  grouping rib_list_items {
    leaf name {
      type string;
      description
        "RIB name or wildcard";
    }
    uses apply-advanced;
  }

  grouping rib_static_metric_type {
    leaf metric-value {
      type union {
        type uint32;
        type string {
          pattern "<.*>|$.*";
        }
      }
      mandatory true;
      description
        "Metric value";
    }
    leaf type {
      type union {
        type string {
          pattern "<.*>|$.*";
        }
        type uint32 {
          range "1 .. 16";
        }
      }
      description
        "Metric type";
    }
  }

  grouping rmopd-traceoptions {
    description
      "Trace options for remote-monitoring";
    uses apply-advanced;
    leaf no-remote-trace {
      type empty;
      description
        "Disable remote tracing";
    }
    container file {
      description
        "Trace file information";
      leaf filename {
        type string {
          length "1 .. 1024";
        }
        description
          "Name of file in which to write trace information";
      }
      leaf size {
        type string;
        description
          "Maximum trace file size";
      }
      leaf files {
        type union {
          type string {
            pattern "<.*>|$.*";
          }
          type uint32 {
            range "2 .. 1000";
          }
        }
        default "3";
        description
          "Maximum number of trace files";
      }
      choice world-readable-choice {
        leaf world-readable {
          type empty;
          description
            "Allow any user to read the log file";
        }
        leaf no-world-readable {
          type empty;
          description
            "Don't allow any user to read the log file";
        }
      }
      leaf match {
        type jt:regular-expression;
        description
          "Regular expression for lines to be logged";
      }
    }
    leaf level {
      type enumeration {
        enum "error" {
          description
            "Match error conditions";
        }
        enum "warning" {
          description
            "Match warning messages";
        }
        enum "notice" {
          description
            "Match conditions that should be handled specially";
        }
        enum "info" {
          description
            "Match informational messages";
        }
        enum "verbose" {
          description
            "Match verbose messages";
        }
        enum "all" {
          description
            "Match all levels";
        }
      }
      default "error";
      description
        "Level of debugging output";
    }
    list flag {
      key "name";
      ordered-by user;
      description
        "Tracing parameters";
      leaf name {
        type enumeration {
          enum "configuration" {
            description
              "Trace configuration events";
          }
          enum "ipc" {
            description
              "Trace ipc messages";
          }
          enum "ppm" {
            description
              "Trace ppm";
          }
          enum "rpd" {
            description
              "Trace rpd events";
          }
          enum "info" {
            description
              "Trace info events";
          }
          enum "statistics" {
            description
              "Trace statistics";
          }
          enum "error" {
            description
              "Trace events related to catastrophic errors in daemon";
          }
          enum "all" {
            description
              "Trace everything";
          }
        }
      }
    }
  }

  grouping route_filter_list_items {
    leaf address {
      type jt:ipprefix;
      description
        "IP address or hostname";
    }
    leaf choice-ident {
      type enumeration {
        enum "exact";
        enum "longer";
        enum "orlonger";
        enum "upto";
        enum "through";
        enum "prefix-length-range";
        enum "address-mask";
      }
    }
    leaf choice-value {
      type string;
    }
    uses apply-advanced;
    container label {
      description
        "Set label for BGP LU label allocation";
      choice label_value {
        case case_1 {
          container range {
            description
              "Label range";
            choice range_value {
              case case_1 {
                leaf range {
                  type string;
                  description
                    "Label range in <start>:<end> format";
                }
              }
            }
          }
        }
        case case_2 {
          leaf label {
            type union {
              type string {
                pattern "<.*>|$.*";
              }
              type uint32 {
                range "0 .. 1048575";
              }
            }
            description
              "Label value";
          }
        }
      }
    }
    leaf get-route-range {
      type empty;
      description
        "Get the range";
    }
    container metric {
      description
        "Metric value";
      uses apply-advanced;
      choice metric_action {
        case case_1 {
          leaf metric {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
        case case_4 {
          container igp {
            presence "enable igp";
            description
              "Track the IGP metric (BGP only)";
            leaf metric_offset {
              type union {
                type int32;
                type string {
                  pattern "<.*>|$.*";
                }
              }
              description
                "Metric offset for MED";
            }
          }
        }
        case case_5 {
          container minimum-igp {
            presence "enable minimum-igp";
            description
              "Track the minimum IGP metric (BGP only)";
            leaf metric_offset {
              type union {
                type int32;
                type string {
                  pattern "<.*>|$.*";
                }
              }
              description
                "Metric offset for MED";
            }
          }
        }
        case case_6 {
          container expression {
            description
              "Calculate value based on route metric and metric2";
            uses metric_expression_type;
          }
        }
        case case_7 {
          leaf aigp {
            type empty;
            description
              "Use aigp, if it exists, to set the IGP metric";
          }
        }
        case case_8 {
          container effective-aigp {
            presence "enable effective-aigp";
            description
              "Track the effective AIGP metric (BGP only)";
            leaf metric_offset {
              type union {
                type int32;
                type string {
                  pattern "<.*>|$.*";
                }
              }
              description
                "Metric offset for MED";
            }
          }
        }
        case case_9 {
          container minimum-effective-aigp {
            presence "enable minimum-effective-aigp";
            description
              "Track the minimum effective AIGP metric (BGP only)";
            leaf metric_offset {
              type union {
                type int32;
                type string {
                  pattern "<.*>|$.*";
                }
              }
              description
                "Metric offset for MED";
            }
          }
        }
      }
    }
    container metric2 {
      description
        "Metric value 2";
      uses apply-advanced;
      choice metric_action {
        case case_1 {
          leaf metric2 {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container metric3 {
      description
        "Metric value 3";
      uses apply-advanced;
      choice metric_action {
        case case_1 {
          leaf metric3 {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container metric4 {
      description
        "Metric value 4";
      uses apply-advanced;
      choice metric_action {
        case case_1 {
          leaf metric4 {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container tag {
      description
        "Tag string";
      uses apply-advanced;
      choice metric_action {
        case case_1 {
          leaf tag {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container tag2 {
      description
        "Tag string 2";
      uses apply-advanced;
      choice metric_action {
        case case_1 {
          leaf tag2 {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container preference {
      description
        "Preference value";
      uses apply-advanced;
      choice metric_action {
        case case_1 {
          leaf preference {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container preference2 {
      description
        "Preference value 2";
      uses apply-advanced;
      choice metric_action {
        case case_1 {
          leaf preference2 {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container color {
      description
        "Color (preference) value";
      uses apply-advanced;
      choice metric_action {
        case case_1 {
          leaf color {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container color2 {
      description
        "Color (preference) value 2";
      uses apply-advanced;
      choice metric_action {
        case case_1 {
          leaf color2 {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container local-preference {
      description
        "Local preference associated with a route";
      uses apply-advanced;
      choice metric_action {
        case case_1 {
          leaf local-preference {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container credibility {
      description
        "TED credibility value for entries from BGP-TE";
      uses apply-advanced;
      choice metric_action {
        case case_1 {
          leaf credibility {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    leaf priority {
      type enumeration {
        enum "high" {
          description
            "Set priority to high";
        }
        enum "medium" {
          description
            "Set priority to medium";
        }
        enum "low" {
          description
            "Set priority to low";
        }
      }
      description
        "Set priority for route installation";
    }
    container prefix-segment {
      description
        "Set prefix segment attributes";
      uses apply-advanced;
      list algorithm {
        key "name";
        max-elements 15;
        description
          "Set prefix segment attributes for strict/flex algorithm ";
        leaf name {
          type union {
            type string {
              pattern "<.*>|$.*";
            }
            type uint32 {
              range "1 .. 255";
            }
          }
          mandatory true;
          description
            "Set prefix segment for strict/flex algorithm";
        }
        leaf index {
          type union {
            type string {
              pattern "<.*>|$.*";
            }
            type uint32 {
              range "0 .. 1048575";
            }
          }
          mandatory true;
          description
            "Set prefix segment index id";
        }
        leaf node-segment {
          type empty;
          description
            "Set node segment flag for this prefix segment";
        }
      }
      leaf index {
        type union {
          type string {
            pattern "<.*>|$.*";
          }
          type uint32 {
            range "0 .. 1048575";
          }
        }
        description
          "Set prefix segment index id";
      }
      leaf node-segment {
        type empty;
        description
          "Set node segment flag for default prefix segment";
      }
      leaf redistribute {
        type empty;
        description
          "Redistribute prefix-segment from route entry";
      }
    }
    leaf label-allocation {
      type enumeration {
        enum "per-table" {
          description
            "Set per-table label allocation mode";
        }
        enum "per-nexthop" {
          description
            "Set per-nexthop label allocation mode";
        }
        enum "per-table-localize" {
          description
            "Set per-table-localize label allocation mode";
        }
      }
      description
        "Set label allocation mode";
    }
    container add-path {
      description
        "Set BGP add-path attributes";
      leaf send-count {
        type union {
          type string {
            pattern "<.*>|$.*";
          }
          type uint32 {
            range "2 .. 64";
          }
        }
        description
          "Number of add-paths sent";
      }
    }
    leaf fib-install-priority {
      type enumeration {
        enum "high" {
          description
            "Set Fib install priority  to high";
        }
        enum "medium" {
          description
            "Set Fib install priority to medium ";
        }
      }
      description
        "Set Fib Instalation priority of a route";
    }
    leaf validation-state {
      type enumeration {
        enum "valid" {
          description
            "Set validaton-state to valid";
        }
        enum "invalid" {
          description
            "Set validation-state to invalid";
        }
        enum "unknown" {
          description
            "Set validation-state to unknown";
        }
      }
      description
        "Set validation-state of a route";
    }
    leaf origin {
      type enumeration {
        enum "igp" {
          description
            "Path originated in the local IGP";
        }
        enum "egp" {
          description
            "Path originated in another AS";
        }
        enum "incomplete" {
          description
            "Path was learned by some other means";
        }
      }
      description
        "BGP path origin";
    }
    container srv6 {
      description
        "Configure SID with 128 bit address";
      leaf sid {
        type jt:ipv6addr;
        description
          "IPv6 Address";
      }
      leaf locator {
        type string;
        description
          "Name of locator";
      }
      choice locator_type {
        case case_1 {
          leaf micro-dt4-sid {
            type empty;
            description
              "Micro SID type dt4";
          }
        }
        case case_2 {
          leaf micro-dt6-sid {
            type empty;
            description
              "Micro SID type dt6";
          }
        }
        case case_3 {
          leaf micro-dt46-sid {
            type empty;
            description
              "Micro SID type dt46";
          }
        }
      }
    }
    container aigp-originate {
      presence "enable aigp-originate";
      description
        "Originate a BGP AIGP attribute";
      leaf distance {
        type union {
          type uint32;
          type string {
            pattern "<.*>|$.*";
          }
        }
        description
          "AIGP distance";
      }
    }
    container aigp-adjust {
      description
        "Adjust a BGP AIGP attribute";
      choice math-op {
        case case_1 {
          leaf add {
            type empty;
          }
        }
        case case_2 {
          leaf subtract {
            type empty;
          }
        }
        case case_3 {
          leaf multiply {
            type empty;
          }
        }
        case case_4 {
          leaf divide {
            type empty;
          }
        }
      }
      choice adjust-value {
        case case_1 {
          leaf user-value {
            type union {
              type uint64;
              type string {
                pattern "<.*>|$.*";
              }
            }
            description
              "Adjustment value";
          }
        }
        case case_2 {
          leaf distance-to-protocol-nexthop {
            type empty;
            description
              "Metric2";
          }
        }
      }
    }
    list community {
      key "choice-ident choice-value community-name";
      ordered-by user;
      description
        "BGP community properties associated with a route";
      leaf choice-ident {
        type enumeration {
          enum "equal-literal";
          enum "set";
          enum "plus-literal";
          enum "add";
          enum "minus-literal";
          enum "delete";
        }
      }
      leaf choice-value {
        type string;
      }
      leaf community-name {
        type string;
        description
          "Name to identify a BGP community";
      }
    }
    list tunnel-attribute {
      key "choice-ident choice-value tunnel-attribute-name";
      ordered-by user;
      description
        "BGP tunnel attribute associated with a route";
      leaf choice-ident {
        type enumeration {
          enum "set";
          enum "remove";
        }
      }
      leaf choice-value {
        type string;
      }
      leaf tunnel-attribute-name {
        type string;
        description
          "Name of a tunnel attribute , or 'all'";
      }
    }
    container assisted-replication {
      presence "enable assisted-replication";
      description
        "Deterministic AR replicator knobs";
      uses apply-advanced;
      leaf-list replicator-ip {
        type jt:ipaddr;
        max-elements 1;
        description
          "Set deterministic AR replicator ip for the flow";
      }
      leaf strict {
        type empty;
        description
          "Do not use any other replicator";
      }
      leaf-list fallback-replicator-ip {
        type jt:ipaddr;
        max-elements 1;
        description
          "Set Fallback replicator-ip";
      }
    }
    leaf damping {
      type string;
      description
        "Define BGP route flap damping parameters";
    }
    container aggregate-bandwidth {
      presence "enable aggregate-bandwidth";
      description
        "Advertise aggregate outbound link bandwidth";
      uses apply-advanced;
      choice transitive-type {
        case case_1 {
          leaf transitive {
            type empty;
            description
              "Transitive flag for link bandwidth";
          }
        }
        case case_2 {
          leaf non-transitive {
            type empty;
            description
              "Non-Transitive flag for link bandwidth";
          }
        }
      }
      leaf divide-equal {
        type empty;
        description
          "Divide-equal";
      }
    }
    container auto-link-bandwidth {
      presence "enable auto-link-bandwidth";
      description
        "Auto sense and attach link bandwidth community";
      uses apply-advanced;
      choice transitive-type {
        case case_1 {
          leaf transitive {
            type empty;
            description
              "Transitive flag for link bandwidth";
          }
        }
        case case_2 {
          leaf non-transitive {
            type empty;
            description
              "Non-Transitive flag for link bandwidth";
          }
        }
      }
    }
    leaf limit-bandwidth {
      type union {
        type uint64;
        type string {
          pattern "<.*>|$.*";
        }
      }
      description
        "Limit advertised aggregate outbound link bandwidth";
    }
    leaf no-entropy-label-capability {
      type empty;
      description
        "Don't advertise entropy label capability";
    }
    leaf as-path-prepend {
      type string;
      description
        "Prepend AS numbers to an AS path (BGP only)";
    }
    container as-path-expand {
      description
        "Prepend AS numbers prior to adding local-as (BGP only)";
      choice aspath_exp_value {
        case case_1 {
          container last-as {
            presence "enable last-as";
            description
              "Prepend last AS";
            leaf count {
              type union {
                type string {
                  pattern "<.*>|$.*";
                }
                type uint32 {
                  range "1 .. 32";
                }
              }
              description
                "Repeat count";
            }
          }
        }
        case case_2 {
          leaf aspath {
            type string;
            description
              "AS path string";
          }
        }
      }
    }
    container next-hop {
      description
        "Set the address of the next-hop router";
      choice nexthop_value {
        case case_1 {
          leaf self {
            type empty;
            description
              "Use a local address as the next-hop address";
          }
        }
        case case_2 {
          leaf peer-address {
            type empty;
            description
              "Use the remote peer address as the next-hop address";
          }
        }
        case case_3 {
          leaf address {
            type jt:ipaddr;
            description
              "Next-hop address";
          }
        }
        case case_4 {
          leaf reject {
            type empty;
            description
              "Use a reject next hop";
          }
        }
        case case_5 {
          leaf discard {
            type empty;
            description
              "Use a discard next hop";
          }
        }
        case case_6 {
          leaf next-table {
            type string;
            description
              "Perform a forwarding lookup in the specified table";
          }
        }
      }
    }
    container install-nexthop {
      description
        "Choose the next hop to be used for forwarding";
      choice strict_type {
        case case_1 {
          leaf strict {
            type empty;
            description
              "Do not use any other available next hops";
          }
        }
        case case_2 {
          leaf strict-named-lsp {
            type empty;
            description
              "Do not use any other non-lsp next hops";
          }
        }
      }
      choice nexthop-value {
        case case_1 {
          leaf-list lsp {
            type string;
            ordered-by user;
            description
              "Next-hop LSP name";
          }
        }
        case case_2 {
          leaf-list lsp-regex {
            type string;
            ordered-by user;
            description
              "Next-hop LSP name regular expression";
          }
        }
        case case_3 {
          leaf-list static-lsp {
            type string;
            ordered-by user;
            description
              "Next-hop static LSP name";
          }
        }
        case case_4 {
          leaf-list static-lsp-regex {
            type string;
            ordered-by user;
            description
              "Next-hop static LSP name regular expression";
          }
        }
        case case_5 {
          leaf non-lsp-nexthop {
            type empty;
            description
              "Next-hop with non-lsp";
          }
        }
        case case_6 {
          leaf non-labelled-nexthop {
            type empty;
            description
              "Next-hop without tag";
          }
        }
        case case_7 {
          leaf overlay-vxlan-interfaces {
            type empty;
            description
              "Next-hop for vxlan interfaces";
          }
        }
      }
      container except {
        description
          "Do not choose to install matching next hops";
        uses apply-advanced;
        choice nexthop-value {
          case case_1 {
            leaf-list lsp {
              type string;
              ordered-by user;
              description
                "Next-hop LSP name";
            }
          }
          case case_2 {
            leaf-list lsp-regex {
              type string;
              ordered-by user;
              description
                "Next-hop LSP name regular expression";
            }
          }
          case case_3 {
            leaf-list static-lsp {
              type string;
              ordered-by user;
              description
                "Next-hop static LSP name";
            }
          }
          case case_4 {
            leaf-list static-lsp-regex {
              type string;
              ordered-by user;
              description
                "Next-hop static LSP name regular expression";
            }
          }
          case case_5 {
            leaf non-lsp-nexthop {
              type empty;
              description
                "Next-hop with non-lsp";
            }
          }
          case case_6 {
            leaf non-labelled-nexthop {
              type empty;
              description
                "Next-hop without tag";
            }
          }
          case case_7 {
            leaf overlay-vxlan-interfaces {
              type empty;
              description
                "Next-hop for vxlan interfaces";
            }
          }
        }
        container fallback {
          description
            "Backup option";
          uses apply-advanced;
          choice nexthop-value {
            case case_1 {
              leaf-list lsp {
                type string;
                ordered-by user;
                description
                  "Next-hop LSP name";
              }
            }
            case case_2 {
              leaf-list lsp-regex {
                type string;
                ordered-by user;
                description
                  "Next-hop LSP name regular expression";
              }
            }
            case case_3 {
              leaf-list static-lsp {
                type string;
                ordered-by user;
                description
                  "Next-hop static LSP name";
              }
            }
            case case_4 {
              leaf-list static-lsp-regex {
                type string;
                ordered-by user;
                description
                  "Next-hop static LSP name regular expression";
              }
            }
            case case_5 {
              leaf non-lsp-nexthop {
                type empty;
                description
                  "Next-hop with non-lsp";
              }
            }
            case case_6 {
              leaf non-labelled-nexthop {
                type empty;
                description
                  "Next-hop without tag";
              }
            }
            case case_7 {
              leaf overlay-vxlan-interfaces {
                type empty;
                description
                  "Next-hop for vxlan interfaces";
              }
            }
          }
          container except {
            description
              "Do not choose to install matching next hops";
            uses apply-advanced;
            choice nexthop-value {
              case case_1 {
                leaf-list lsp {
                  type string;
                  ordered-by user;
                  description
                    "Next-hop LSP name";
                }
              }
              case case_2 {
                leaf-list lsp-regex {
                  type string;
                  ordered-by user;
                  description
                    "Next-hop LSP name regular expression";
                }
              }
              case case_3 {
                leaf-list static-lsp {
                  type string;
                  ordered-by user;
                  description
                    "Next-hop static LSP name";
                }
              }
              case case_4 {
                leaf-list static-lsp-regex {
                  type string;
                  ordered-by user;
                  description
                    "Next-hop static LSP name regular expression";
                }
              }
              case case_5 {
                leaf non-lsp-nexthop {
                  type empty;
                  description
                    "Next-hop with non-lsp";
                }
              }
              case case_6 {
                leaf non-labelled-nexthop {
                  type empty;
                  description
                    "Next-hop without tag";
                }
              }
              case case_7 {
                leaf overlay-vxlan-interfaces {
                  type empty;
                  description
                    "Next-hop for vxlan interfaces";
                }
              }
            }
          }
        }
      }
      container fallback {
        description
          "Backup option ";
        uses apply-advanced;
        choice nexthop-value {
          case case_1 {
            leaf-list lsp {
              type string;
              ordered-by user;
              description
                "Next-hop LSP name";
            }
          }
          case case_2 {
            leaf-list lsp-regex {
              type string;
              ordered-by user;
              description
                "Next-hop LSP name regular expression";
            }
          }
          case case_3 {
            leaf-list static-lsp {
              type string;
              ordered-by user;
              description
                "Next-hop static LSP name";
            }
          }
          case case_4 {
            leaf-list static-lsp-regex {
              type string;
              ordered-by user;
              description
                "Next-hop static LSP name regular expression";
            }
          }
          case case_5 {
            leaf non-lsp-nexthop {
              type empty;
              description
                "Next-hop with non-lsp";
            }
          }
          case case_6 {
            leaf non-labelled-nexthop {
              type empty;
              description
                "Next-hop without tag";
            }
          }
          case case_7 {
            leaf overlay-vxlan-interfaces {
              type empty;
              description
                "Next-hop for vxlan interfaces";
            }
          }
        }
        container except {
          description
            "Do not choose to install matching next hops";
          uses apply-advanced;
          choice nexthop-value {
            case case_1 {
              leaf-list lsp {
                type string;
                ordered-by user;
                description
                  "Next-hop LSP name";
              }
            }
            case case_2 {
              leaf-list lsp-regex {
                type string;
                ordered-by user;
                description
                  "Next-hop LSP name regular expression";
              }
            }
            case case_3 {
              leaf-list static-lsp {
                type string;
                ordered-by user;
                description
                  "Next-hop static LSP name";
              }
            }
            case case_4 {
              leaf-list static-lsp-regex {
                type string;
                ordered-by user;
                description
                  "Next-hop static LSP name regular expression";
              }
            }
            case case_5 {
              leaf non-lsp-nexthop {
                type empty;
                description
                  "Next-hop with non-lsp";
              }
            }
            case case_6 {
              leaf non-labelled-nexthop {
                type empty;
                description
                  "Next-hop without tag";
              }
            }
            case case_7 {
              leaf overlay-vxlan-interfaces {
                type empty;
                description
                  "Next-hop for vxlan interfaces";
              }
            }
          }
        }
      }
    }
    leaf trace {
      type empty;
      description
        "Log matches to a trace file";
    }
    container external {
      presence "enable external";
      description
        "External route";
      uses apply-advanced;
      leaf type {
        type union {
          type string {
            pattern "<.*>|$.*";
          }
          type int32 {
            range "1 .. 2";
          }
        }
        description
          "OSPF external metric type";
      }
      leaf nssa-only {
        type empty;
        description
          "Clear P-bit on lsa type 7";
      }
    }
    container load-balance {
      description
        "Type of load balancing in forwarding table";
      choice load_balance_type {
        case case_1 {
          leaf per-packet {
            type empty;
            description
              "Load balance on a per-packet basis deprecated, use per-flow instead";
          }
        }
        case case_2 {
          leaf per-flow {
            type empty;
            description
              "Load balance on a per-flow basis";
          }
        }
        case case_3;
        case case_4;
        case case_5;
        case case_6;
        case case_7;
        case case_8;
        case case_9;
        case case_10;
        case case_11;
      }
    }
    container advertise-locator {
      presence "enable advertise-locator";
      description
        "Advertise SRv6 Locator";
      uses apply-advanced;
      leaf internal {
        type empty;
        description
          "Advertise locator as Interal route";
      }
    }
    leaf set-down-bit {
      type empty;
      description
        "Set down bit";
    }
    leaf analyze {
      type empty;
      description
        "Send to registered controllers for analysis";
    }
    leaf destination-class {
      type string;
      description
        "Set destination class in forwarding table";
    }
    leaf source-class {
      type string;
      description
        "Set source class in forwarding table";
    }
    leaf forwarding-class {
      type string;
      description
        "Set source or destination class in forwarding table";
    }
    container map-to-interface {
      description
        "Set output logical interface";
      choice map_to_interface_value {
        case case_1 {
          leaf self {
            type empty;
            description
              "Map the interface to itself";
          }
        }
        case case_2 {
          leaf interface {
            type union {
              type jt:interface-name;
              type string {
                pattern "<.*>|$.*";
              }
            }
            description
              "Output logical interface";
          }
        }
      }
    }
    leaf-list ssm-source {
      type jt:ipaddr;
      ordered-by user;
      description
        "List of Sources for SSM mapping";
    }
    container p2mp-lsp-root {
      description
        "P2mp lsp root address";
      uses apply-advanced;
      leaf address {
        type jt:ipv4addr;
        description
          "Ipv4 root address";
      }
    }
    leaf dynamic-tunnel-attributes {
      type string;
      description
        "Choose the dynamic tunnel attributes used for forwarding";
    }
    leaf tunnel-end-point-address {
      type jt:ipaddr;
      description
        "Set tunnel end-point address of tunnel";
    }
    leaf selected-mldp-egress {
      type empty;
      description
        "This node should act as egress node for MLDP inband signalling";
    }
    leaf mhop-bfd-port {
      type empty;
      description
        "Use port number 4784 for MPLS-BFD as per RFC5884";
    }
    leaf no-backup {
      type empty;
      description
        "This prefix should not have backup";
    }
    leaf default-action {
      type enumeration {
        enum "accept" {
          description
            "Accept a route";
        }
        enum "reject" {
          description
            "Reject a route";
        }
      }
      description
        "Set default policy action";
    }
    leaf next {
      type enumeration {
        enum "policy" {
          description
            "Skip to next policy filter";
        }
        enum "term" {
          description
            "Skip to next term in a policy filter";
        }
      }
      description
        "Skip to next policy or term";
    }
    choice accept_reject {
      case case_1 {
        leaf accept {
          type empty;
          description
            "Accept a route";
        }
      }
      case case_2 {
        leaf reject {
          type empty;
          description
            "Reject a route";
        }
      }
    }
    container bgp-output-queue-priority {
      description
        "Set the BGP Update output queue priority.";
      choice class {
        case case_1 {
          leaf priority {
            type union {
              type string {
                pattern "<.*>|$.*";
              }
              type uint32 {
                range "1 .. 16";
              }
            }
            description
              "Output queue priority; higher is better";
          }
        }
        case case_2 {
          leaf expedited {
            type empty;
            description
              "Expedited queue; highest priority";
          }
        }
      }
    }
    leaf multipath-resolve {
      type empty;
      description
        "Use all paths for resolution over this prefix";
    }
    leaf source-routing-path-template {
      type string;
      description
        "Spring-te template to apply";
    }
    leaf label-allocation-fallback-reject {
      type empty;
      description
        "Suppress prefix export when label allocation fails";
    }
    leaf resolution-map {
      type string;
      description
        "Set resolution map modes";
    }
    leaf ignore-service-label {
      type empty;
      description
        "Ignore service labels";
    }
    container prefix-attribute-flags {
      presence "enable prefix-attribute-flags";
      description
        "Set ISIS prefix attribute flags sub TLV";
      uses apply-advanced;
      leaf node-segment-flag {
        type empty;
        description
          "Set node segment flag ";
      }
      leaf external-prefix-flag {
        type empty;
        description
          "Set external prefix flag ";
      }
      leaf anycast-flag {
        type empty;
        description
          "Set anycast flag ";
      }
      leaf entropy-label-capability-flag {
        type empty;
        description
          "Set entropy label capability flag ";
      }
    }
    container ipv4-source-router-id {
      presence "enable ipv4-source-router-id";
      description
        "Set IPv4 source router id in advertisement";
      uses apply-advanced;
      leaf router-id {
        type jt:ipaddr;
        description
          "Specify IPv4 address";
      }
    }
    container ipv6-source-router-id {
      presence "enable ipv6-source-router-id";
      description
        "Set IPv6 source router id in advertisement";
      uses apply-advanced;
      leaf router-id {
        type jt:ipv6addr;
        description
          "Specify IPv6 address";
      }
    }
    leaf request-long-lived-ack {
      type empty;
      description
        "Advertise route after forwarding is programmed";
    }
    leaf send-withdrawal-on-route-change {
      type empty;
      description
        "Withdraw route if change is not acked from forwarding";
    }
    container slice {
      description
        "Configure Policy Slice action";
      leaf slice-name {
        type string {
          length "1 .. 64";
        }
        description
          "Slice Name";
      }
    }
    leaf filter {
      type string;
      description
        "Set firewall-filter name";
    }
    leaf strip-as-path {
      type empty;
      description
        "Remove the incoming BGP as-path and replace with local AS";
    }
    container request-acknowledgements {
      description
        "Set request acknowledgement";
      leaf nexthop-ack {
        type empty;
        description
          "Set nexthop acknowledgement ";
      }
      leaf route-ack {
        type empty;
        description
          "Set route acknowledgement ";
      }
    }
  }

  grouping rpd_rib_group_type {
    description
      "Routing table group";
    leaf name {
      type string;
      description
        "Routing table group";
    }
    uses apply-advanced;
    leaf export-rib {
      type string;
      description
        "Export routing table";
    }
    leaf-list import-rib {
      type string;
      ordered-by user;
      description
        "Import routing table";
    }
    leaf-list import-policy {
      type jt:policy-algebra;
      ordered-by user;
      description
        "Import policy";
    }
  }

  grouping rtf_prefix_list_items {
    leaf name {
      type string {
        length "1 .. 63";
      }
      description
        "Family route-target prefix";
    }
    uses apply-advanced;
  }

  grouping scripts_type {
    uses apply-advanced;
    container commit {
      description
        "Commit-time scripting mechanism";
      uses apply-advanced;
      leaf allow-transients {
        type empty;
        description
          "Allow loading of transient configuration changes";
      }
      container traceoptions {
        description
          "Trace options for commit scripts";
        uses script_traceoptions;
      }
      leaf refresh {
        type empty;
        description
          "Refresh all operation scripts from their source";
      }
      leaf refresh-from {
        type string {
          length "1 .. 254";
        }
        description
          "Refresh all operation scripts from a given base URL";
      }
      leaf max-datasize {
        type string;
        units "bytes";
        description
          "Maximum data segment size for scripts execution";
      }
      leaf direct-access {
        type empty;
        description
          "Access the configuration directly from database";
      }
      container dampen {
        presence "enable dampen";
        description
          "Dampen execution of commit scripts";
        uses apply-advanced;
        container dampen-options {
          description
            "Dampen options for commit scripts";
          uses apply-advanced;
          leaf cpu-factor {
            type union {
              type string {
                pattern "<.*>|$.*";
              }
              type uint32 {
                range "1 .. 100";
              }
            }
            description
              "CPU factor at which to pause";
          }
          leaf line-interval {
            type union {
              type string {
                pattern "<.*>|$.*";
              }
              type uint32 {
                range "1 .. 4294967295";
              }
            }
            description
              "Line interval at which to pause";
          }
          leaf time-interval {
            type union {
              type string {
                pattern "<.*>|$.*";
              }
              type uint32 {
                range "1 .. 4294967295";
              }
            }
            units "microseconds";
            description
              "Time to pause";
          }
        }
      }
      list file {
        key "name";
        ordered-by user;
        description
          "Commit script file";
        uses commit_scripts_file_type;
      }
    }
    container op {
      description
        "Operations scripting";
      uses apply-advanced;
      leaf refresh {
        type empty;
        description
          "Refresh all operation scripts from their source";
      }
      leaf refresh-from {
        type string {
          length "1 .. 254";
        }
        description
          "Refresh all operation scripts from a given base URL";
      }
      container traceoptions {
        description
          "Trace options for operation scripts";
        uses script_traceoptions;
      }
      list file {
        key "name";
        description
          "Configuration for each operation script";
        uses op_scripts_file_type;
      }
      leaf no-allow-url {
        type empty;
        description
          "Do not allow the remote execution of op scripts";
      }
      leaf allow-url-for-python {
        type empty;
        description
          "Allow the remote execution of Python op scripts";
      }
      leaf max-datasize {
        type string;
        units "bytes";
        description
          "Maximum data segment size for scripts execution";
      }
      container dampen {
        presence "enable dampen";
        description
          "Dampen execution of op scripts";
        uses apply-advanced;
        container dampen-options {
          description
            "Dampen options for op scripts";
          uses apply-advanced;
          leaf cpu-factor {
            type union {
              type string {
                pattern "<.*>|$.*";
              }
              type uint32 {
                range "1 .. 100";
              }
            }
            description
              "CPU factor at which to pause";
          }
          leaf line-interval {
            type union {
              type string {
                pattern "<.*>|$.*";
              }
              type uint32 {
                range "1 .. 4294967295";
              }
            }
            description
              "Line interval at which to pause";
          }
          leaf time-interval {
            type union {
              type string {
                pattern "<.*>|$.*";
              }
              type uint32 {
                range "1 .. 4294967295";
              }
            }
            units "microseconds";
            description
              "Time to pause";
          }
        }
      }
      container start {
        description
          "Start op scripts with start-criteria check";
        uses apply-advanced;
        container start-options {
          description
            "Start options for op scripts";
          uses apply-advanced;
          leaf mem-factor {
            type union {
              type string {
                pattern "<.*>|$.*";
              }
              type uint32 {
                range "1 .. 100";
              }
            }
            description
              "Memory factor at which to start/stop";
          }
        }
      }
    }
    container translation {
      description
        "Translation scripts";
      uses apply-advanced;
      leaf max-datasize {
        type string;
        units "bytes";
        description
          "Maximum data segment size for translation scripts execution";
      }
    }
    container action {
      description
        "Action scripts";
      uses apply-advanced;
      leaf max-datasize {
        type string;
        units "bytes";
        description
          "Maximum data segment size for action scripts execution";
      }
    }
    leaf language {
      type enumeration {
        enum "python" {
          description
            "Allow Python 2.x scripts on-box (Python2.x support will be deprecated in 21.1)";
        }
        enum "python3" {
          description
            "Allow Python 3.x scripts on-box";
        }
      }
      description
        "Allow/Disallow Python scripts on-box";
    }
    leaf synchronize {
      type empty;
      description
        "Push all scripts to other RE on commit synchronize";
    }
  }

  grouping commit_scripts_file_type {
    leaf name {
      type string {
        length "1 .. 254";
      }
      description
        "Local filename of the script file";
    }
    uses apply-advanced;
    leaf optional {
      type empty;
      description
        "Allow commit to succeed if the script is missing";
    }
    leaf source {
      type string {
        length "1 .. 254";
      }
      description
        "URL of source for this script";
    }
    leaf cert-file {
      type string;
      description
        "Specify the certificate file name";
    }
    leaf routing-instance {
      type string;
      description
        "Routing instance";
    }
    leaf refresh {
      type empty;
      description
        "Refresh all operation scripts from their source";
    }
    leaf refresh-from {
      type string {
        length "1 .. 254";
      }
      description
        "Refresh all operation scripts from a given base URL";
    }
    container checksum {
      description
        "Checksum of this script";
      uses apply-advanced;
      leaf sha-256 {
        type string {
          length "1 .. 254";
        }
        description
          "SHA-256 checksum of this script";
      }
    }
  }

  grouping op_scripts_file_type {
    leaf name {
      type string {
        length "1 .. 254";
      }
      description
        "Local filename of the script file";
    }
    uses apply-advanced;
    leaf command {
      type string {
        length "1 .. 254";
      }
      description
        "Command alias for the script file";
    }
    container dampen {
      presence "enable dampen";
      description
        "Dampen execution of the script";
      uses apply-advanced;
      container dampen-options {
        description
          "Dampen options for the script";
        uses apply-advanced;
        leaf cpu-factor {
          type union {
            type string {
              pattern "<.*>|$.*";
            }
            type uint32 {
              range "1 .. 100";
            }
          }
          description
            "CPU factor at which to pause";
        }
        leaf line-interval {
          type union {
            type string {
              pattern "<.*>|$.*";
            }
            type uint32 {
              range "1 .. 4294967295";
            }
          }
          description
            "Line interval at which to pause";
        }
        leaf time-interval {
          type union {
            type string {
              pattern "<.*>|$.*";
            }
            type uint32 {
              range "1 .. 4294967295";
            }
          }
          units "microseconds";
          description
            "Time to pause";
        }
      }
    }
    container start {
      description
        "Start op scripts with start-criteria check";
      uses apply-advanced;
      container start-options {
        description
          "Start options for the op script";
        uses apply-advanced;
        leaf mem-factor {
          type union {
            type string {
              pattern "<.*>|$.*";
            }
            type uint32 {
              range "1 .. 100";
            }
          }
          description
            "Memory factor at which to start/stop";
        }
      }
    }
    leaf description {
      type string {
        length "1 .. 254";
      }
      description
        "Description of the script";
    }
    leaf source {
      type string {
        length "1 .. 254";
      }
      description
        "URL of source for this script";
    }
    leaf cert-file {
      type string;
      description
        "Specify the certificate file name";
    }
    leaf routing-instance {
      type string;
      description
        "Routing instance";
    }
    leaf allow-commands {
      type jt:regular-expression;
      description
        "Regular expression for commands to allow explicitly";
    }
    leaf refresh {
      type empty;
      description
        "Refresh all operation scripts from their source";
    }
    leaf refresh-from {
      type string {
        length "1 .. 254";
      }
      description
        "Refresh all operation scripts from a given base URL";
    }
    list arguments {
      key "name";
      description
        "Command line argument to the script";
      leaf name {
        type string {
          length "1 .. 254";
        }
        description
          "Name of the argument";
      }
      uses apply-advanced;
      leaf description {
        type string {
          length "1 .. 254";
        }
        description
          "Description of the argument";
      }
    }
    container checksum {
      description
        "Checksum of this script";
      uses apply-advanced;
      leaf sha-256 {
        type string {
          length "1 .. 254";
        }
        description
          "SHA-256 checksum of this script";
      }
    }
  }

  grouping script_traceoptions {
    uses apply-advanced;
    leaf no-remote-trace {
      type empty;
      description
        "Disable remote tracing";
    }
    container file {
      description
        "Trace file information";
      leaf filename {
        type string {
          length "1 .. 1024";
        }
        description
          "Name of file in which to write trace information";
      }
      leaf size {
        type string;
        description
          "Maximum trace file size";
      }
      leaf files {
        type union {
          type string {
            pattern "<.*>|$.*";
          }
          type uint32 {
            range "2 .. 1000";
          }
        }
        default "3";
        description
          "Maximum number of trace files";
      }
      choice world-readable-choice {
        leaf world-readable {
          type empty;
          description
            "Allow any user to read the log file";
        }
        leaf no-world-readable {
          type empty;
          description
            "Don't allow any user to read the log file";
        }
      }
    }
    list flag {
      key "name";
      description
        "Tracing parameters";
      leaf name {
        type enumeration {
          enum "all" {
            description
              "Trace all operations";
          }
          enum "events" {
            description
              "Trace important events";
          }
          enum "input" {
            description
              "Trace script input data";
          }
          enum "offline" {
            description
              "Generate data for offline development";
          }
          enum "output" {
            description
              "Trace script output data";
          }
          enum "rpc" {
            description
              "Trace script RPCs";
          }
          enum "xslt" {
            description
              "Trace the XSLT library";
          }
        }
      }
    }
  }

  grouping security-ipsec-vpn {
    uses apply-advanced;
    container traceoptions {
      description
        "Trace options for IPSec data-plane debug";
      uses ipsec-traceoptions;
    }
    list security-association {
      key "name";
      ordered-by user;
      description
        "Define an IPSec security association";
      uses ipsec-sa;
    }
  }

  grouping ipsec-sa {
    leaf name {
      type string {
        length "1 .. 32";
      }
      description
        "Name of IPSec security association";
    }
    uses apply-advanced;
    leaf description {
      type string {
        length "1 .. 80";
      }
      description
        "Text description of security association";
    }
    leaf mode {
      type enumeration {
        enum "transport" {
          description
            "Transport mode";
        }
        enum "tunnel" {
          description
            "Tunnel mode";
        }
      }
      default "transport";
      description
        "Define security association mode";
    }
    choice sa_choice {
      case case_1 {
        container manual {
          description
            "Define a manual security association";
          uses apply-advanced;
          list direction {
            key "name";
            ordered-by user;
            description
              "Define the direction of the security association";
            leaf name {
              type enumeration {
                enum "inbound" {
                  description
                    "Inbound security association";
                }
                enum "outbound" {
                  description
                    "Outbound security association";
                }
                enum "bidirectional" {
                  description
                    "Bidirectional security association";
                }
              }
            }
            uses apply-advanced;
            leaf protocol {
              type enumeration {
                enum "ah" {
                  description
                    "Authentication header";
                }
                enum "esp" {
                  description
                    "Encapsulated Security Payload header";
                }
                enum "bundle" {
                  description
                    "Bundle (AH authentication plus ESP encryption)";
                }
              }
              mandatory true;
              description
                "Define an IPSec protocol for the security association";
            }
            leaf spi {
              type union {
                type string {
                  pattern "<.*>|$.*";
                }
                type uint32 {
                  range "256 .. 16639";
                }
              }
              mandatory true;
              description
                "Define security parameter index";
            }
            container authentication {
              description
                "Define authentication parameters";
              uses apply-advanced;
              leaf algorithm {
                type enumeration {
                  enum "hmac-md5-96" {
                    description
                      "HMAC-MD5-96 authentication algorithm";
                  }
                  enum "hmac-sha1-96" {
                    description
                      "HMAC-SHA1-96 authentication algorithm";
                  }
                  enum "hmac-sha2-256" {
                    description
                      "HMAC-SHA2-256 authentication algorithm";
                  }
                  enum "hmac-sha-256-128" {
                    description
                      "HMAC-SHA-256-128 authentication algorithm";
                  }
                }
                mandatory true;
                description
                  "Define authentication algorithm";
              }
              container key {
                description
                  "Define an authentication key";
                choice key-choice {
                  case case_1 {
                    leaf ascii-text {
                      type string {
                        length "1 .. 255";
                      }
                      description
                        "Format as text";
                    }
                  }
                  case case_2 {
                    leaf hexadecimal {
                      type string {
                        length "1 .. 255";
                      }
                      description
                        "Format as hexadecimal";
                    }
                  }
                }
              }
            }
            container encryption {
              description
                "Define encryption parameters";
              uses apply-advanced;
              leaf algorithm {
                type enumeration {
                  enum "des-cbc" {
                    description
                      "DES-CBC encryption algorithm";
                  }
                  enum "3des-cbc" {
                    description
                      "3DES-CBC encryption algorithm";
                  }
                  enum "aes-128-cbc" {
                    description
                      "AES-CBC 128-bit encryption algorithm";
                  }
                  enum "aes-192-cbc" {
                    description
                      "AES-CBC 192-bit encryption algorithm";
                  }
                  enum "aes-256-cbc" {
                    description
                      "AES-CBC 256-bit encryption algorithm";
                  }
                }
                mandatory true;
                description
                  "Define encryption algorithm";
              }
              container key {
                description
                  "Define an encryption key";
                choice key-choice {
                  case case_1 {
                    leaf ascii-text {
                      type string {
                        length "1 .. 255";
                      }
                      description
                        "Format as text";
                    }
                  }
                  case case_2 {
                    leaf hexadecimal {
                      type string {
                        length "1 .. 255";
                      }
                      description
                        "Format as hexadecimal";
                    }
                  }
                }
              }
            }
          }
        }
      }
      case case_2;
    }
  }

  grouping ipsec-traceoptions {
    description
      "Data-plane IPSec tracing options";
    uses apply-advanced;
    list flag {
      key "name";
      ordered-by user;
      description
        "Events to include in data-plane IPSec trace output";
      leaf name {
        type enumeration {
          enum "packet-processing" {
            description
              "Trace data packet processing events";
          }
          enum "packet-drops" {
            description
              "Trace packet drops";
          }
          enum "security-associations" {
            description
              "Trace security association management events";
          }
          enum "next-hop-tunnel-binding" {
            description
              "Trace next-hop tunnel binding events";
          }
          enum "all" {
            description
              "Trace with all flags enabled";
          }
        }
      }
    }
  }

  grouping security-traceoptions {
    description
      "Trace options for key management process";
    uses apply-advanced;
    leaf no-remote-trace {
      type empty;
      description
        "Disable remote tracing";
    }
    container file {
      description
        "Trace file information";
      leaf filename {
        type string {
          length "1 .. 1024";
        }
        description
          "Name of file in which to write trace information";
      }
      leaf size {
        type string;
        description
          "Maximum trace file size";
      }
      leaf files {
        type union {
          type string {
            pattern "<.*>|$.*";
          }
          type uint32 {
            range "2 .. 1000";
          }
        }
        default "3";
        description
          "Maximum number of trace files";
      }
      choice world-readable-choice {
        leaf world-readable {
          type empty;
          description
            "Allow any user to read the log file";
        }
        leaf no-world-readable {
          type empty;
          description
            "Don't allow any user to read the log file";
        }
      }
      leaf match {
        type jt:regular-expression;
        description
          "Regular expression for lines to be logged";
      }
    }
    list flag {
      key "name";
      ordered-by user;
      description
        "Tracing parameters";
      leaf name {
        type enumeration {
          enum "timer" {
            description
              "Trace internal timer events";
          }
          enum "routing-socket" {
            description
              "Trace routing socket messages";
          }
          enum "parse" {
            description
              "Trace configuration processing";
          }
          enum "config" {
            description
              "Trace configuration download processing";
          }
          enum "ike" {
            description
              "Trace IKE module processing";
          }
          enum "policy-manager" {
            description
              "Trace policy manager processing";
          }
          enum "general" {
            description
              "Trace general events";
          }
          enum "database" {
            description
              "Trace security associations database events";
          }
          enum "certificates" {
            description
              "Trace certificate events";
          }
          enum "snmp" {
            description
              "Trace SNMP operations";
          }
          enum "thread" {
            description
              "Trace thread processing";
          }
          enum "high-availability" {
            description
              "Trace high-availability operations";
          }
          enum "next-hop-tunnels" {
            description
              "Trace next-hop-tunnels operations";
          }
          enum "all" {
            description
              "Trace everything";
          }
          enum "ams" {
            description
              "Trace AMS events";
          }
          enum "lic" {
            description
              "Trace License events";
          }
        }
      }
    }
    leaf level {
      type enumeration {
        enum "error" {
          description
            "Match error conditions";
        }
        enum "warning" {
          description
            "Match warning messages";
        }
        enum "notice" {
          description
            "Match conditions that should be handled specially";
        }
        enum "info" {
          description
            "Match informational messages";
        }
        enum "verbose" {
          description
            "Match verbose messages";
        }
        enum "all" {
          description
            "Match all levels";
        }
      }
      default "error";
      description
        "Level of debugging output";
    }
  }

  grouping source_address_filter_list_items {
    leaf address {
      type jt:ipprefix;
      description
        "IP address or hostname";
    }
    leaf choice-ident {
      type enumeration {
        enum "exact";
        enum "longer";
        enum "orlonger";
        enum "upto";
        enum "through";
        enum "prefix-length-range";
      }
    }
    leaf choice-value {
      type string;
    }
    uses apply-advanced;
    container metric {
      description
        "Metric value";
      uses apply-advanced;
      choice metric_action {
        case case_1 {
          leaf metric {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
        case case_4 {
          container igp {
            presence "enable igp";
            description
              "Track the IGP metric (BGP only)";
            leaf metric_offset {
              type union {
                type int32;
                type string {
                  pattern "<.*>|$.*";
                }
              }
              description
                "Metric offset for MED";
            }
          }
        }
        case case_5 {
          container minimum-igp {
            presence "enable minimum-igp";
            description
              "Track the minimum IGP metric (BGP only)";
            leaf metric_offset {
              type union {
                type int32;
                type string {
                  pattern "<.*>|$.*";
                }
              }
              description
                "Metric offset for MED";
            }
          }
        }
        case case_6 {
          container expression {
            description
              "Calculate value based on route metric and metric2";
            uses metric_expression_type;
          }
        }
        case case_7 {
          leaf aigp {
            type empty;
            description
              "Use aigp, if it exists, to set the IGP metric";
          }
        }
        case case_8 {
          container effective-aigp {
            presence "enable effective-aigp";
            description
              "Track the effective AIGP metric (BGP only)";
            leaf metric_offset {
              type union {
                type int32;
                type string {
                  pattern "<.*>|$.*";
                }
              }
              description
                "Metric offset for MED";
            }
          }
        }
        case case_9 {
          container minimum-effective-aigp {
            presence "enable minimum-effective-aigp";
            description
              "Track the minimum effective AIGP metric (BGP only)";
            leaf metric_offset {
              type union {
                type int32;
                type string {
                  pattern "<.*>|$.*";
                }
              }
              description
                "Metric offset for MED";
            }
          }
        }
      }
    }
    container metric2 {
      description
        "Metric value 2";
      uses apply-advanced;
      choice metric_action {
        case case_1 {
          leaf metric2 {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container metric3 {
      description
        "Metric value 3";
      uses apply-advanced;
      choice metric_action {
        case case_1 {
          leaf metric3 {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container metric4 {
      description
        "Metric value 4";
      uses apply-advanced;
      choice metric_action {
        case case_1 {
          leaf metric4 {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container tag {
      description
        "Tag string";
      uses apply-advanced;
      choice metric_action {
        case case_1 {
          leaf tag {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container tag2 {
      description
        "Tag string 2";
      uses apply-advanced;
      choice metric_action {
        case case_1 {
          leaf tag2 {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container preference {
      description
        "Preference value";
      uses apply-advanced;
      choice metric_action {
        case case_1 {
          leaf preference {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container preference2 {
      description
        "Preference value 2";
      uses apply-advanced;
      choice metric_action {
        case case_1 {
          leaf preference2 {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container color {
      description
        "Color (preference) value";
      uses apply-advanced;
      choice metric_action {
        case case_1 {
          leaf color {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container color2 {
      description
        "Color (preference) value 2";
      uses apply-advanced;
      choice metric_action {
        case case_1 {
          leaf color2 {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container local-preference {
      description
        "Local preference associated with a route";
      uses apply-advanced;
      choice metric_action {
        case case_1 {
          leaf local-preference {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    container credibility {
      description
        "TED credibility value for entries from BGP-TE";
      uses apply-advanced;
      choice metric_action {
        case case_1 {
          leaf credibility {
            type union {
              type uint32;
              type string {
                pattern "<.*>|$.*";
              }
            }
          }
        }
        case case_2 {
          leaf add {
            type union {
              type uint32;
              type string {
                pattern "<.*>|$.*";
              }
            }
            description
              "Add constant to attribute";
          }
        }
        case case_3 {
          leaf subtract {
            type union {
              type uint32;
              type string {
                pattern "<.*>|$.*";
              }
            }
            description
              "Subtract constant from attribute";
          }
        }
      }
    }
    leaf priority {
      type enumeration {
        enum "high" {
          description
            "Set priority to high";
        }
        enum "medium" {
          description
            "Set priority to medium";
        }
        enum "low" {
          description
            "Set priority to low";
        }
      }
      description
        "Set priority for route installation";
    }
    container prefix-segment {
      description
        "Set prefix segment attributes";
      uses apply-advanced;
      list algorithm {
        key "name";
        max-elements 15;
        description
          "Set prefix segment attributes for strict/flex algorithm ";
        leaf name {
          type union {
            type string {
              pattern "<.*>|$.*";
            }
            type uint32 {
              range "1 .. 255";
            }
          }
          mandatory true;
          description
            "Set prefix segment for strict/flex algorithm";
        }
        leaf index {
          type union {
            type string {
              pattern "<.*>|$.*";
            }
            type uint32 {
              range "0 .. 1048575";
            }
          }
          mandatory true;
          description
            "Set prefix segment index id";
        }
        leaf node-segment {
          type empty;
          description
            "Set node segment flag for this prefix segment";
        }
      }
      leaf index {
        type union {
          type string {
            pattern "<.*>|$.*";
          }
          type uint32 {
            range "0 .. 1048575";
          }
        }
        description
          "Set prefix segment index id";
      }
      leaf node-segment {
        type empty;
        description
          "Set node segment flag for default prefix segment";
      }
      leaf redistribute {
        type empty;
        description
          "Redistribute prefix-segment from route entry";
      }
    }
    leaf label-allocation {
      type enumeration {
        enum "per-table" {
          description
            "Set per-table label allocation mode";
        }
        enum "per-nexthop" {
          description
            "Set per-nexthop label allocation mode";
        }
        enum "per-table-localize" {
          description
            "Set per-table-localize label allocation mode";
        }
      }
      description
        "Set label allocation mode";
    }
    container add-path {
      description
        "Set BGP add-path attributes";
      leaf send-count {
        type union {
          type string {
            pattern "<.*>|$.*";
          }
          type uint32 {
            range "2 .. 64";
          }
        }
        description
          "Number of add-paths sent";
      }
    }
    leaf fib-install-priority {
      type enumeration {
        enum "high" {
          description
            "Set Fib install priority  to high";
        }
        enum "medium" {
          description
            "Set Fib install priority to medium ";
        }
      }
      description
        "Set Fib Instalation priority of a route";
    }
    leaf validation-state {
      type enumeration {
        enum "valid" {
          description
            "Set validaton-state to valid";
        }
        enum "invalid" {
          description
            "Set validation-state to invalid";
        }
        enum "unknown" {
          description
            "Set validation-state to unknown";
        }
      }
      description
        "Set validation-state of a route";
    }
    leaf origin {
      type enumeration {
        enum "igp" {
          description
            "Path originated in the local IGP";
        }
        enum "egp" {
          description
            "Path originated in another AS";
        }
        enum "incomplete" {
          description
            "Path was learned by some other means";
        }
      }
      description
        "BGP path origin";
    }
    container srv6 {
      description
        "Configure SID with 128 bit address";
      leaf sid {
        type jt:ipv6addr;
        description
          "IPv6 Address";
      }
      leaf locator {
        type string;
        description
          "Name of locator";
      }
      choice locator_type {
        case case_1 {
          leaf micro-dt4-sid {
            type empty;
            description
              "Micro SID type dt4";
          }
        }
        case case_2 {
          leaf micro-dt6-sid {
            type empty;
            description
              "Micro SID type dt6";
          }
        }
        case case_3 {
          leaf micro-dt46-sid {
            type empty;
            description
              "Micro SID type dt46";
          }
        }
      }
    }
    container aigp-originate {
      presence "enable aigp-originate";
      description
        "Originate a BGP AIGP attribute";
      leaf distance {
        type union {
          type uint32;
          type string {
            pattern "<.*>|$.*";
          }
        }
        description
          "AIGP distance";
      }
    }
    container aigp-adjust {
      description
        "Adjust a BGP AIGP attribute";
      choice math-op {
        case case_1 {
          leaf add {
            type empty;
          }
        }
        case case_2 {
          leaf subtract {
            type empty;
          }
        }
        case case_3 {
          leaf multiply {
            type empty;
          }
        }
        case case_4 {
          leaf divide {
            type empty;
          }
        }
      }
      choice adjust-value {
        case case_1 {
          leaf user-value {
            type union {
              type uint64;
              type string {
                pattern "<.*>|$.*";
              }
            }
            description
              "Adjustment value";
          }
        }
        case case_2 {
          leaf distance-to-protocol-nexthop {
            type empty;
            description
              "Metric2";
          }
        }
      }
    }
    list community {
      key "choice-ident choice-value community-name";
      ordered-by user;
      description
        "BGP community properties associated with a route";
      leaf choice-ident {
        type enumeration {
          enum "equal-literal";
          enum "set";
          enum "plus-literal";
          enum "add";
          enum "minus-literal";
          enum "delete";
        }
      }
      leaf choice-value {
        type string;
      }
      leaf community-name {
        type string;
        description
          "Name to identify a BGP community";
      }
    }
    list tunnel-attribute {
      key "choice-ident choice-value tunnel-attribute-name";
      ordered-by user;
      description
        "BGP tunnel attribute associated with a route";
      leaf choice-ident {
        type enumeration {
          enum "set";
          enum "remove";
        }
      }
      leaf choice-value {
        type string;
      }
      leaf tunnel-attribute-name {
        type string;
        description
          "Name of a tunnel attribute , or 'all'";
      }
    }
    container assisted-replication {
      presence "enable assisted-replication";
      description
        "Deterministic AR replicator knobs";
      uses apply-advanced;
      leaf-list replicator-ip {
        type jt:ipaddr;
        max-elements 1;
        description
          "Set deterministic AR replicator ip for the flow";
      }
      leaf strict {
        type empty;
        description
          "Do not use any other replicator";
      }
      leaf-list fallback-replicator-ip {
        type jt:ipaddr;
        max-elements 1;
        description
          "Set Fallback replicator-ip";
      }
    }
    leaf damping {
      type string;
      description
        "Define BGP route flap damping parameters";
    }
    container aggregate-bandwidth {
      presence "enable aggregate-bandwidth";
      description
        "Advertise aggregate outbound link bandwidth";
      uses apply-advanced;
      choice transitive-type {
        case case_1 {
          leaf transitive {
            type empty;
            description
              "Transitive flag for link bandwidth";
          }
        }
        case case_2 {
          leaf non-transitive {
            type empty;
            description
              "Non-Transitive flag for link bandwidth";
          }
        }
      }
      leaf divide-equal {
        type empty;
        description
          "Divide-equal";
      }
    }
    container auto-link-bandwidth {
      presence "enable auto-link-bandwidth";
      description
        "Auto sense and attach link bandwidth community";
      uses apply-advanced;
      choice transitive-type {
        case case_1 {
          leaf transitive {
            type empty;
            description
              "Transitive flag for link bandwidth";
          }
        }
        case case_2 {
          leaf non-transitive {
            type empty;
            description
              "Non-Transitive flag for link bandwidth";
          }
        }
      }
    }
    leaf limit-bandwidth {
      type union {
        type uint64;
        type string {
          pattern "<.*>|$.*";
        }
      }
      description
        "Limit advertised aggregate outbound link bandwidth";
    }
    leaf no-entropy-label-capability {
      type empty;
      description
        "Don't advertise entropy label capability";
    }
    leaf as-path-prepend {
      type string;
      description
        "Prepend AS numbers to an AS path (BGP only)";
    }
    container as-path-expand {
      description
        "Prepend AS numbers prior to adding local-as (BGP only)";
      choice aspath_exp_value {
        case case_1 {
          container last-as {
            presence "enable last-as";
            description
              "Prepend last AS";
            leaf count {
              type union {
                type string {
                  pattern "<.*>|$.*";
                }
                type uint32 {
                  range "1 .. 32";
                }
              }
              description
                "Repeat count";
            }
          }
        }
        case case_2 {
          leaf aspath {
            type string;
            description
              "AS path string";
          }
        }
      }
    }
    container next-hop {
      description
        "Set the address of the next-hop router";
      choice nexthop_value {
        case case_1 {
          leaf self {
            type empty;
            description
              "Use a local address as the next-hop address";
          }
        }
        case case_2 {
          leaf peer-address {
            type empty;
            description
              "Use the remote peer address as the next-hop address";
          }
        }
        case case_3 {
          leaf address {
            type jt:ipaddr;
            description
              "Next-hop address";
          }
        }
        case case_4 {
          leaf reject {
            type empty;
            description
              "Use a reject next hop";
          }
        }
        case case_5 {
          leaf discard {
            type empty;
            description
              "Use a discard next hop";
          }
        }
        case case_6 {
          leaf next-table {
            type string;
            description
              "Perform a forwarding lookup in the specified table";
          }
        }
      }
    }
    container install-nexthop {
      description
        "Choose the next hop to be used for forwarding";
      choice strict_type {
        case case_1 {
          leaf strict {
            type empty;
            description
              "Do not use any other available next hops";
          }
        }
        case case_2 {
          leaf strict-named-lsp {
            type empty;
            description
              "Do not use any other non-lsp next hops";
          }
        }
      }
      choice nexthop-value {
        case case_1 {
          leaf-list lsp {
            type string;
            ordered-by user;
            description
              "Next-hop LSP name";
          }
        }
        case case_2 {
          leaf-list lsp-regex {
            type string;
            ordered-by user;
            description
              "Next-hop LSP name regular expression";
          }
        }
        case case_3 {
          leaf-list static-lsp {
            type string;
            ordered-by user;
            description
              "Next-hop static LSP name";
          }
        }
        case case_4 {
          leaf-list static-lsp-regex {
            type string;
            ordered-by user;
            description
              "Next-hop static LSP name regular expression";
          }
        }
        case case_5 {
          leaf non-lsp-nexthop {
            type empty;
            description
              "Next-hop with non-lsp";
          }
        }
        case case_6 {
          leaf non-labelled-nexthop {
            type empty;
            description
              "Next-hop without tag";
          }
        }
        case case_7 {
          leaf overlay-vxlan-interfaces {
            type empty;
            description
              "Next-hop for vxlan interfaces";
          }
        }
      }
      container except {
        description
          "Do not choose to install matching next hops";
        uses apply-advanced;
        choice nexthop-value {
          case case_1 {
            leaf-list lsp {
              type string;
              ordered-by user;
              description
                "Next-hop LSP name";
            }
          }
          case case_2 {
            leaf-list lsp-regex {
              type string;
              ordered-by user;
              description
                "Next-hop LSP name regular expression";
            }
          }
          case case_3 {
            leaf-list static-lsp {
              type string;
              ordered-by user;
              description
                "Next-hop static LSP name";
            }
          }
          case case_4 {
            leaf-list static-lsp-regex {
              type string;
              ordered-by user;
              description
                "Next-hop static LSP name regular expression";
            }
          }
          case case_5 {
            leaf non-lsp-nexthop {
              type empty;
              description
                "Next-hop with non-lsp";
            }
          }
          case case_6 {
            leaf non-labelled-nexthop {
              type empty;
              description
                "Next-hop without tag";
            }
          }
          case case_7 {
            leaf overlay-vxlan-interfaces {
              type empty;
              description
                "Next-hop for vxlan interfaces";
            }
          }
        }
        container fallback {
          description
            "Backup option";
          uses apply-advanced;
          choice nexthop-value {
            case case_1 {
              leaf-list lsp {
                type string;
                ordered-by user;
                description
                  "Next-hop LSP name";
              }
            }
            case case_2 {
              leaf-list lsp-regex {
                type string;
                ordered-by user;
                description
                  "Next-hop LSP name regular expression";
              }
            }
            case case_3 {
              leaf-list static-lsp {
                type string;
                ordered-by user;
                description
                  "Next-hop static LSP name";
              }
            }
            case case_4 {
              leaf-list static-lsp-regex {
                type string;
                ordered-by user;
                description
                  "Next-hop static LSP name regular expression";
              }
            }
            case case_5 {
              leaf non-lsp-nexthop {
                type empty;
                description
                  "Next-hop with non-lsp";
              }
            }
            case case_6 {
              leaf non-labelled-nexthop {
                type empty;
                description
                  "Next-hop without tag";
              }
            }
            case case_7 {
              leaf overlay-vxlan-interfaces {
                type empty;
                description
                  "Next-hop for vxlan interfaces";
              }
            }
          }
          container except {
            description
              "Do not choose to install matching next hops";
            uses apply-advanced;
            choice nexthop-value {
              case case_1 {
                leaf-list lsp {
                  type string;
                  ordered-by user;
                  description
                    "Next-hop LSP name";
                }
              }
              case case_2 {
                leaf-list lsp-regex {
                  type string;
                  ordered-by user;
                  description
                    "Next-hop LSP name regular expression";
                }
              }
              case case_3 {
                leaf-list static-lsp {
                  type string;
                  ordered-by user;
                  description
                    "Next-hop static LSP name";
                }
              }
              case case_4 {
                leaf-list static-lsp-regex {
                  type string;
                  ordered-by user;
                  description
                    "Next-hop static LSP name regular expression";
                }
              }
              case case_5 {
                leaf non-lsp-nexthop {
                  type empty;
                  description
                    "Next-hop with non-lsp";
                }
              }
              case case_6 {
                leaf non-labelled-nexthop {
                  type empty;
                  description
                    "Next-hop without tag";
                }
              }
              case case_7 {
                leaf overlay-vxlan-interfaces {
                  type empty;
                  description
                    "Next-hop for vxlan interfaces";
                }
              }
            }
          }
        }
      }
      container fallback {
        description
          "Backup option ";
        uses apply-advanced;
        choice nexthop-value {
          case case_1 {
            leaf-list lsp {
              type string;
              ordered-by user;
              description
                "Next-hop LSP name";
            }
          }
          case case_2 {
            leaf-list lsp-regex {
              type string;
              ordered-by user;
              description
                "Next-hop LSP name regular expression";
            }
          }
          case case_3 {
            leaf-list static-lsp {
              type string;
              ordered-by user;
              description
                "Next-hop static LSP name";
            }
          }
          case case_4 {
            leaf-list static-lsp-regex {
              type string;
              ordered-by user;
              description
                "Next-hop static LSP name regular expression";
            }
          }
          case case_5 {
            leaf non-lsp-nexthop {
              type empty;
              description
                "Next-hop with non-lsp";
            }
          }
          case case_6 {
            leaf non-labelled-nexthop {
              type empty;
              description
                "Next-hop without tag";
            }
          }
          case case_7 {
            leaf overlay-vxlan-interfaces {
              type empty;
              description
                "Next-hop for vxlan interfaces";
            }
          }
        }
        container except {
          description
            "Do not choose to install matching next hops";
          uses apply-advanced;
          choice nexthop-value {
            case case_1 {
              leaf-list lsp {
                type string;
                ordered-by user;
                description
                  "Next-hop LSP name";
              }
            }
            case case_2 {
              leaf-list lsp-regex {
                type string;
                ordered-by user;
                description
                  "Next-hop LSP name regular expression";
              }
            }
            case case_3 {
              leaf-list static-lsp {
                type string;
                ordered-by user;
                description
                  "Next-hop static LSP name";
              }
            }
            case case_4 {
              leaf-list static-lsp-regex {
                type string;
                ordered-by user;
                description
                  "Next-hop static LSP name regular expression";
              }
            }
            case case_5 {
              leaf non-lsp-nexthop {
                type empty;
                description
                  "Next-hop with non-lsp";
              }
            }
            case case_6 {
              leaf non-labelled-nexthop {
                type empty;
                description
                  "Next-hop without tag";
              }
            }
            case case_7 {
              leaf overlay-vxlan-interfaces {
                type empty;
                description
                  "Next-hop for vxlan interfaces";
              }
            }
          }
        }
      }
    }
    leaf trace {
      type empty;
      description
        "Log matches to a trace file";
    }
    container external {
      presence "enable external";
      description
        "External route";
      uses apply-advanced;
      leaf type {
        type union {
          type string {
            pattern "<.*>|$.*";
          }
          type int32 {
            range "1 .. 2";
          }
        }
        description
          "OSPF external metric type";
      }
      leaf nssa-only {
        type empty;
        description
          "Clear P-bit on lsa type 7";
      }
    }
    container load-balance {
      description
        "Type of load balancing in forwarding table";
      choice load_balance_type {
        case case_1 {
          leaf per-packet {
            type empty;
            description
              "Load balance on a per-packet basis deprecated, use per-flow instead";
          }
        }
        case case_2 {
          leaf per-flow {
            type empty;
            description
              "Load balance on a per-flow basis";
          }
        }
        case case_3;
        case case_4;
        case case_5;
        case case_6;
        case case_7;
        case case_8;
        case case_9;
        case case_10;
        case case_11;
      }
    }
    container advertise-locator {
      presence "enable advertise-locator";
      description
        "Advertise SRv6 Locator";
      uses apply-advanced;
      leaf internal {
        type empty;
        description
          "Advertise locator as Interal route";
      }
    }
    leaf set-down-bit {
      type empty;
      description
        "Set down bit";
    }
    leaf analyze {
      type empty;
      description
        "Send to registered controllers for analysis";
    }
    leaf destination-class {
      type string;
      description
        "Set destination class in forwarding table";
    }
    leaf source-class {
      type string;
      description
        "Set source class in forwarding table";
    }
    leaf forwarding-class {
      type string;
      description
        "Set source or destination class in forwarding table";
    }
    container map-to-interface {
      description
        "Set output logical interface";
      choice map_to_interface_value {
        case case_1 {
          leaf self {
            type empty;
            description
              "Map the interface to itself";
          }
        }
        case case_2 {
          leaf interface {
            type union {
              type jt:interface-name;
              type string {
                pattern "<.*>|$.*";
              }
            }
            description
              "Output logical interface";
          }
        }
      }
    }
    leaf-list ssm-source {
      type jt:ipaddr;
      ordered-by user;
      description
        "List of Sources for SSM mapping";
    }
    container p2mp-lsp-root {
      description
        "P2mp lsp root address";
      uses apply-advanced;
      leaf address {
        type jt:ipv4addr;
        description
          "Ipv4 root address";
      }
    }
    leaf dynamic-tunnel-attributes {
      type string;
      description
        "Choose the dynamic tunnel attributes used for forwarding";
    }
    leaf tunnel-end-point-address {
      type jt:ipaddr;
      description
        "Set tunnel end-point address of tunnel";
    }
    leaf selected-mldp-egress {
      type empty;
      description
        "This node should act as egress node for MLDP inband signalling";
    }
    leaf mhop-bfd-port {
      type empty;
      description
        "Use port number 4784 for MPLS-BFD as per RFC5884";
    }
    leaf no-backup {
      type empty;
      description
        "This prefix should not have backup";
    }
    leaf default-action {
      type enumeration {
        enum "accept" {
          description
            "Accept a route";
        }
        enum "reject" {
          description
            "Reject a route";
        }
      }
      description
        "Set default policy action";
    }
    leaf next {
      type enumeration {
        enum "policy" {
          description
            "Skip to next policy filter";
        }
        enum "term" {
          description
            "Skip to next term in a policy filter";
        }
      }
      description
        "Skip to next policy or term";
    }
    choice accept_reject {
      case case_1 {
        leaf accept {
          type empty;
          description
            "Accept a route";
        }
      }
      case case_2 {
        leaf reject {
          type empty;
          description
            "Reject a route";
        }
      }
    }
    container bgp-output-queue-priority {
      description
        "Set the BGP Update output queue priority.";
      choice class {
        case case_1 {
          leaf priority {
            type union {
              type string {
                pattern "<.*>|$.*";
              }
              type uint32 {
                range "1 .. 16";
              }
            }
            description
              "Output queue priority; higher is better";
          }
        }
        case case_2 {
          leaf expedited {
            type empty;
            description
              "Expedited queue; highest priority";
          }
        }
      }
    }
    leaf multipath-resolve {
      type empty;
      description
        "Use all paths for resolution over this prefix";
    }
    leaf source-routing-path-template {
      type string;
      description
        "Spring-te template to apply";
    }
    leaf label-allocation-fallback-reject {
      type empty;
      description
        "Suppress prefix export when label allocation fails";
    }
    leaf resolution-map {
      type string;
      description
        "Set resolution map modes";
    }
    leaf ignore-service-label {
      type empty;
      description
        "Ignore service labels";
    }
    container prefix-attribute-flags {
      presence "enable prefix-attribute-flags";
      description
        "Set ISIS prefix attribute flags sub TLV";
      uses apply-advanced;
      leaf node-segment-flag {
        type empty;
        description
          "Set node segment flag ";
      }
      leaf external-prefix-flag {
        type empty;
        description
          "Set external prefix flag ";
      }
      leaf anycast-flag {
        type empty;
        description
          "Set anycast flag ";
      }
      leaf entropy-label-capability-flag {
        type empty;
        description
          "Set entropy label capability flag ";
      }
    }
    container ipv4-source-router-id {
      presence "enable ipv4-source-router-id";
      description
        "Set IPv4 source router id in advertisement";
      uses apply-advanced;
      leaf router-id {
        type jt:ipaddr;
        description
          "Specify IPv4 address";
      }
    }
    container ipv6-source-router-id {
      presence "enable ipv6-source-router-id";
      description
        "Set IPv6 source router id in advertisement";
      uses apply-advanced;
      leaf router-id {
        type jt:ipv6addr;
        description
          "Specify IPv6 address";
      }
    }
    leaf request-long-lived-ack {
      type empty;
      description
        "Advertise route after forwarding is programmed";
    }
    leaf send-withdrawal-on-route-change {
      type empty;
      description
        "Withdraw route if change is not acked from forwarding";
    }
    container slice {
      description
        "Configure Policy Slice action";
      leaf slice-name {
        type string {
          length "1 .. 64";
        }
        description
          "Slice Name";
      }
    }
    leaf filter {
      type string;
      description
        "Set firewall-filter name";
    }
    leaf strip-as-path {
      type empty;
      description
        "Remove the incoming BGP as-path and replace with local AS";
    }
    container request-acknowledgements {
      description
        "Set request acknowledgement";
      leaf nexthop-ack {
        type empty;
        description
          "Set nexthop acknowledgement ";
      }
      leaf route-ack {
        type empty;
        description
          "Set route acknowledgement ";
      }
    }
  }

  grouping spring-te-template-map {
    description
      "SPRING-TE template color map";
    leaf name {
      type string;
      mandatory true;
      description
        "Name of SPRING-TE template";
    }
    uses apply-advanced;
    choice colors {
      case case_1 {
        leaf-list color {
          type union {
            type uint32;
            type string {
              pattern "<.*>|$.*";
            }
          }
          description
            "Set of color list to be mapped to corresponding SPRING-TE template";
        }
      }
      case case_2 {
        leaf color-any {
          type empty;
          description
            "Map any color to corresponding SPRING-TE template";
        }
      }
    }
  }

  grouping springte_lsp_nh_obj {
    uses apply-advanced;
    leaf nexthop {
      type string {
        length "1 .. 128";
      }
      mandatory true;
      description
        "SPRING-TE LSP to use to reach destination";
    }
    container lsp-source {
      description
        "Source of tunnel creation";
      uses apply-advanced;
      choice lsp-src-choice {
        case case_1 {
          leaf pcep {
            type empty;
            description
              "Path computation element protocol";
          }
        }
        case case_2 {
          leaf static {
            type empty;
            description
              "Static configuration";
          }
        }
        case case_3 {
          leaf dtm {
            type empty;
            description
              "Dynamic tunnel module";
          }
        }
        case case_4 {
          leaf bgp {
            type empty;
            description
              "BGP SRTE";
          }
        }
      }
    }
  }

  grouping syslog-object {
    leaf name {
      type enumeration {
        enum "any" {
          description
            "All facilities";
        }
        enum "authorization" {
          description
            "Authorization system";
        }
        enum "daemon" {
          description
            "Various system processes";
        }
        enum "ftp" {
          description
            "FTP process";
        }
        enum "ntp" {
          description
            "NTP process";
        }
        enum "security" {
          description
            "Security related";
        }
        enum "kernel" {
          description
            "Kernel";
        }
        enum "user" {
          description
            "User processes";
        }
        enum "dfc" {
          description
            "Dynamic flow capture";
        }
        enum "external" {
          description
            "Local external applications";
        }
        enum "firewall" {
          description
            "Firewall filtering system";
        }
        enum "pfe" {
          description
            "Packet Forwarding Engine";
        }
        enum "conflict-log" {
          description
            "Configuration conflict log";
        }
        enum "change-log" {
          description
            "Configuration change log";
        }
        enum "interactive-commands" {
          description
            "Commands executed by the UI";
        }
      }
      description
        "Facility type";
    }
    choice level {
      case case_1 {
        leaf any {
          type empty;
          description
            "All levels";
        }
      }
      case case_2 {
        leaf emergency {
          type empty;
          description
            "Panic conditions";
        }
      }
      case case_3 {
        leaf alert {
          type empty;
          description
            "Conditions that should be corrected immediately";
        }
      }
      case case_4 {
        leaf critical {
          type empty;
          description
            "Critical conditions";
        }
      }
      case case_5 {
        leaf error {
          type empty;
          description
            "Error conditions";
        }
      }
      case case_6 {
        leaf warning {
          type empty;
          description
            "Warning messages";
        }
      }
      case case_7 {
        leaf notice {
          type empty;
          description
            "Conditions that should be handled specially";
        }
      }
      case case_8 {
        leaf info {
          type empty;
          description
            "Informational messages";
        }
      }
      case case_9 {
        leaf none {
          type empty;
          description
            "No messages";
        }
      }
    }
  }

  grouping tacplus-server-object {
    leaf name {
      type jt:hostname;
      description
        "TACACS+ authentication server address";
    }
    uses apply-advanced;
    leaf routing-instance {
      type string;
      description
        "Routing instance";
    }
    leaf port {
      type union {
        type uint16;
        type string {
          pattern "<.*>|$.*";
        }
      }
      default "49";
      description
        "TACACS+ authentication server port number";
    }
    leaf secret {
      type jt:unreadable;
      description
        "Shared secret with the authentication server";
    }
    leaf timeout {
      type union {
        type string {
          pattern "<.*>|$.*";
        }
        type uint32 {
          range "1 .. 90";
        }
      }
      units "seconds";
      default "3";
      description
        "Request timeout period";
    }
    leaf single-connection {
      type empty;
      description
        "Optimize TCP connection attempts";
    }
    leaf source-address {
      type jt:hostname;
      description
        "Use specified address as source address";
    }
  }

  grouping te-class-object {
    leaf traffic-class {
      type enumeration {
        enum "ct0" {
          description
            "Traffic class 0";
        }
        enum "ct1" {
          description
            "Traffic class 1";
        }
        enum "ct2" {
          description
            "Traffic class 2";
        }
        enum "ct3" {
          description
            "Traffic class 3";
        }
      }
      description
        "Traffic class";
    }
    leaf priority {
      type union {
        type string {
          pattern "<.*>|$.*";
        }
        type uint32 {
          range "0 .. 7";
        }
      }
      description
        "Preemption priority for this class";
    }
  }

  grouping three-color-policer-type {
    description
      "Three-color policer";
    leaf name {
      type string;
      description
        "Policer name";
    }
    uses apply-advanced;
    container action {
      description
        "Action for three-color policer";
      uses apply-advanced;
      list loss-priority {
        key "name";
        ordered-by user;
        description
          "Loss priority for packet";
        uses three-color-policer-action;
      }
    }
    choice rate-type-choice {
      case case_1 {
        container single-rate {
          description
            "Single-rate policer";
          uses apply-advanced;
          choice mode-choice {
            case case_1 {
              leaf color-blind {
                type empty;
                description
                  "Color-blind mode";
              }
            }
            case case_2 {
              leaf color-aware {
                type empty;
                description
                  "Color-aware mode";
              }
            }
          }
          leaf committed-information-rate {
            type string;
            units "bits per second";
            description
              "Bandwidth allowed for committed traffic";
          }
          leaf committed-burst-size {
            type string;
            units "bytes";
            description
              "Burst size allowed for committed traffic";
          }
          leaf excess-burst-size {
            type string;
            units "bytes";
            description
              "Burst size allowed for excess traffic";
          }
        }
      }
      case case_2 {
        container two-rate {
          description
            "Two-rate policer";
          uses apply-advanced;
          choice mode-choice {
            case case_1 {
              leaf color-blind {
                type empty;
                description
                  "Color-blind mode";
              }
            }
            case case_2 {
              leaf color-aware {
                type empty;
                description
                  "Color-aware mode";
              }
            }
          }
          leaf committed-information-rate {
            type string;
            units "bits per second";
            description
              "Bandwidth allowed for committed traffic";
          }
          leaf committed-burst-size {
            type string;
            units "bytes";
          }
          leaf peak-information-rate {
            type string;
            units "bits per second";
            description
              "Bandwidth allowed for peak traffic";
          }
          leaf peak-burst-size {
            type string;
            units "bytes";
            description
              "Burst size allowed for peak traffic  ";
          }
        }
      }
    }
  }

  grouping three-color-policer-action {
    description
      "Action for three-color policer";
    leaf name {
      type enumeration {
        enum "high" {
          description
            "High loss priority";
        }
      }
      description
        "Loss priority for packet";
    }
    uses apply-advanced;
    container then {
      description
        "Action to take if the rate limits are exceeded";
      uses apply-advanced;
      leaf discard {
        type empty;
        description
          "Discard the packet";
      }
    }
  }

  grouping twamp-authentication-key-chain {
    leaf name {
      type string;
      description
        "Name of authentication key chain";
    }
    uses apply-advanced;
    list key-id {
      key "name";
      description
        "Authentication element configuration";
      leaf name {
        type string {
          length "1 .. 80";
        }
        description
          "Authentication element identifier";
      }
      uses apply-advanced;
      leaf secret {
        type string {
          length "1 .. 256";
        }
        mandatory true;
        description
          "Authentication key";
      }
    }
  }

  grouping vrrp-group {
    description
      "Virtual Router Redundancy Protocol group";
    leaf name {
      type union {
        type string {
          pattern "<.*>|$.*";
        }
        type uint32 {
          range "0 .. 255";
        }
      }
      description
        "Identifier for VRRP group";
    }
    uses apply-advanced;
    leaf priority {
      type union {
        type string {
          pattern "<.*>|$.*";
        }
        type uint32 {
          range "0 .. 255";
        }
      }
      description
        "Virtual router election priority";
    }
    leaf mode {
      type enumeration {
        enum "master" {
          description
            "VRRP mode master";
        }
        enum "backup" {
          description
            "VRRP mode backup";
        }
      }
    }
    choice advertisement_type {
      case case_1 {
        leaf advertise-interval {
          type union {
            type string {
              pattern "<.*>|$.*";
            }
            type uint32 {
              range "1 .. 255";
            }
          }
          units "seconds";
          description
            "Advertisement interval";
        }
      }
      case case_2 {
        leaf fast-interval {
          type union {
            type string {
              pattern "<.*>|$.*";
            }
            type uint32 {
              range "10 .. 40950";
            }
          }
          units "milliseconds";
          description
            "Fast advertisement interval";
        }
      }
      case case_3 {
        leaf inet6-advertise-interval {
          type union {
            type string {
              pattern "<.*>|$.*";
            }
            type uint32 {
              range "100 .. 40000";
            }
          }
          units "milliseconds";
          description
            "Inet6 advertisement interval";
        }
      }
    }
    leaf authentication-type {
      type enumeration {
        enum "simple" {
          description
            "Simple password";
        }
      }
      description
        "Authentication type";
    }
    leaf authentication-key {
      type string;
      description
        "Authentication key";
    }
    leaf virtual-mac-disable {
      type empty;
      description
        "Disable advertisement of virtual MAC address for configured virtual ip-address";
    }
    container track {
      description
        "Interfaces to track for VRRP group";
      uses apply-advanced;
      list interface {
        key "name";
        ordered-by user;
        description
          "Interface to track in VRRP group";
        leaf name {
          type union {
            type jt:interface-unit;
            type string {
              pattern "<.*>|$.*";
            }
          }
          description
            "Name of interface";
        }
        uses apply-advanced;
        container weight {
          description
            "Adjust priority by this weight";
          uses apply-advanced;
          leaf cost {
            type union {
              type string {
                pattern "<.*>|$.*";
              }
              type int32 {
                range "-253 .. 253";
              }
            }
            description
              "Value to subtract from priority when interface is down";
          }
          leaf reverse {
            type empty;
            description
              "Will cause vrrp instance to be down when interface is up and vice versa";
          }
        }
      }
      list track-script {
        key "name";
        ordered-by user;
        description
          "Tracking script for VRRP group";
        leaf name {
          type string;
          description
            "Script instance";
        }
        uses apply-advanced;
        leaf script-name {
          type string;
          description
            "Name of script";
        }
        leaf interval {
          type union {
            type string {
              pattern "<.*>|$.*";
            }
            type uint32 {
              range "0 .. 4294967295";
            }
          }
          description
            "Run script at every interval";
        }
        leaf time-out {
          type union {
            type string {
              pattern "<.*>|$.*";
            }
            type uint32 {
              range "0 .. 4294967295";
            }
          }
          description
            "Timeout";
        }
        leaf rise {
          type union {
            type string {
              pattern "<.*>|$.*";
            }
            type uint32 {
              range "1 .. 4294967295";
            }
          }
          description
            "Rise";
        }
        leaf fall {
          type union {
            type string {
              pattern "<.*>|$.*";
            }
            type uint32 {
              range "1 .. 4294967295";
            }
          }
          description
            "Fall";
        }
        container weight {
          description
            "Adjust priority by this weight";
          uses apply-advanced;
          leaf cost {
            type union {
              type string {
                pattern "<.*>|$.*";
              }
              type int32 {
                range "-253 .. 253";
              }
            }
            description
              "Value to subtract from priority when script returns non-zero code";
          }
          leaf reverse {
            type empty;
            description
              "Will cause vrrp instance to be down when script is up and vice versa";
          }
        }
      }
      leaf-list notify-script {
        type string;
        ordered-by user;
        description
          "Notify script for VRRP group";
      }
      container notify-master {
        description
          "Notify script to MASTER transition";
        uses apply-advanced;
        leaf-list script-name {
          type string;
          ordered-by user;
          description
            "Name of script";
        }
        leaf username {
          type string;
          description
            "Username under which scripts should run";
        }
      }
      container notify-backup {
        description
          "Notify script to BACKUP transition";
        uses apply-advanced;
        leaf-list script-name {
          type string;
          ordered-by user;
          description
            "Name of script";
        }
        leaf username {
          type string;
          description
            "Username under which scripts should run";
        }
      }
      container notify-fault {
        description
          "Notify script to FAULT transition";
        uses apply-advanced;
        leaf-list script-name {
          type string;
          ordered-by user;
          description
            "Name of script";
        }
        leaf username {
          type string;
          description
            "Username under which scripts should run";
        }
      }
    }
    list virtual-address {
      key "name";
      ordered-by user;
      description
        "Virtual IPv4 address";
      uses virtual-address;
    }
    container unicast {
      description
        "Unicast parameters";
      uses apply-advanced;
      list local-address {
        key "name";
        ordered-by user;
        description
          "Unicast local ipv4 address";
        uses inet-local-address;
      }
      list peer-address {
        key "name";
        ordered-by user;
        description
          "Unicast peer ipv4 address";
        uses inet-peer-address;
      }
    }
  }

  grouping inet-local-address {
    leaf name {
      type jt:ipv4addr;
      description
        "One or more unicast source ipv4 address";
    }
    uses apply-advanced;
  }

  grouping inet-peer-address {
    leaf name {
      type jt:ipv4addr;
      description
        "One or more unicast peer ipv4 address";
    }
    uses apply-advanced;
  }

  grouping virtual-address {
    leaf name {
      type jt:ipv4prefix;
      description
        "One or more virtual IPv4 addresses";
    }
    uses apply-advanced;
    leaf device-name {
      type union {
        type jt:interface-unit;
        type string {
          pattern "<.*>|$.*";
        }
      }
      description
        "Name of device";
    }
  }

  grouping vrrp-inet6-group {
    description
      "Virtual Router Redundancy Protocol group";
    leaf name {
      type union {
        type string {
          pattern "<.*>|$.*";
        }
        type uint32 {
          range "0 .. 255";
        }
      }
      description
        "Identifier for VRRP group";
    }
    uses apply-advanced;
    leaf priority {
      type union {
        type string {
          pattern "<.*>|$.*";
        }
        type uint32 {
          range "0 .. 255";
        }
      }
      description
        "Virtual router election priority";
    }
    leaf mode {
      type enumeration {
        enum "master" {
          description
            "VRRP mode master";
        }
        enum "backup" {
          description
            "VRRP mode backup";
        }
      }
    }
    choice advertisement_type {
      case case_1 {
        leaf advertise-interval {
          type union {
            type string {
              pattern "<.*>|$.*";
            }
            type uint32 {
              range "1 .. 255";
            }
          }
          units "seconds";
          description
            "Advertisement interval";
        }
      }
      case case_2 {
        leaf fast-interval {
          type union {
            type string {
              pattern "<.*>|$.*";
            }
            type uint32 {
              range "10 .. 40950";
            }
          }
          units "milliseconds";
          description
            "Fast advertisement interval";
        }
      }
      case case_3 {
        leaf inet6-advertise-interval {
          type union {
            type string {
              pattern "<.*>|$.*";
            }
            type uint32 {
              range "100 .. 40000";
            }
          }
          units "milliseconds";
          description
            "Inet6 advertisement interval";
        }
      }
    }
    leaf authentication-type {
      type enumeration {
        enum "simple" {
          description
            "Simple password";
        }
      }
      description
        "Authentication type";
    }
    leaf authentication-key {
      type string;
      description
        "Authentication key";
    }
    leaf virtual-mac-disable {
      type empty;
      description
        "Disable advertisement of virtual MAC address for configured virtual ip-address";
    }
    container track {
      description
        "Interfaces to track for VRRP group";
      uses apply-advanced;
      list interface {
        key "name";
        ordered-by user;
        description
          "Interface to track in VRRP group";
        leaf name {
          type union {
            type jt:interface-unit;
            type string {
              pattern "<.*>|$.*";
            }
          }
          description
            "Name of interface";
        }
        uses apply-advanced;
        container weight {
          description
            "Adjust priority by this weight";
          uses apply-advanced;
          leaf cost {
            type union {
              type string {
                pattern "<.*>|$.*";
              }
              type int32 {
                range "-253 .. 253";
              }
            }
            description
              "Value to subtract from priority when interface is down";
          }
          leaf reverse {
            type empty;
            description
              "Will cause vrrp instance to be down when interface is up and vice versa";
          }
        }
      }
      list track-script {
        key "name";
        ordered-by user;
        description
          "Tracking script for VRRP group";
        leaf name {
          type string;
          description
            "Script instance";
        }
        uses apply-advanced;
        leaf script-name {
          type string;
          description
            "Name of script";
        }
        leaf interval {
          type union {
            type string {
              pattern "<.*>|$.*";
            }
            type uint32 {
              range "0 .. 4294967295";
            }
          }
          description
            "Run script at every interval";
        }
        leaf time-out {
          type union {
            type string {
              pattern "<.*>|$.*";
            }
            type uint32 {
              range "0 .. 4294967295";
            }
          }
          description
            "Timeout";
        }
        leaf rise {
          type union {
            type string {
              pattern "<.*>|$.*";
            }
            type uint32 {
              range "1 .. 4294967295";
            }
          }
          description
            "Rise";
        }
        leaf fall {
          type union {
            type string {
              pattern "<.*>|$.*";
            }
            type uint32 {
              range "1 .. 4294967295";
            }
          }
          description
            "Fall";
        }
        container weight {
          description
            "Adjust priority by this weight";
          uses apply-advanced;
          leaf cost {
            type union {
              type string {
                pattern "<.*>|$.*";
              }
              type int32 {
                range "-253 .. 253";
              }
            }
            description
              "Value to subtract from priority when script returns non-zero code";
          }
          leaf reverse {
            type empty;
            description
              "Will cause vrrp instance to be down when script is up and vice versa";
          }
        }
      }
      leaf-list notify-script {
        type string;
        ordered-by user;
        description
          "Notify script for VRRP group";
      }
      container notify-master {
        description
          "Notify script to MASTER transition";
        uses apply-advanced;
        leaf-list script-name {
          type string;
          ordered-by user;
          description
            "Name of script";
        }
        leaf username {
          type string;
          description
            "Username under which scripts should run";
        }
      }
      container notify-backup {
        description
          "Notify script to BACKUP transition";
        uses apply-advanced;
        leaf-list script-name {
          type string;
          ordered-by user;
          description
            "Name of script";
        }
        leaf username {
          type string;
          description
            "Username under which scripts should run";
        }
      }
      container notify-fault {
        description
          "Notify script to FAULT transition";
        uses apply-advanced;
        leaf-list script-name {
          type string;
          ordered-by user;
          description
            "Name of script";
        }
        leaf username {
          type string;
          description
            "Username under which scripts should run";
        }
      }
    }
    list virtual-inet6-address {
      key "name";
      ordered-by user;
      description
        "Virtual IPv6 address";
      uses virtual-inet6-address;
    }
    container unicast {
      description
        "Unicast parameters";
      uses apply-advanced;
      list local-address {
        key "name";
        ordered-by user;
        description
          "Unicast local ipv6 address";
        uses inet6-local-address;
      }
      list peer-address {
        key "name";
        ordered-by user;
        description
          "Unicast peer ipv6 address";
        uses inet6-peer-address;
      }
    }
  }

  grouping inet6-local-address {
    leaf name {
      type jt:ipv6addr;
      description
        "One or more unicast source ipv6 address";
    }
    uses apply-advanced;
  }

  grouping inet6-peer-address {
    leaf name {
      type jt:ipv6addr;
      description
        "One or more unicast peer ipv6 address";
    }
    uses apply-advanced;
  }

  grouping virtual-inet6-address {
    leaf name {
      type jt:ipv6prefix;
      description
        "One or more virtual IPv6 addresses";
    }
    uses apply-advanced;
    leaf device-name {
      type union {
        type jt:interface-unit;
        type string {
          pattern "<.*>|$.*";
        }
      }
      description
        "Name of device";
    }
  }

  container configuration {
    config true;
    uses juniper-config;
    list groups {
      key "name";
      ordered-by user;
      description
        "Configuration groups";
      uses juniper-group;
    }
  }
}
