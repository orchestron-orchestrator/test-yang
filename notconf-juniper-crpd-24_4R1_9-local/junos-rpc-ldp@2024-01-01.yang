module junos-rpc-ldp {
  namespace "http://yang.juniper.net/junos/rpc/ldp";
  prefix ldp;

  import junos-common-types {
    prefix jt;
    revision-date 2024-01-01;
  }

  organization
    "Juniper Networks, Inc.";
  contact
    "yang-support@juniper.net";
  description
    "Junos RPC YANG module for ldp command(s)";

  revision 2024-01-01 {
    description
      "Junos: 20241218.202301_builder.r1463698";
  }

  grouping ldp-neighbor-information-block {
    list ldp-neighbor {
      key "ldp-neighbor-address";
      leaf ldp-neighbor-address {
        type jt:ipaddr;
      }
      leaf interface-name {
        type string;
        description
          "Name of interface";
      }
      leaf ldp-label-space-id {
        type string;
      }
      leaf ldp-remaining-time {
        type int32;
      }
      leaf ldp-local-transport-address {
        type jt:ipaddr;
      }
      leaf ldp-transport-address {
        type jt:ipaddr;
      }
      leaf ldp-transport-preference {
        type string;
      }
      leaf ldp-config-sequence {
        type uint32;
      }
      leaf ldp-up-time {
        type string;
      }
      leaf ldp-reference-count {
        type int32;
      }
      leaf ldp-auto-discovered-reference-count {
        type int32;
      }
      leaf ldp-holdtime {
        type int32;
      }
      leaf ldp-proposed-local-holdtime {
        type int32;
        description
          "The local value of the hold time";
      }
      leaf ldp-proposed-peer-holdtime {
        type int32;
        description
          "The peer's proposed value of the hold time";
      }
      leaf ldp-hello-interval {
        type int32;
      }
      container ldp-neighbor-hello-flags {
        description
          "LDP neighbor hello flags";
        leaf-list ldp-neighbor-hello-flag {
          type string;
          description
            "LDP neighbor hello flag";
        }
      }
      container ldp-neighbor-types {
        description
          "LDP neighbor types";
        leaf-list ldp-neighbor-type {
          type string;
          description
            "LDP neighbor type";
        }
      }
    }
  }

  rpc get-ldp-neighbor-information {
    description
      "Show LDP neighbor status";

    input {
      choice daemon-select {
        case logical-system {
          leaf logical-system {
            type string;
            description
              "Name of logical system, or 'all'";
          }
        }
      }
      leaf verbosity_level {
        type enumeration {
          enum "brief" {
            description
              "Display brief output (default)";
          }
          enum "detail" {
            description
              "Display detailed output";
          }
          enum "extensive" {
            description
              "Display extensive output";
          }
        }
        default "brief";
      }
      leaf instance {
        type string;
        description
          "Name of LDP routing instance";
      }
      leaf neighbor {
        type jt:ipaddr;
        description
          "IP address of the neighbor";
      }
      leaf neighbor-type {
        type enumeration {
          enum "auto-targeted" {
            description
              "Auto targeted neighbors";
          }
          enum "auto-discovery" {
            description
              "Auto discovery neighbors";
          }
          enum "link-protection" {
            description
              "Link protection neighbors";
          }
          enum "session-protection" {
            description
              "Session protection neighbors";
          }
        }
      }
    }
    output {
      container ldp-neighbor-information {
        uses ldp-neighbor-information-block;
      }
    }
  }
}
